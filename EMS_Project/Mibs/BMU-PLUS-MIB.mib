--*****************************************************************************
--				UTL BMU PLUS MIB
--*****************************************************************************

BMU-PLUS-MIB DEFINITIONS ::= BEGIN
 
		IMPORTS
        	RowStatus      			FROM STANDARD-MIB

        	DisplayString  			FROM RFC1213-MIB       
			
    		OBJECT-IDENTITY, 
    		NOTIFICATION-TYPE, 
    		MODULE-IDENTITY, 
    		Integer32, 
    		Unsigned32,
    		IpAddress,
    		TimeTicks			FROM SNMPv2-SMI
    		
	 	OBJECT-TYPE    			FROM RFC-1212
	 		
		MODULE-COMPLIANCE, 
		OBJECT-GROUP, 
		NOTIFICATION-GROUP		FROM SNMPv2-CONF
			
		node, 
		rack, 
		subRack, 
		slot 				FROM SCC-MIB

		enterprises 			FROM RFC1155-SMI		

	;

	utl   	MODULE-IDENTITY
	
            	LAST-UPDATED    	"1807130630Z"
            	ORGANIZATION    	"United Telecoms Limited, Bangalore-560048."
            	CONTACT-INFO    	"Website: http://www.utlindia.com."                                           
            	DESCRIPTION     	"MIB module for UTL DWDM."
            	REVISION 	    	"1807130630Z"
            	DESCRIPTION    	 	"MIB module for BMU Plus Card."
            
            	::= { enterprises 18036 }

	utlrnd  OBJECT-IDENTITY
            	STATUS  current
            
		DESCRIPTION "UTL R and D."
            	
		::= { utl 1 }

	dwdm 				OBJECT IDENTIFIER	::=   { utlrnd 1 }
	indus 				OBJECT IDENTIFIER	::=   { dwdm 1 }
	bmuPlus 			OBJECT IDENTIFIER 	::=   { indus 46 }

	bmuPlusCardGeneralDetails 	OBJECT IDENTIFIER 	::=   { bmuPlus 1 }
	bmuPlusConfiguration 		OBJECT IDENTIFIER 	::=   { bmuPlus 2 }	

--*****************************************************************************
--			BMU PLUS CARD GENERAL DETAILS
--*****************************************************************************

	bmuPlusCardGeneralDetailsTable OBJECT-TYPE 
		SYNTAX 		SEQUENCE OF BmuPlusCardGeneralDetailsEntry
		MAX-ACCESS	not-accessible
		STATUS		current

		DESCRIPTION
		 " we can get BMU Plus card general details "

		::= { bmuPlusCardGeneralDetails 1 }

	bmuPlusCardGeneralDetailsEntry OBJECT-TYPE
		SYNTAX  	BmuPlusCardGeneralDetailsEntry
		MAX-ACCESS  	not-accessible
		STATUS  	current

		DESCRIPTION 
		 "Enter node rack, subrack, slot and bmuPlusInterface numbers"

		INDEX   { node, rack, subRack, slot, bmuPlusInterface }
		::= { bmuPlusCardGeneralDetailsTable 1 }

	BmuPlusCardGeneralDetailsEntry ::=
		SEQUENCE {
				bmuPlusInterface				INTEGER,
				bmuPlusEepromCardId				INTEGER,
				bmuPlusEepromCardName				DisplayString,
				bmuPlusEepromPartCode				DisplayString,
				bmuPlusEepromCardSerialNumber			DisplayString,
				bmuPlusEepromHardwareExternalReleaseVersion	DisplayString,
				bmuPlusSoftwareExternalReleaseVersion		DisplayString,
				bmuPlusEepromHardwareInternalReleaseVersion	DisplayString,
				bmuPlusSoftwareInternalReleaseVersion		DisplayString,
				bmuPlusEepromCardUidNumber			DisplayString,
				bmuPlusEepromCardEUI48Number			DisplayString,
				bmuPlusEepromCardEUI64Number			DisplayString,
				bmuPlusCardRootFileSystemVersion		DisplayString,
				bmuPlusInstallationDate				DisplayString,
				bmuPlusCommissionDate				DisplayString,
				bmuPlusCardRunningTime				DisplayString,
				bmuPlusCardRestartCount				INTEGER,
				bmuPlusCardGeneralDetailsTableRowStatus		RowStatus
			}
			
	bmuPlusInterface OBJECT-TYPE
		SYNTAX  		INTEGER
		MAX-ACCESS  	not-accessible
		STATUS  		current
		DESCRIPTION 	"bmuPlusInterface number"
		::= { bmuPlusCardGeneralDetailsEntry 1 }
			
	bmuPlusEepromCardId OBJECT-TYPE
		SYNTAX  	INTEGER
		MAX-ACCESS  	read-only
		STATUS  	current

		DESCRIPTION
		 " Tells the card ID of the BMU-PLUS card, present in the EEPROM.
		 	bmuPlusInterface = 1 "

		::= { bmuPlusCardGeneralDetailsEntry 2 }

	bmuPlusEepromCardName OBJECT-TYPE
		SYNTAX  	DisplayString (SIZE (0..255))
		MAX-ACCESS  	read-only
		STATUS		current

		DESCRIPTION
		 " Tells the card name of the BMU-PLUS card, present in the EEPROM.
		 	bmuPlusInterface = 1 "

		::= { bmuPlusCardGeneralDetailsEntry 3 }

	bmuPlusEepromPartCode OBJECT-TYPE
		SYNTAX  	DisplayString (SIZE (0..255))
		MAX-ACCESS  	read-only
		STATUS		current

		DESCRIPTION
		 " Tells the part code of the BMU-PLUS card, present in the EEPROM.
		 	bmuPlusInterface = 1 "

		::= { bmuPlusCardGeneralDetailsEntry 4 }

	bmuPlusEepromCardSerialNumber OBJECT-TYPE
		SYNTAX  	DisplayString (SIZE (0..255))
		MAX-ACCESS  	read-write
		STATUS		current

		DESCRIPTION
		 " This property get / set the information about BMU-PLUS 
		 	Card's Serial Number.
		 	bmuPlusInterface = 1 "

		::= { bmuPlusCardGeneralDetailsEntry 5 }

	bmuPlusEepromHardwareExternalReleaseVersion OBJECT-TYPE
		SYNTAX  	DisplayString (SIZE (0..255))
		MAX-ACCESS  	read-only
		STATUS		current

		DESCRIPTION
		 " To get the Card's Hardware External Release Version. This detail 
		 	will be displayed to the customer. This version will increment 
		 	only if there are significant architectural changes in the product.
		 	bmuPlusInterface = 1 "

		::= { bmuPlusCardGeneralDetailsEntry 6 }

	bmuPlusSoftwareExternalReleaseVersion OBJECT-TYPE
		SYNTAX  	DisplayString (SIZE (0..255))
		MAX-ACCESS  	read-only
		STATUS		current

		DESCRIPTION
		 " To get the Card's Software External Release Version.  This detail 
		 will be displayed to the customer. This version will increment 
		 only if there are significant architectural changes in the product
		 bmuPlusInterface = 1 "

		::= { bmuPlusCardGeneralDetailsEntry 7 }

	bmuPlusEepromHardwareInternalReleaseVersion OBJECT-TYPE
		SYNTAX  	DisplayString (SIZE (0..255))
		MAX-ACCESS  	read-only
		STATUS		current

		DESCRIPTION
		 " To get the Card's Hardware Internal Release Version. This detail 
		 is used for development purposes only. It differs from the external 
		 hardware version.
		 bmuPlusInterface = 1 "

		::= { bmuPlusCardGeneralDetailsEntry 8 }

	bmuPlusSoftwareInternalReleaseVersion OBJECT-TYPE
		SYNTAX  	DisplayString (SIZE (0..255))
		MAX-ACCESS  	read-only
		STATUS		current

		DESCRIPTION
		 " To get the Card's Software Internal Release Version.  This detail 
		 is used for development purposes only. It differs from the external 
		 software version.
		 bmuPlusInterface = 1 "

		::= { bmuPlusCardGeneralDetailsEntry 9 }

	bmuPlusEepromCardUidNumber OBJECT-TYPE
		SYNTAX  	DisplayString (SIZE (0..255))
		MAX-ACCESS  	read-only
		STATUS		current

		DESCRIPTION
		 " Tells the Card Unique Identifier It is a 4 byte address used to 
		 uniquely identify a card.
		 bmuPlusInterface = 1 "

		::= { bmuPlusCardGeneralDetailsEntry 10 }

	bmuPlusEepromCardEUI48Number OBJECT-TYPE
		SYNTAX  	DisplayString (SIZE (0..255))
		MAX-ACCESS  	read-only
		STATUS		current

		DESCRIPTION
		 " Tells the Card EUI-48 Number. It’s a 6 byte address used to 
		 uniquely identify a card.
		 bmuPlusInterface = 1 "

		::= { bmuPlusCardGeneralDetailsEntry 11 }

	bmuPlusEepromCardEUI64Number OBJECT-TYPE
		SYNTAX  	DisplayString (SIZE (0..255))
		MAX-ACCESS  	read-only
		STATUS		current

		DESCRIPTION
		 " Tells the Card EUI-64 Number. It’s a 8 byte address.
		 bmuPlusInterface = 1 "

		::= { bmuPlusCardGeneralDetailsEntry 12 }
		
	bmuPlusCardRootFileSystemVersion OBJECT-TYPE		 
		SYNTAX  DisplayString
		MAX-ACCESS  read-only
		STATUS current
		DESCRIPTION
			"Tells the Card's Root File System Version
			-----------------------------
			bmuPlusInterface: 1
			-----------------------------
			Value:
		      	eg: 8
			-----------------------------"
		::= { bmuPlusCardGeneralDetailsEntry 13 }

	bmuPlusInstallationDate OBJECT-TYPE
		SYNTAX  		DisplayString (SIZE (0..255))
		MAX-ACCESS  	read-write
		STATUS			current

		DESCRIPTION
		 " To get the card's installation date in dd/mm/yyyy format.
		 bmuPlusInterface = 1 "

		::= { bmuPlusCardGeneralDetailsEntry 22 }

	bmuPlusCommissionDate OBJECT-TYPE
		SYNTAX  		DisplayString (SIZE (0..255))
		MAX-ACCESS  	read-write
		STATUS			current

		DESCRIPTION
		 " To get the card's commission date in  dd/mm/yyyy format.
		 bmuPlusInterface = 1 "

		::= { bmuPlusCardGeneralDetailsEntry 23 }

	bmuPlusCardRunningTime OBJECT-TYPE
		SYNTAX  	DisplayString (SIZE (0..255))
		MAX-ACCESS  	read-only
		STATUS		current

		DESCRIPTION
		 " To get the duration of time for which the card is operational/running.
		 bmuPlusInterface = 1 "

		::= { bmuPlusCardGeneralDetailsEntry 24 }

	bmuPlusCardRestartCount OBJECT-TYPE
		SYNTAX  	INTEGER
		MAX-ACCESS  	read-only
		STATUS		current

		DESCRIPTION
		 " To get the number of times the card has been soft reset. This value 
		 will get reset to 0 on factory reset.
		 bmuPlusInterface = 1 "

		::= { bmuPlusCardGeneralDetailsEntry 25 }

	bmuPlusCardGeneralDetailsTableRowStatus OBJECT-TYPE
		SYNTAX		RowStatus
		MAX-ACCESS	read-write
		STATUS		current
		DESCRIPTION
			"This is MIB realted property,
			NOT to be considered as a card property"

		::= { bmuPlusCardGeneralDetailsEntry 26 }

--*****************************************************************************
--				BMU PLUS CONFIGURATION
--*****************************************************************************

	bmuPlusConfigurationTable OBJECT-TYPE
		SYNTAX  	SEQUENCE OF BmuPlusConfigurationEntry
		MAX-ACCESS  	not-accessible
		STATUS  	current

		DESCRIPTION
		 " we can get BMU Plus configuration details "

		::= { bmuPlusConfiguration 1 }
              
        bmuPlusConfigurationEntry OBJECT-TYPE
		SYNTAX  	BmuPlusConfigurationEntry
		MAX-ACCESS  	not-accessible
		STATUS  	current

		DESCRIPTION 
		 "Enter node rack, subrack, slot and bmuPlusInterface numbers"

		INDEX   { node, rack, subRack, slot, bmuPlusInterface }

		::= { bmuPlusConfigurationTable 1 }
	
	BmuPlusConfigurationEntry ::= 
		SEQUENCE {
				bmuPlusCardSoftwareUpgrade		DisplayString,				
				bmuPlusSoftReset 			INTEGER,
				bmuPlusSyncSystemTimeWithNtpServer				DisplayString,
				bmuPlusSyncRtcWithNtpServer						DisplayString,
				bmuPlusSyncRtcWithSystemTime					DisplayString,
				bmuPlusUpdateGivenTimeIntoSystem				DisplayString,
				bmuPlusUpdateGivenTimeIntoRtc					DisplayString,
				bmuPlusSystemTimeAndRtcTime						DisplayString,
				bmuPlusConfigurationTableRowStatus	RowStatus
			}

	bmuPlusCardSoftwareUpgrade OBJECT-TYPE
		SYNTAX 		DisplayString
		MAX-ACCESS 	read-write
		STATUS 		current
		DESCRIPTION
			"Valid only as SET command.
			This property upgrades the software of the BMU-PLUS card
			It takes the path of the software release as
			a value,
			scuPlusInterface: 0
			Values:
			eg: /home/root/rel-2.0.0.tar.gz
			-----------------------------"

		::= { bmuPlusConfigurationEntry 1 }

 	bmuPlusSoftReset OBJECT-TYPE
		SYNTAX  	INTEGER
		MAX-ACCESS  	read-write
		STATUS  	current

		DESCRIPTION
		 " soft reset the card with value 1.
		 bmuPlusInterface = 1 "

		::= { bmuPlusConfigurationEntry 2 }

	bmuPlusSyncSystemTimeWithNtpServer	 OBJECT-TYPE
		SYNTAX  		DisplayString
  		MAX-ACCESS  		read-write
  		STATUS  		current
  		DESCRIPTION	 	" when we want to manually sync the time value
						present in linux kernel with the NTP server
						we can use this OID. We can provide NTP server
						ip address as a value to this OID and the time
						will be synced to that ilarticular server. 
						If we are not providing NTP server IP address 
						then the system will be synced with the NTP server 
						which is already been registered with card. 
						If both are absent then error message will be returned
						-----------------------------
							Interface 	: 0
						-----------------------------
						If we want to provide NTP server IP address then
						Value should be a valid IP address as shown below
						: 192.168.21.25
						
						If we don't want to provide NTP server address then no
						need to pass any value. 
						---------------------------"
  						
  		::= { bmuPlusConfigurationEntry 7 }
  		
  	bmuPlusSyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface 	: 0
						-----------------------------
						If we want to provide NTP server IP address then
						Value should be a valid IP address as shown below
						: 192.168.21.25
							
						If we don't want to provide NTP server address, then no
						need to ilass any value. 
						---------------------------"
  						
  		::= { bmuPlusConfigurationEntry 8 }
  		
  	bmuPlusSyncRtcWithSystemTime	 OBJECT-TYPE
		SYNTAX  		DisplayString
  		MAX-ACCESS  	read-write
  		STATUS  		current
  		DESCRIPTION	 	" when we want to manually sync the time value
						present in RTC with the time value in linux kernel
						we can use this OID. With this set operation, 
						the time available with linux kernel will be updated
						into RTC. It is not required to provide any value for 
						this operation
						-----------------------------
						Interface 	: 0
						-----------------------------"
  						
  		::= { bmuPlusConfigurationEntry 9 }
  		
  	bmuPlusUpdateGivenTimeIntoSystem	 OBJECT-TYPE
		SYNTAX  		DisplayString
  		MAX-ACCESS  	read-write
  		STATUS  		current
  		DESCRIPTION	 	" when we want to manually update system time
						with the user provided time, we can use this OID.
						With OID we need to provide time value which we
						want to update in the system.
						-----------------------------
						Interface 	: 0
						-----------------------------
						Value should be of given format:
						YYYY-MM-DD H:M:S
						
						Example: 2017-10-31 15:20:44
						---------------------------"
						
  		::= { bmuPlusConfigurationEntry 10 }
  		
  	bmuPlusUpdateGivenTimeIntoRtc	 OBJECT-TYPE
		SYNTAX  		DisplayString
  		MAX-ACCESS  	read-write
  		STATUS  		current
  		DESCRIPTION	 	" when we want to manually update RTC time
						with the user provided time, we can use this OID.
						With OID we need to provide time value which we
						want to update in RTC.
						-----------------------------
						Interface 	: 0
						-----------------------------
						Value should be of given format:
						YYYY-MM-DD H:M:S
						
						Example: 2017-10-31 15:20:44
						---------------------------"
						
  		::= { bmuPlusConfigurationEntry 11 }
  		
  	bmuPlusSystemTimeAndRtcTime	 OBJECT-TYPE
		SYNTAX  		DisplayString
  		MAX-ACCESS  		read-only
  		STATUS  		current
  		DESCRIPTION	 	" get the system time and time value present in RTC.
						-----------------------------
						Interface 	: 0
						-----------------------------"
						
  		::= { bmuPlusConfigurationEntry 12 }
		
	bmuPlusConfigurationTableRowStatus OBJECT-TYPE
              SYNTAX      RowStatus
              MAX-ACCESS  read-write
              STATUS      current
              DESCRIPTION
                      "	This is MIB realted property,
			NOT to be considered as a card property"
              ::= { bmuPlusConfigurationEntry 20 }
		
--***************************************************************************** 
		  	  
	snmpcurrentGroup OBJECT-GROUP
		OBJECTS {
				bmuPlusInterface,
				bmuPlusEepromCardId,
				bmuPlusEepromCardName,
				bmuPlusEepromPartCode,
				bmuPlusEepromCardSerialNumber,
				bmuPlusEepromHardwareExternalReleaseVersion,
				bmuPlusSoftwareExternalReleaseVersion,
				bmuPlusEepromHardwareInternalReleaseVersion,
				bmuPlusSoftwareInternalReleaseVersion,
				bmuPlusEepromCardUidNumber,
				bmuPlusEepromCardEUI48Number,
				bmuPlusEepromCardEUI64Number,
				bmuPlusCardRootFileSystemVersion,
				bmuPlusInstallationDate,
				bmuPlusCommissionDate,
				bmuPlusCardRunningTime,
				bmuPlusCardRestartCount,
				bmuPlusCardGeneralDetailsTableRowStatus,
				bmuPlusCardSoftwareUpgrade,	
				bmuPlusSoftReset,
				bmuPlusSyncSystemTimeWithNtpServer,
				bmuPlusSyncRtcWithNtpServer,
				bmuPlusSyncRtcWithSystemTime,
				bmuPlusUpdateGivenTimeIntoSystem,
				bmuPlusUpdateGivenTimeIntoRtc,
				bmuPlusSystemTimeAndRtcTime,
				bmuPlusConfigurationTableRowStatus
 			}
		STATUS  current

		DESCRIPTION
		 "A collection of objects from RFC 1213 made current by this MIB module."

		::= { utlrnd 2 }
	
END

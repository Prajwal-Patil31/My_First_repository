--*****************************************************************************
--			MIB FILE FOR THE OMMP401 CARD
--*****************************************************************************

OMMP401-MIB DEFINITIONS ::= BEGIN
 
          IMPORTS
        	
		RowStatus      			FROM STANDARD-MIB
			
		DisplayString  			FROM RFC1213-MIB       
    	
    		OBJECT-IDENTITY,
    		NOTIFICATION-TYPE,
    		MODULE-IDENTITY,
    		Integer32,
    		Unsigned32,
    		IpAddress,
    		TimeTicks			FROM SNMPv2-SMI
	 
	 	OBJECT-TYPE    			FROM RFC-1212
	 		
		MODULE-COMPLIANCE,
		OBJECT-GROUP,
		NOTIFICATION-GROUP		FROM SNMPv2-CONF
	
		node,
		rack,
		subRack,
		slot				FROM SCC-MIB
    
		enterprises			FROM RFC1155-SMI
	;

 

	utl   MODULE-IDENTITY
            LAST-UPDATED    	"1807130630Z"
            ORGANIZATION    	"United Telecoms Limited, Bangalore-560048."
            CONTACT-INFO    	"Website: http://www.utlindia.com."                                           
            DESCRIPTION     	"MIB module for UTL 40/80 channel DWDM."
            REVISION 	    	"1807130630Z"
            DESCRIPTION    	"MIB module for OMMP401 Card."
            ::= { enterprises 18036 }

	utlrnd  OBJECT-IDENTITY
            STATUS  current
            DESCRIPTION "UTL Research and Development."
            ::= { utl 1 }

	dwdm 	OBJECT IDENTIFIER				::=	{ utlrnd 1 }
	indus 	OBJECT IDENTIFIER				::=	{ dwdm 1 }
	ommp401 	OBJECT IDENTIFIER 			::=	{ indus 90 }

	ommp401CardGeneralDetails OBJECT IDENTIFIER		::=	{ ommp401 1 }
	ommp401Configuration OBJECT IDENTIFIER 		::=	{ ommp401 2 }
	ommp401Alarm OBJECT IDENTIFIER 			::=	{ ommp401 3 }
	ommp401Performance OBJECT IDENTIFIER 		::=	{ ommp401 4 }
	ommp401Diagnostics OBJECT IDENTIFIER 		::=	{ ommp401 5 }

	ommp401AlarmQuery OBJECT IDENTIFIER			::=	{ ommp401Alarm 1 }
	ommp401AlarmNotification OBJECT IDENTIFIER		::=	{ ommp401Alarm 2 }

--*****************************************************************************
--				CARD GENERAL DETAILS
--*****************************************************************************

	ommp401CardGeneralDetailsTable OBJECT-TYPE
		SYNTAX  SEQUENCE OF Ommp401CardGeneralDetailsEntry 
		MAX-ACCESS  not-accessible
		STATUS  current
		DESCRIPTION
                     "Contains card general details' queries for the OMMP401 card"
		::= { ommp401CardGeneralDetails 1 }

	ommp401CardGeneralDetailsEntry  OBJECT-TYPE
		SYNTAX  Ommp401CardGeneralDetailsEntry 
		MAX-ACCESS  not-accessible
		STATUS  current
		DESCRIPTION 
              	""
		INDEX   { node, rack, subRack, slot, ommp401InterfaceNumber }
		::= { ommp401CardGeneralDetailsTable 1 }

	Ommp401CardGeneralDetailsEntry  ::= 
		SEQUENCE {
				ommp401InterfaceNumber					INTEGER,
				ommp401EepromCardId					        INTEGER,
				ommp401EepromCardName					DisplayString,
				ommp401EepromPartCode					DisplayString,
				ommp401EepromCardSerialNumber				DisplayString,
				ommp401EepromHardwareExternalReleaseVersion		        DisplayString,
				ommp401SoftwareExternalReleaseVersion		        DisplayString,
				ommp401EepromHardwareInternalReleaseVersion		        DisplayString,
				ommp401SoftwareInternalReleaseVersion		        DisplayString,
				ommp401EepromCardUidNumber			                DisplayString,
				ommp401EepromCardEui48Number				        DisplayString,
				ommp401EepromCardEui64Number				        DisplayString,
				ommp401CardInstallationDate				        DisplayString,
				ommp401CardCommissionDate				        DisplayString,
				ommp401CardRunningTime					DisplayString,
				ommp401CardRestartCount					INTEGER,
				ommp401Cfp2ReadyForOperation				        INTEGER,
				ommp401Cfp2VendorName					        DisplayString,
				ommp401Cfp2VendorIeeeId					INTEGER,
				ommp401Cfp2PartNumber					        DisplayString,
				ommp401Cfp2SerialNumber					DisplayString,
				ommp401Cfp2ManufacturingDate				        DisplayString,
				ommp401Cfp2HardwareVersionNumber			 DisplayString,
				ommp401Cfp2FirmwareVersionNumber			 DisplayString,
				ommp401Cfp2MediaType					 DisplayString,
				ommp401NumberOfNetworkLanesInCfp2			 INTEGER,
				ommp401NumberOfHostLanesInCfp2				 INTEGER,
				ommp401Cfp2ModuleId					 DisplayString,
				ommp401Cfp2PowerClass					 INTEGER,
				ommp401Cfp2ProductCodeValue				 INTEGER,
				ommp401Cfp2WavelengthTunabilitySupported			INTEGER,
				ommp401TunableCfp2LaserFirstFrequency			        DisplayString,
				ommp401TunableCfp2LaserLastFrequency			        DisplayString,
				ommp401Cfp2ConnectorType					DisplayString,
				ommp401Cfp2SignalEncodingTypeSupported			DisplayString,
				ommp401Cfp2MaximumBitrateSupported			        DisplayString,
				ommp401Cfp2MaximumCaseTemperatureSupported		        INTEGER,
				ommp401Cfp2MinimumCaseTemperatureSupported		        DisplayString,
				ommp401Cfp2ActiveWavelengthControlSupported			INTEGER,
				ommp401Cfp2TransmitterIsCooledOrUncooled			INTEGER,
				ommp401Qsfp28EepromPage						INTEGER,
				ommp401Qsfp28VendorName						DisplayString,
				ommp401Qsfp28VendorIeeeId					DisplayString,
				ommp401Qsfp28PartNumber						DisplayString,
				ommp401Qsfp28SerialNumber					DisplayString,
				ommp401Qsfp28RevisionNumber					DisplayString,
				ommp401Qsfp28ManufacturingDate					DisplayString,
				ommp401FixedQsfp28LaserWavelength				DisplayString,
				ommp401Qsfp28ConnectorType					DisplayString,
				ommp401Qsfp28LinkLength						DisplayString,
				ommp401Qsfp28SignalEncodingTypeSupported			INTEGER,
				ommp401Qsfp28TransceiverCodesSupported				DisplayString,
				ommp401Qsfp28NominalBitrateSupported				DisplayString,
				ommp401Cfp2ModuleInfo						INTEGER,
				ommp401CardGeneralDetailsTableRowStatus			RowStatus
			 }
	

	ommp401InterfaceNumber OBJECT-TYPE
		SYNTAX  INTEGER
		MAX-ACCESS  not-accessible
		STATUS  current
		DESCRIPTION
			"Interface number represents the port number.
			InterfaceNumber to port mapping is as follows:
			1 - CLIENT-1,
			2 - CLIENT-2,
			3 - CLIENT-3,
			4 - CLIENT-4,
			5 - LINE-1
			-----------------------------
			For properties which do not apply on any interface,
			the interface number must be passed as 0
			-----------------------------"
		::= { ommp401CardGeneralDetailsEntry 1 }
	
	ommp401EepromCardId OBJECT-TYPE		 
		SYNTAX  INTEGER
		MAX-ACCESS  read-only
		STATUS current
		DESCRIPTION
			"Tells the card ID of the OMMP401 card, present in the EEPROM
			-----------------------------
			ommp401InterfaceNumber: 0
			-----------------------------"
		::= { ommp401CardGeneralDetailsEntry 2 }

	ommp401EepromCardName OBJECT-TYPE		 
		SYNTAX  DisplayString
		MAX-ACCESS  read-only
		STATUS current
		DESCRIPTION
			"Tells the card name of the OMMP401 card, present in the EEPROM
			-----------------------------
			ommp401InterfaceNumber: 0
			-----------------------------"
		::= { ommp401CardGeneralDetailsEntry 3 }

	ommp401EepromPartCode OBJECT-TYPE		 
		SYNTAX  DisplayString
		MAX-ACCESS  read-only
		STATUS current
		DESCRIPTION
			"Tells the part code of the OMMP401 card, present in the EEPROM
			-----------------------------
			ommp401InterfaceNumber: 0
			-----------------------------"
		::= { ommp401CardGeneralDetailsEntry 4 }

	ommp401EepromCardSerialNumber OBJECT-TYPE		 
		SYNTAX  DisplayString
		MAX-ACCESS  read-write
		STATUS current
		DESCRIPTION
			"This property get / set the information about 
			OMMP401 Card's Serial Number.
			-----------------------------
			ommp401InterfaceNumber: 0
			-----------------------------
			Values:
			eg: 123456
			-----------------------------"
		::= { ommp401CardGeneralDetailsEntry 5 }

	ommp401EepromHardwareExternalReleaseVersion OBJECT-TYPE		 
		SYNTAX  DisplayString
		MAX-ACCESS  read-only
		STATUS current
		DESCRIPTION
			"Gets the Card's Hardware External Release Version. 
			This detail will be displayed to the customer.
			This version will increment only if there are significant
			architectural changes in the product
			-----------------------------
			ommp401InterfaceNumber: 0
			-----------------------------
			Value:
			eg: 0.1
			-----------------------------"
		::= { ommp401CardGeneralDetailsEntry 6 }

	ommp401SoftwareExternalReleaseVersion OBJECT-TYPE		 
		SYNTAX  DisplayString
		MAX-ACCESS  read-only
		STATUS current
		DESCRIPTION
			"Gets the Card's Software External Release Version. 
			This detail will be displayed to the customer.
			This version will increment only if there are
			significant architectural changes in the product
			-----------------------------
			ommp401InterfaceNumber: 0
			-----------------------------
			Value:
			eg: 0.1
			-----------------------------"
		::= { ommp401CardGeneralDetailsEntry 7 }

	ommp401EepromHardwareInternalReleaseVersion OBJECT-TYPE		 
		SYNTAX  DisplayString
		MAX-ACCESS  read-only
		STATUS current
		DESCRIPTION
			"Gets the Card's Hardware Internal Release Version.
			This detail is used for development purposes only.
			It differs from the external hardware version.
			-----------------------------
			ommp401InterfaceNumber: 0
			-----------------------------
			Value:
			eg: 4.1
			-----------------------------"
		::= { ommp401CardGeneralDetailsEntry 8 }

	ommp401SoftwareInternalReleaseVersion OBJECT-TYPE		 
		SYNTAX  DisplayString
		MAX-ACCESS  read-only
		STATUS current
		DESCRIPTION
			"Gets the Card's Software Internal Release Version.
			This detail is used for development purposes only.
			It differs from the external software version.
		      	-----------------------------
			ommp401InterfaceNumber: 0
			-----------------------------
			Value:
			eg: 5.1
			-----------------------------"
		::= { ommp401CardGeneralDetailsEntry 9 }

	ommp401EepromCardUidNumber OBJECT-TYPE		 
		SYNTAX  DisplayString
		MAX-ACCESS  read-only
		STATUS current
		DESCRIPTION
			"Tells the Card Unique IDentifier. It is a 4 byte
			address used to uniquely identify a card.
			----------------------------
			ommp401InterfaceNumber: 0
			------------------------------
			Value:
		      	eg: 12345678
			-----------------------------"
		::= { ommp401CardGeneralDetailsEntry 10 }

	ommp401EepromCardEui48Number OBJECT-TYPE		 
		SYNTAX  DisplayString
		MAX-ACCESS  read-only
		STATUS current
		DESCRIPTION
			"Tells the Card EUI-48 Number. It is a 6 byte address
			used to uniquely identify a card.
			-----------------------------
			ommp401InterfaceNumber: 0
			-----------------------------
			Value:
		      	eg: 0004A3123456
			-----------------------------"
		::= { ommp401CardGeneralDetailsEntry 11 }

	ommp401EepromCardEui64Number OBJECT-TYPE		 
		SYNTAX  DisplayString
		MAX-ACCESS  read-only
		STATUS current
		DESCRIPTION
			"Tells the Card EUI-64 Number. It is a 8 byte address
			used to uniquely identify a card.
			-----------------------------
			ommp401InterfaceNumber: 0
			-----------------------------
			Value:
		      	eg: 0004A31234567890
			-----------------------------"
		::= { ommp401CardGeneralDetailsEntry 12 }
		
	ommp401CardInstallationDate OBJECT-TYPE		 
		SYNTAX  DisplayString
		MAX-ACCESS  read-write
		STATUS current
		DESCRIPTION
			"Gets the card's installation date in
			dd/mm/yyyy format
			-----------------------------
			ommp401InterfaceNumber: 0
			-----------------------------
			Value:
		      	eg: 12/02/2023
			-----------------------------"
		::= { ommp401CardGeneralDetailsEntry 13 }

	ommp401CardCommissionDate OBJECT-TYPE		 
		SYNTAX  DisplayString
		MAX-ACCESS  read-write
		STATUS current
		DESCRIPTION
			"Gets the card's commission date in
			dd/mm/yyyy format
			-----------------------------
			ommp401InterfaceNumber: 0
			-----------------------------
			Value:
		      	eg: 12/02/2023
			-----------------------------"
		::= { ommp401CardGeneralDetailsEntry 14 }

	ommp401CardRunningTime OBJECT-TYPE		 
		SYNTAX  DisplayString
		MAX-ACCESS  read-only
		STATUS current
		DESCRIPTION
			"Get the duration of time for which the card is
			operational/running
			-----------------------------
			ommp401InterfaceNumber: 0
			-----------------------------
			Values:
		      	eg: 4d:3h:2m:1s
			-----------------------------"
		::= { ommp401CardGeneralDetailsEntry 15 }

	ommp401CardRestartCount OBJECT-TYPE		 
		SYNTAX  INTEGER
		MAX-ACCESS  read-only
		STATUS current
		DESCRIPTION
			"Get the number of times the card has been soft reset.
			This value will get reset to 0 on factory reset.
			-----------------------------
			ommp401InterfaceNumber: 0
			-----------------------------
			Values:
		      	eg: 10
			-----------------------------"
		::= { ommp401CardGeneralDetailsEntry 16 }

	ommp401Cfp2ReadyForOperation OBJECT-TYPE		 
		SYNTAX  INTEGER
		MAX-ACCESS  read-only
		STATUS current
		DESCRIPTION
			"Module not ready indicates that the CFP2
			has detected a condition that tells
			transmit or receive data is invalid.
			It shall consist of logical OR of the
			following signals:
			> Transmit Signal Conditioner Loss of Lock
			> Transmitter Laser Fault
			> Receiver Signal Conditioner Loss of Lock
			(Ref: INF-8077 2.4.1)
			-----------------------------
			ommp401InterfaceNumber:
			5 - LINE-1
			-----------------------------
			Values:		
			0 - CFP2 is ready for operation 
			1 - CFP2 is not ready for operation
			-----------------------------"
		::= { ommp401CardGeneralDetailsEntry 17 }

	ommp401Cfp2VendorName OBJECT-TYPE		 
		SYNTAX  DisplayString
		MAX-ACCESS  read-only
		STATUS current
		DESCRIPTION
			"This property provides Vendor Name for given CFP2. 
			The vendor name shall be the full name of the 
			corporation, a commonly accepted abbreviation of 
			the name of the corporation, the SCSI company code
			for the corporation, or the stock exchange code for
			the corporation.
			-----------------------------
			ommp401InterfaceNumber:
			5 - LINE-1
			-----------------------------
			Values:			
			eg: Lumentum
			-----------------------------"
		::= { ommp401CardGeneralDetailsEntry 18 }

	ommp401Cfp2VendorIeeeId OBJECT-TYPE		 
		SYNTAX  INTEGER
		MAX-ACCESS  read-only
		STATUS current
		DESCRIPTION
			"This property defines the IEEE company Identifier for
			the vendor of CFP2. A value of all zero in the 3-byte
			field indicates that the Vendor OUI is unspecified.
			-----------------------------
			ommp401InterfaceNumber:
			5 - LINE-1
			-----------------------------
			Values:			
			eg: 010
			-----------------------------"
		::= { ommp401CardGeneralDetailsEntry 19 }

	ommp401Cfp2PartNumber OBJECT-TYPE		 
		SYNTAX  DisplayString
		MAX-ACCESS  read-only
		STATUS current
		DESCRIPTION
			"This property defines the vendor part number or
			product name of the CFP2. A value of all zero
			indicates that the vendor Part Number is unspecified.
			-----------------------------
			ommp401InterfaceNumber:
			5 - LINE-1
			-----------------------------
			Values:			
			eg: FTRX-1811-2D2
			-----------------------------"
		::= { ommp401CardGeneralDetailsEntry 20 }

	ommp401Cfp2SerialNumber OBJECT-TYPE		 
		SYNTAX  DisplayString
		MAX-ACCESS  read-only
		STATUS current
		DESCRIPTION
			"This property provides vendor serial number defining
			the vendor’s serial number for the CFP2. A value of all
			zero in the 16-byte field indicates that the vendor
			serial number is unspecified.
			-----------------------------
			ommp401InterfaceNumber:
			5 - LINE-1
			-----------------------------
			Values:			
			eg: KBG02CU
			-----------------------------"
		::= { ommp401CardGeneralDetailsEntry 21 }

	ommp401Cfp2ManufacturingDate OBJECT-TYPE		 
		SYNTAX  DisplayString
		MAX-ACCESS  read-only
		STATUS current
		DESCRIPTION
			"This property defines the manufacturing date for 
			CFP2. A value of 8-byte field in ASCII which represents
			year, month and date of each two bytes. 
			Extra two bytes may be blank
			-----------------------------
			ommp401InterfaceNumber:
			5 - LINE-1
			-----------------------------
			Values:			
			eg: 07292020
			-----------------------------"
		::= { ommp401CardGeneralDetailsEntry 22 }

	ommp401Cfp2HardwareVersionNumber OBJECT-TYPE		 
		SYNTAX  DisplayString
		MAX-ACCESS  read-only
		STATUS current
		DESCRIPTION
			"This property defines the hardware version number for 
			CFP2. A value of 2-byte field which represents
			hardware version number in x.y format. 
			-----------------------------
			ommp401InterfaceNumber:
			5 - LINE-1
			-----------------------------
			Values:			
			eg: 1.1
			-----------------------------"
		::= { ommp401CardGeneralDetailsEntry 23 }

	ommp401Cfp2FirmwareVersionNumber OBJECT-TYPE		 
		SYNTAX  DisplayString
		MAX-ACCESS  read-only
		STATUS current
		DESCRIPTION
			"This property defines the Firmware version number for 
			CFP2. A value of 2-byte field which represents
			firmware version number in x.y format. 
			-----------------------------
			ommp401InterfaceNumber:
			5 - LINE-1
			-----------------------------
			Values:			
			eg: 1.1
			-----------------------------"
		::= { ommp401CardGeneralDetailsEntry 24 }

	ommp401Cfp2MediaType OBJECT-TYPE		 
		SYNTAX  DisplayString
		MAX-ACCESS  read-only
		STATUS current
		DESCRIPTION
			"This property defines the Media type for 
			CFP2. A value of 2-Bit field which represents
			media type. 
			-----------------------------
			ommp401InterfaceNumber:
			5 - LINE-1
			-----------------------------
			Values:			
			eg: SMF
			-----------------------------"
		::= { ommp401CardGeneralDetailsEntry 25 }

	ommp401NumberOfNetworkLanesInCfp2 OBJECT-TYPE		 
		SYNTAX  INTEGER
		MAX-ACCESS  read-only
		STATUS current
		DESCRIPTION
			"This property defines the Number of Network Lanes for 
			CFP2. A value of 4-Bits field which represents
			Number of Network Lanes. 
			-----------------------------
			ommp401InterfaceNumber:
			5 - LINE-1
			-----------------------------
			Values:			
			eg: 1
			-----------------------------"
		::= { ommp401CardGeneralDetailsEntry 26 }

	ommp401NumberOfHostLanesInCfp2 OBJECT-TYPE		 
		SYNTAX  INTEGER
		MAX-ACCESS  read-only
		STATUS current
		DESCRIPTION
			"This property defines the Number of Network Host for 
			CFP2. A value of 4-Bits field which represents
			Number of Host Lanes.
			-----------------------------
			ommp401InterfaceNumber:
			5 - LINE-1
			-----------------------------
			Values:			
			eg: 1
			-----------------------------"
		::= { ommp401CardGeneralDetailsEntry 27 }
		
	ommp401Cfp2ModuleId OBJECT-TYPE		 
		SYNTAX  DisplayString
		MAX-ACCESS  read-only
		STATUS current
		DESCRIPTION
			"This property defines the Module ID for 
			CFP2. A value of 1-Byte field which represents
			Module identifier.
			-----------------------------
			ommp401InterfaceNumber:
			5 - LINE-1
			-----------------------------
			Values:			
			eg: CFP2
			-----------------------------"
		::= { ommp401CardGeneralDetailsEntry 28 }

	ommp401Cfp2PowerClass OBJECT-TYPE		 
		SYNTAX  INTEGER
		MAX-ACCESS  read-only
		STATUS current
		DESCRIPTION
			"This property defines the Power Class for 
			CFP2. A value of 2-Bits field which represents
			Power class.
			-----------------------------
			ommp401InterfaceNumber:
			5 - LINE-1
			-----------------------------
			Values:			
			0 - <= 9Watts
			1 - <= 12Watts
			2 - <= 15Watts
			3 - > 15Watts
			-----------------------------"
		::= { ommp401CardGeneralDetailsEntry 29 }

	ommp401Cfp2ProductCodeValue OBJECT-TYPE		 
		SYNTAX  INTEGER
		MAX-ACCESS  read-only
		STATUS current
		DESCRIPTION
			"This property defines the Product code value for 
			CFP2. A value of 7-Bits field which represents
			Product code value.
			-----------------------------
			ommp401InterfaceNumber:
			5 - LINE-1
			-----------------------------
			Values:			
			eg: 50h
			-----------------------------"
		::= { ommp401CardGeneralDetailsEntry 30 }
		
	ommp401Cfp2WavelengthTunabilitySupported OBJECT-TYPE		 
		SYNTAX  INTEGER
		MAX-ACCESS  read-only
		STATUS current
		DESCRIPTION
			"This property provides information whether the CFP2
			supports wavelength tunability or not.
			-----------------------------
			ommp401InterfaceNumber:
			5 - LINE-1
			-----------------------------
			Values:			
			1 - CFP2 supports wavelength tunability
			0 - CFP2 does not supports wavelength tunability
			-----------------------------"
		::= { ommp401CardGeneralDetailsEntry 31 }

	ommp401TunableCfp2LaserFirstFrequency OBJECT-TYPE		 
		SYNTAX  DisplayString
		MAX-ACCESS  read-only
		STATUS current
		DESCRIPTION
			"This property defines the first LASER frequency of CFP2.
			The two byte value is specified in units of THz.
			-----------------------------
			ommp401InterfaceNumber:
			5 - LINE-1
			-----------------------------
			Values:			
			eg: 191
			-----------------------------"
		::= { ommp401CardGeneralDetailsEntry 32 }

	ommp401TunableCfp2LaserLastFrequency OBJECT-TYPE		 
		SYNTAX  DisplayString
		MAX-ACCESS  read-only
		STATUS current
		DESCRIPTION
			"This property defines the last laser frequency of CFP2.
		 	 The two byte value is specified in units of THz.
			-----------------------------
			ommp401InterfaceNumber:
			5 - LINE-1
			-----------------------------
			Values:			
			eg: 196
			-----------------------------"
		::= { ommp401CardGeneralDetailsEntry 33 }

	ommp401Cfp2ConnectorType OBJECT-TYPE		 
		SYNTAX  DisplayString
		MAX-ACCESS  read-only
		STATUS current
		DESCRIPTION
			"This property provides information of the CFP2
			connector, value indicates the external connector
			provided on the CFP2.
			-----------------------------
			ommp401InterfaceNumber:
			5 - LINE-1
			-----------------------------
			Values:
			eg: LC
			-----------------------------"
		::= { ommp401CardGeneralDetailsEntry 34 }

	ommp401Cfp2SignalEncodingTypeSupported OBJECT-TYPE		 
		SYNTAX  DisplayString
		MAX-ACCESS  read-only
		STATUS current
		DESCRIPTION
			"This property indicates the serial encoding mechanisms
			that are supported by the CFP2.
			-----------------------------
			ommp401InterfaceNumber:
			5 - LINE-1
			-----------------------------
			Values:
			eg: 16QAM
			-----------------------------"
		::= { ommp401CardGeneralDetailsEntry 35 }

	ommp401Cfp2MaximumBitrateSupported OBJECT-TYPE		 
		SYNTAX  DisplayString
		MAX-ACCESS  read-only
		STATUS current
		DESCRIPTION
			"This property provides maximum bit rate(Gbps) value
			supported by CFP2
			-----------------------------
			ommp401InterfaceNumber:
			5 - LINE-1
			-----------------------------
			Values: 9.5
			-----------------------------"
		::= { ommp401CardGeneralDetailsEntry 36 }

	ommp401Cfp2MaximumCaseTemperatureSupported OBJECT-TYPE		 
		SYNTAX  INTEGER
		MAX-ACCESS  read-only
		STATUS current
		DESCRIPTION
			"This property provides the maximum case temperature
			(degree celcius) supported by CFP2.
			-----------------------------
			ommp401InterfaceNumber:
			5 - LINE-1
			-----------------------------
			Values:
			eg: 70
			-----------------------------"
		::= { ommp401CardGeneralDetailsEntry 37 }

	ommp401Cfp2MinimumCaseTemperatureSupported OBJECT-TYPE		 
		SYNTAX  DisplayString
		MAX-ACCESS  read-only
		STATUS current
		DESCRIPTION
			"This property provides the manimum case temperature
			(degree celcius) supported by CFP2.
			-----------------------------
			ommp401InterfaceNumber:
			5 - LINE-1
			-----------------------------
			Values:
			eg: 70
			-----------------------------"
		::= { ommp401CardGeneralDetailsEntry 38 }

	ommp401Cfp2ActiveWavelengthControlSupported OBJECT-TYPE		 
		SYNTAX  INTEGER
		MAX-ACCESS  read-only
		STATUS current
		DESCRIPTION
			"This property provides whether the CFP2 wavelength 
			controlling state is active or not
			-----------------------------
			ommp401InterfaceNumber:
			5 - LINE-1
			-----------------------------
			Values:
			1 - Supported
			0 - Not supported
			-----------------------------"
		::= { ommp401CardGeneralDetailsEntry 39 }

	ommp401Cfp2TransmitterIsCooledOrUncooled OBJECT-TYPE		 
		SYNTAX  INTEGER
		MAX-ACCESS  read-only
		STATUS current
		DESCRIPTION
			"This property provide information on which type of
			diode used in transmitter of the CFP2
			-----------------------------
			ommp401InterfaceNumber:
			5 - LINE-1
			-----------------------------
			Values:
			1 - Cooling circuit supported for CFP2 transmitter. 
			0 - Cooling circuit not supported for CFP2 transmitter.
			-----------------------------"
		::= { ommp401CardGeneralDetailsEntry 40 }

	ommp401Qsfp28EepromPage OBJECT-TYPE		 
		SYNTAX  INTEGER
		MAX-ACCESS  read-write
		STATUS current
		DESCRIPTION
			"This property sets/gets the QSFP28 EEPROM page, 
			the value represents the QSFP28 EEPROM page number.
			-----------------------------
			ommp401InterfaceNumber:
			1 to 4 - CLIENT-1 to CLIENT-4
			-----------------------------
			Values:			
			eg: 1(EEPROM Page number)
			-----------------------------"
		::= { ommp401CardGeneralDetailsEntry 41 }

	ommp401Qsfp28VendorName OBJECT-TYPE		 
		SYNTAX  DisplayString
		MAX-ACCESS  read-only
		STATUS current
		DESCRIPTION
			"This property provides Vendor Name for given QSFP28. 
			The vendor name shall be the full name of the 
			corporation, a commonly accepted abbreviation of 
			the name of the corporation, the SCSI company code
			for the corporation, or the stock exchange code for
			the corporation.
			-----------------------------
			ommp401InterfaceNumber:
			1 to 4 - CLIENT-1 to CLIENT-4
			-----------------------------
			Values:			
			eg: Lumentum
			-----------------------------"
		::= { ommp401CardGeneralDetailsEntry 42 }

	ommp401Qsfp28VendorIeeeId OBJECT-TYPE		 
		SYNTAX  DisplayString
		MAX-ACCESS  read-only
		STATUS current
		DESCRIPTION
			"This property defines the IEEE company Identifier for
			the vendor of QSFP28. A value of all zero in the 3-byte
			field indicates that the Vendor OUI is unspecified.
			-----------------------------
			ommp401InterfaceNumber:
			1 to 4 - CLIENT-1 to CLIENT-4
			-----------------------------
			Values:			
			eg: 010
			-----------------------------"
		::= { ommp401CardGeneralDetailsEntry 43 }

	ommp401Qsfp28PartNumber OBJECT-TYPE		 
		SYNTAX  DisplayString
		MAX-ACCESS  read-only
		STATUS current
		DESCRIPTION
			"This property defines the vendor part number or
			product name of the QSFP28. A value of all zero
			indicates that the vendor Part Number is unspecified.
			-----------------------------
			ommp401InterfaceNumber:
			1 to 4 - CLIENT-1 to CLIENT-4
			-----------------------------
			Values:			
			eg: WXTR15101000427
			-----------------------------"
		::= { ommp401CardGeneralDetailsEntry 44 }

	ommp401Qsfp28SerialNumber OBJECT-TYPE		 
		SYNTAX  DisplayString
		MAX-ACCESS  read-only
		STATUS current
		DESCRIPTION
			"This property provides vendor serial number defining
			the vendor’s serial number for the QSFP28. A value of all
			zero in the 16-byte field indicates that the vendor
			serial number is unspecified.
			-----------------------------
			ommp401InterfaceNumber:
			1 to 4 - CLIENT-1 to CLIENT-4
			-----------------------------
			Values:			
			eg: WXTRRPGEAS1
			-----------------------------"
		::= { ommp401CardGeneralDetailsEntry 45 }

	ommp401Qsfp28RevisionNumber OBJECT-TYPE		 
		SYNTAX  DisplayString
		MAX-ACCESS  read-only
		STATUS current
		DESCRIPTION
			"The vendor revision number defining the vendor’s
			product revision number. A value of all zero indicates
			that the vendor revision number is unspecified
			-----------------------------
			ommp401InterfaceNumber:
			1 to 4 - CLIENT-1 to CLIENT-4
			-----------------------------
			Values:			
			eg: A0
			-----------------------------"
		::= { ommp401CardGeneralDetailsEntry 46 }

	ommp401Qsfp28ManufacturingDate OBJECT-TYPE		 
		SYNTAX  DisplayString
		MAX-ACCESS  read-only
		STATUS current
		DESCRIPTION
			"This property defines the manufacturing date for 
			QSFP28. A value of 8-byte field in ASCII which represents
			year, month and date of each two bytes. 
			Extra two bytes may be blank
			-----------------------------
			ommp401InterfaceNumber:
			1 to 4 - CLIENT-1 to CLIENT-4
			-----------------------------
			Values:			
			eg: 160223
			-----------------------------"
		::= { ommp401CardGeneralDetailsEntry 47 }

	ommp401FixedQsfp28LaserWavelength OBJECT-TYPE		 
		SYNTAX  DisplayString
		MAX-ACCESS  read-only
		STATUS current
		DESCRIPTION
			"This property provides transmitter LASER wavelength(nm)
			of the QSFP28
			-----------------------------
			ommp401InterfaceNumber:
			1 to 4 - CLIENT-1 to CLIENT-4
			-----------------------------
			Values:			
			eg: 1310.0
			-----------------------------"
		::= { ommp401CardGeneralDetailsEntry 48 }

	ommp401Qsfp28ConnectorType OBJECT-TYPE		 
		SYNTAX  DisplayString
		MAX-ACCESS  read-only
		STATUS current
		DESCRIPTION
			"This property provides information of the QSFP28
			connector, value indicates the external connector
			provided on the QSFP28.
			-----------------------------
			ommp401InterfaceNumber:
			1 to 4 - CLIENT-1 to CLIENT-4
			-----------------------------
			Values:
			eg: LC
			-----------------------------"
		::= { ommp401CardGeneralDetailsEntry 49 }

	ommp401Qsfp28LinkLength OBJECT-TYPE		 
		SYNTAX  DisplayString
		MAX-ACCESS  read-only
		STATUS current
		DESCRIPTION
			"This property provides link length suported by the QSFP28
			-----------------------------
			ommp401InterfaceNumber:
			1 to 4 - CLIENT-1 to CLIENT-4
			-----------------------------
			Values:
			eg: 80.00
			-----------------------------"
		::= { ommp401CardGeneralDetailsEntry 50 }

	ommp401Qsfp28SignalEncodingTypeSupported OBJECT-TYPE		 
		SYNTAX  INTEGER
		MAX-ACCESS  read-only
		STATUS current
		DESCRIPTION
			"This property indicates the serial encoding mechanisms
			that are supported by the QSFP28.
			-----------------------------
			ommp401InterfaceNumber:
			1 to 4 - CLIENT-1 to CLIENT-4
			-----------------------------
			Values:
			1 - RZ
			2 - 8B10B
			3 - SONET Scrambled
			4 - NRZ
			5 - 64B/66B
			-----------------------------"
		::= { ommp401CardGeneralDetailsEntry 51 }

	ommp401Qsfp28TransceiverCodesSupported OBJECT-TYPE		 
		SYNTAX  DisplayString
		MAX-ACCESS  read-only
		STATUS current
		DESCRIPTION
			"The identifier value specifies which transceiver
			codes are supported by the QSFP28
			-----------------------------
			ommp401InterfaceNumber:
			1 to 4 - CLIENT-1 to CLIENT-4
			-----------------------------
			Values:
			0   - 1000BASE-SX
			1   - 1000BASE-LX
			2   - 1000BASE-CX
			3   - 1000BASE-T
			4-7 - Reserved
			-----------------------------"
		::= { ommp401CardGeneralDetailsEntry 52 }

	ommp401Qsfp28NominalBitrateSupported OBJECT-TYPE		 
		SYNTAX  DisplayString
		MAX-ACCESS  read-only
		STATUS current
		DESCRIPTION
			"This property provides Nominal bit rate value(Gbps)
			supported by the QSFP28
			-----------------------------
			ommp401InterfaceNumber:
			1 to 4 - CLIENT-1 to CLIENT-4
			-----------------------------
			Values: 2.0
			-----------------------------"
		::= { ommp401CardGeneralDetailsEntry 53 }
		
	ommp401Cfp2ModuleInfo OBJECT-TYPE		 
		SYNTAX  INTEGER
		MAX-ACCESS  read-only
		STATUS current
		DESCRIPTION
			"This property defines the Module Information for 
			CFP2. A value of 1-Byte field which represents
			Module identifier.
			-----------------------------
			ommp401InterfaceNumber:
			5 - LINE-1
			-----------------------------
			Values:			
			eg: 1-> 100G-CFP2
			    2-> 200G-CFP2
			    3-> 400G-CFP2
			    4-> UNKNOWN-CFP2
			-----------------------------"
		::= { ommp401CardGeneralDetailsEntry 54 }

	ommp401CardGeneralDetailsTableRowStatus OBJECT-TYPE
              SYNTAX      RowStatus
              MAX-ACCESS  read-write
              STATUS      current
              DESCRIPTION
			"*****************************
			This is MIB realted property,
			NOT to be considered as a card property
			*****************************"
              ::= { ommp401CardGeneralDetailsEntry 55 }

--*****************************************************************************
--				   CONFIGURATION
--*****************************************************************************

	ommp401ConfigurationTable OBJECT-TYPE
		SYNTAX  SEQUENCE OF Ommp401ConfigurationEntry 
		MAX-ACCESS  not-accessible
		STATUS  current
		DESCRIPTION
		      "Contains configuration queries of the OMMP401 card"
		::= { ommp401Configuration 1 }

	ommp401ConfigurationEntry  OBJECT-TYPE
              SYNTAX  Ommp401ConfigurationEntry 
              MAX-ACCESS  not-accessible
              STATUS  current
              DESCRIPTION 
              	""
		INDEX   { node, rack, subRack, slot, ommp401InterfaceNumber }
		::= { ommp401ConfigurationTable 1 }
	
	Ommp401ConfigurationEntry  ::= 
		SEQUENCE {
				ommp401CardSoftwareUpgrade					DisplayString,
				ommp401CardSignalMonitorState				INTEGER,
				ommp401CardOpticalMonitorState				INTEGER,
				ommp401CardSoftReset						INTEGER,
				ommp401CardFactoryReset					INTEGER,
				ommp401SyncSystemTimeWithNtpServer				DisplayString,
				ommp401SyncRtcWithNtpServer						DisplayString,
				ommp401SyncRtcWithSystemTime						DisplayString,
				ommp401UpdateGivenTimeIntoSystem					DisplayString,
				ommp401UpdateGivenTimeIntoRtc					DisplayString,
				ommp401SystemTimeAndRtcTime						DisplayString,
				ommp401TrafficConfiguration					INTEGER,
				ommp401LoopbackState						INTEGER,
				ommp401PortSignalMonitorState				INTEGER,
				ommp401PortOpticalMonitorState				INTEGER,
				ommp401ClearSignalPerformance				INTEGER,
				ommp401AlsState						INTEGER,
				ommp401AlsPulseRepetitionTime				INTEGER,
				ommp401OtuFecConfiguration					INTEGER,
				ommp401OtuSignalFailThreshold				INTEGER,
				ommp401OtuSignalDegradeThreshold				INTEGER,
				ommp401OtuSapiTransmitTraceMessage				DisplayString,
				ommp401OtuDapiTransmitTraceMessage				DisplayString,
				ommp401OtuOperatorSpecificTransmitTraceMessage		DisplayString,
				ommp401OtuSapiExpectedTraceMessage				DisplayString,
				ommp401OtuDapiExpectedTraceMessage				DisplayString,
				ommp401OtuOperatorSpecificExpectedTraceMessage		DisplayString,
				ommp401OduSignalFailThreshold				INTEGER,
				ommp401OduSignalDegradeThreshold				INTEGER,
				ommp401OduSapiTransmitTraceMessage				DisplayString,
				ommp401OduDapiTransmitTraceMessage				DisplayString,
				ommp401OduOperatorSpecificTransmitTraceMessage		DisplayString,
				ommp401OduSapiExpectedTraceMessage				DisplayString,
				ommp401OduDapiExpectedTraceMessage				DisplayString,
				ommp401OduOperatorSpecificExpectedTraceMessage		DisplayString,
				ommp401TunableCfp2LaserWavelength				INTEGER,
				ommp401Cfp2LaserState						INTEGER,
				ommp401Cfp2Reset						INTEGER,
				ommp401Cfp2PowerDownMode					INTEGER,
				ommp401Cfp2HighTemperatureAlarmThreshold			DisplayString,
				ommp401Cfp2LowTemperatureAlarmThreshold			DisplayString,
				ommp401Cfp2HighTemperatureWarningThreshold			DisplayString,
				ommp401Cfp2LowTemperatureWarningThreshold			DisplayString,
				ommp401Cfp2InputHighPowerAlarmThreshold			DisplayString,
				ommp401Cfp2InputLowPowerAlarmThreshold			DisplayString,
				ommp401Cfp2InputHighPowerWarningThreshold			DisplayString,
				ommp401Cfp2InputLowPowerWarningThreshold			DisplayString,
				ommp401Cfp2OutputHighPowerAlarmThreshold			DisplayString,
				ommp401Cfp2OutputLowPowerAlarmThreshold			DisplayString,
				ommp401Cfp2OutputHighPowerWarningThreshold			DisplayString,
				ommp401Cfp2OutputLowPowerWarningThreshold			DisplayString,
				ommp401Cfp2HighSupplyVoltageAlarmThreshold			DisplayString,
				ommp401Cfp2LowSupplyVoltageAlarmThreshold			DisplayString,
				ommp401Cfp2HighSupplyVoltageWarningThreshold			DisplayString,
				ommp401Cfp2LowSupplyVoltageWarningThreshold			DisplayString,
				ommp401Qsfp28LaserState						INTEGER,
				ommp401Qsfp28Reset						INTEGER,
				ommp401Qsfp28PowerDownMode					INTEGER,
				ommp401Qsfp28HighTemperatureAlarmThreshold			DisplayString,
				ommp401Qsfp28LowTemperatureAlarmThreshold			DisplayString,
				ommp401Qsfp28HighTemperatureWarningThreshold			DisplayString,
				ommp401Qsfp28LowTemperatureWarningThreshold			DisplayString,
				ommp401Qsfp28HighBiasCurrentAlarmThreshold			DisplayString,
				ommp401Qsfp28LowBiasCurrentAlarmThreshold			DisplayString,
				ommp401Qsfp28HighBiasCurrentWarningThreshold			DisplayString,
				ommp401Qsfp28LowBiasCurrentWarningThreshold			DisplayString,
				ommp401Qsfp28InputHighPowerAlarmThreshold			DisplayString,
				ommp401Qsfp28InputLowPowerAlarmThreshold			DisplayString,
				ommp401Qsfp28InputHighPowerWarningThreshold			DisplayString,
				ommp401Qsfp28InputLowPowerWarningThreshold			DisplayString,
				ommp401Qsfp28OutputHighPowerAlarmThreshold			DisplayString,
				ommp401Qsfp28OutputLowPowerAlarmThreshold			DisplayString,
				ommp401Qsfp28OutputHighPowerWarningThreshold			DisplayString,
				ommp401Qsfp28OutputLowPowerWarningThreshold			DisplayString,
				ommp401Qsfp28HighSupplyVoltageAlarmThreshold			DisplayString,
				ommp401Qsfp28LowSupplyVoltageAlarmThreshold			DisplayString,
				ommp401Qsfp28HighSupplyVoltageWarningThreshold			DisplayString,
				ommp401Qsfp28LowSupplyVoltageWarningThreshold			DisplayString,
				ommp401Cfp2InputPowerFailureAlarmInhibit			INTEGER,
				ommp401Cfp2OutputPowerFailureAlarmInhibit			INTEGER,
				ommp401Cfp2HighTemperatureAlarmInhibit			INTEGER,
				ommp401Cfp2LowTemperatureAlarmInhibit				INTEGER,
				ommp401Cfp2HighTemperatureWarningInhibit			INTEGER,
				ommp401Cfp2LowTemperatureWarningInhibit			INTEGER,
				ommp401Cfp2InputHighPowerAlarmInhibit				INTEGER,
				ommp401Cfp2InputLowPowerAlarmInhibit				INTEGER,
				ommp401Cfp2InputHighPowerWarningInhibit			INTEGER,
				ommp401Cfp2InputLowPowerWarningInhibit			INTEGER,
				ommp401Cfp2OutputHighPowerAlarmInhibit			INTEGER,
				ommp401Cfp2OutputLowPowerAlarmInhibit				INTEGER,
				ommp401Cfp2OutputHighPowerWarningInhibit			INTEGER,
				ommp401Cfp2OutputLowPowerWarningInhibit			INTEGER,
				ommp401Cfp2HighSupplyVoltageAlarmInhibit			INTEGER,
				ommp401Cfp2LowSupplyVoltageAlarmInhibit			INTEGER,
				ommp401Cfp2HighSupplyVoltageWarningInhibit			INTEGER,
				ommp401Cfp2LowSupplyVoltageWarningInhibit			INTEGER,
				ommp401Cfp2PresenceAbsenceNotificationInhibit			INTEGER,
				ommp401Qsfp28InputPowerFailureAlarmInhibit			INTEGER,
				ommp401Qsfp28OutputPowerFailureAlarmInhibit			INTEGER,
				ommp401Qsfp28HighTemperatureAlarmInhibit			INTEGER,
				ommp401Qsfp28LowTemperatureAlarmInhibit				INTEGER,
				ommp401Qsfp28HighTemperatureWarningInhibit			INTEGER,
				ommp401Qsfp28LowTemperatureWarningInhibit			INTEGER,
				ommp401Qsfp28HighBiasCurrentAlarmInhibit			INTEGER,
				ommp401Qsfp28LowBiasCurrentAlarmInhibit				INTEGER,
				ommp401Qsfp28HighBiasCurrentWarningInhibit			INTEGER,
				ommp401Qsfp28LowBiasCurrentWarningInhibit			INTEGER,
				ommp401Qsfp28InputHighPowerAlarmInhibit				INTEGER,
				ommp401Qsfp28InputLowPowerAlarmInhibit				INTEGER,
				ommp401Qsfp28InputHighPowerWarningInhibit			INTEGER,
				ommp401Qsfp28InputLowPowerWarningInhibit			INTEGER,
				ommp401Qsfp28OutputHighPowerAlarmInhibit			INTEGER,
				ommp401Qsfp28OutputLowPowerAlarmInhibit				INTEGER,
				ommp401Qsfp28OutputHighPowerWarningInhibit			INTEGER,
				ommp401Qsfp28OutputLowPowerWarningInhibit			INTEGER,
				ommp401Qsfp28HighSupplyVoltageAlarmInhibit			INTEGER,
				ommp401Qsfp28LowSupplyVoltageAlarmInhibit			INTEGER,
				ommp401Qsfp28HighSupplyVoltageWarningInhibit			INTEGER,
				ommp401Qsfp28LowSupplyVoltageWarningInhibit			INTEGER,
				ommp401Qsfp28PresenceAbsenceNotificationInhibit			INTEGER,
				ommp401OtuLossOfSignalAlarmInhibit				INTEGER,
				ommp401OtuLossOfFrameAlarmInhibit				INTEGER,
				ommp401OtuOutOfFrameAlarmInhibit				INTEGER,
				ommp401OtuLossOfMultiFrameAlarmInhibit			INTEGER,
				ommp401OtuOutOfMultiFrameAlarmInhibit			INTEGER,
				ommp401OtuSignalDegradeAlarmInhibit				INTEGER,
				ommp401OtuAlarmIndicationSignalAlarmInhibit			INTEGER,
				ommp401OtuIncomingAlignmentErrorAlarmInhibit			INTEGER,
				ommp401OtuTrailTraceIdentifierMismatchAlarmInhibit		INTEGER,
				ommp401OtuBackwardIncomingAlignmentErrorAlarmInhibit		INTEGER,
				ommp401OtuBackwardDefectIndicationAlarmInhibit		INTEGER,
				ommp401OduSignalDegradeAlarmInhibit				INTEGER,
				ommp401OduAlarmIndicationSignalAlarmInhibit			INTEGER,
				ommp401OduTrailTraceIdentifierMismatchAlarmInhibit		INTEGER,
				ommp401OduLockedDefectAlarmInhibit				INTEGER,
				ommp401OduOpenConnectionIndicationAlarmInhibit		INTEGER,
				ommp401OduBackwardDefectIndicationAlarmInhibit		INTEGER,
				ommp401OduTcm1BackwardDefectIndicationAlarmInhibit		INTEGER,
				ommp401OduTcm2BackwardDefectIndicationAlarmInhibit		INTEGER,
				ommp401OduTcm3BackwardDefectIndicationAlarmInhibit		INTEGER,
				ommp401OduTcm4BackwardDefectIndicationAlarmInhibit		INTEGER,
				ommp401OduTcm5BackwardDefectIndicationAlarmInhibit		INTEGER,
				ommp401OduTcm6BackwardDefectIndicationAlarmInhibit		INTEGER,
				ommp401OduTcm1LossOfTandemConnectionAlarmInhibit		INTEGER,
				ommp401OduTcm2LossOfTandemConnectionAlarmInhibit		INTEGER,
				ommp401OduTcm3LossOfTandemConnectionAlarmInhibit		INTEGER,
				ommp401OduTcm4LossOfTandemConnectionAlarmInhibit		INTEGER,
				ommp401OduTcm5LossOfTandemConnectionAlarmInhibit		INTEGER,
				ommp401OduTcm6LossOfTandemConnectionAlarmInhibit		INTEGER,
				ommp401OduTcm1BackwardIncomingAlignmentErrorAlarmInhibit	INTEGER,
				ommp401OduTcm2BackwardIncomingAlignmentErrorAlarmInhibit	INTEGER,
				ommp401OduTcm3BackwardIncomingAlignmentErrorAlarmInhibit	INTEGER,
				ommp401OduTcm4BackwardIncomingAlignmentErrorAlarmInhibit	INTEGER,
				ommp401OduTcm5BackwardIncomingAlignmentErrorAlarmInhibit	INTEGER,
				ommp401OduTcm6BackwardIncomingAlignmentErrorAlarmInhibit	INTEGER,
				ommp401OpuPayloadMismatchAlarmInhibit				INTEGER,
				ommp401EthernetLossOfSignalAlarmInhibit				INTEGER,
				ommp401EthernetIngressRemoteFaultAlarmInhibit			INTEGER,
				ommp401EthernetIngressPcsErrorBlocksDetectedAlarmInhibit	INTEGER,
				ommp401EthernetIngressPcsBipErrorsDetectedAlarmInhibit		INTEGER,
				ommp401EthernetIngressOpuClientServerFailIndicationAlarmInhibit	INTEGER,
				ommp401EthernetIngressLocalFaultAlarmInhibit			INTEGER,
				ommp401EthernetIngressLossOfAlignmentAlarmInhibit		INTEGER,
				ommp401EthernetIngressLossOfAlignmentMarkerLockAlarmInhibit	INTEGER,
				ommp401EthernetIngressLossOfBlockLockAlarmInhibit		INTEGER,
				ommp401EthernetEgressRemoteFaultAlarmInhibit			INTEGER,
				ommp401EthernetEgressPcsErrorBlocksDetectedAlarmInhibit		INTEGER,
				ommp401EthernetEgressPcsBipErrorsDetectedAlarmInhibit		INTEGER,
				ommp401EthernetEgressHighBerAlarmInhibit			INTEGER,
				ommp401EthernetEgressLocalFaultAlarmInhibit			INTEGER,
				ommp401EthernetEgressLossOfAlignmentAlarmInhibit		INTEGER,
				ommp401EthernetEgressLossOfAlignmentMarkerLockAlarmInhibit	INTEGER,
				ommp401EthernetEgressLossOfBlockLockAlarmInhibit		INTEGER,
				ommp401Cfp2InputPowerFailureAlarmSeverity			DisplayString,
				ommp401Cfp2OutputPowerFailureAlarmSeverity			DisplayString,
				ommp401Cfp2HighTemperatureAlarmSeverity			DisplayString,
				ommp401Cfp2LowTemperatureAlarmSeverity			DisplayString,
				ommp401Cfp2HighTemperatureWarningSeverity			DisplayString,
				ommp401Cfp2LowTemperatureWarningSeverity			DisplayString,
				ommp401Cfp2InputHighPowerAlarmSeverity			DisplayString,
				ommp401Cfp2InputLowPowerAlarmSeverity				DisplayString,
				ommp401Cfp2InputHighPowerWarningSeverity			DisplayString,
				ommp401Cfp2InputLowPowerWarningSeverity			DisplayString,
				ommp401Cfp2OutputHighPowerAlarmSeverity			DisplayString,
				ommp401Cfp2OutputLowPowerAlarmSeverity			DisplayString,
				ommp401Cfp2OutputHighPowerWarningSeverity			DisplayString,
				ommp401Cfp2OutputLowPowerWarningSeverity			DisplayString,
				ommp401Cfp2HighSupplyVoltageAlarmSeverity			DisplayString,
				ommp401Cfp2LowSupplyVoltageAlarmSeverity			DisplayString,
				ommp401Cfp2HighSupplyVoltageWarningSeverity			DisplayString,
				ommp401Cfp2LowSupplyVoltageWarningSeverity			DisplayString,
				ommp401Cfp2PresenceAbsenceNotificationSeverity		DisplayString,
				ommp401Qsfp28InputPowerFailureAlarmSeverity			DisplayString,
				ommp401Qsfp28OutputPowerFailureAlarmSeverity			DisplayString,
				ommp401Qsfp28HighTemperatureAlarmSeverity			DisplayString,
				ommp401Qsfp28LowTemperatureAlarmSeverity			DisplayString,
				ommp401Qsfp28HighTemperatureWarningSeverity			DisplayString,
				ommp401Qsfp28LowTemperatureWarningSeverity			DisplayString,
				ommp401Qsfp28HighBiasCurrentAlarmSeverity			DisplayString,
				ommp401Qsfp28LowBiasCurrentAlarmSeverity			DisplayString,
				ommp401Qsfp28HighBiasCurrentWarningSeverity			DisplayString,
				ommp401Qsfp28LowBiasCurrentWarningSeverity			DisplayString,
				ommp401Qsfp28InputHighPowerAlarmSeverity			DisplayString,
				ommp401Qsfp28InputLowPowerAlarmSeverity				DisplayString,
				ommp401Qsfp28InputHighPowerWarningSeverity			DisplayString,
				ommp401Qsfp28InputLowPowerWarningSeverity			DisplayString,
				ommp401Qsfp28OutputHighPowerAlarmSeverity			DisplayString,
				ommp401Qsfp28OutputLowPowerAlarmSeverity			DisplayString,
				ommp401Qsfp28OutputHighPowerWarningSeverity			DisplayString,
				ommp401Qsfp28OutputLowPowerWarningSeverity			DisplayString,
				ommp401Qsfp28HighSupplyVoltageAlarmSeverity			DisplayString,
				ommp401Qsfp28LowSupplyVoltageAlarmSeverity			DisplayString,
				ommp401Qsfp28HighSupplyVoltageWarningSeverity			DisplayString,
				ommp401Qsfp28LowSupplyVoltageWarningSeverity			DisplayString,
				ommp401Qsfp28PresenceAbsenceNotificationSeverity		DisplayString,
				ommp401OtuLossOfSignalAlarmSeverity				DisplayString,
				ommp401OtuLossOfFrameAlarmSeverity				DisplayString,
				ommp401OtuOutOfFrameAlarmSeverity				DisplayString,
				ommp401OtuOutOfMultiFrameAlarmSeverity			DisplayString,
				ommp401OtuSignalDegradeAlarmSeverity				DisplayString,
				ommp401OtuAlarmIndicationSignalAlarmSeverity			DisplayString,
				ommp401OtuIncomingAlignmentErrorAlarmSeverity			DisplayString,
				ommp401OtuTrailTraceIdentifierMismatchAlarmSeverity		DisplayString,
				ommp401OtuBackwardIncomingAlignmentErrorAlarmSeverity		DisplayString,
				ommp401OtuBackwardDefectIndicationAlarmSeverity		DisplayString,
				ommp401OduSignalDegradeAlarmSeverity				DisplayString,
				ommp401OduAlarmIndicationSignalAlarmSeverity			DisplayString,
				ommp401OduTrailTraceIdentifierMismatchAlarmSeverity		DisplayString,
				ommp401OduLockedDefectAlarmSeverity				DisplayString,
				ommp401OduOpenConnectionIndicationAlarmSeverity		DisplayString,
				ommp401OduBackwardDefectIndicationAlarmSeverity		DisplayString,
				ommp401OduTcm1BackwardDefectIndicationAlarmSeverity		DisplayString,
				ommp401OduTcm2BackwardDefectIndicationAlarmSeverity		DisplayString,
				ommp401OduTcm3BackwardDefectIndicationAlarmSeverity		DisplayString,
				ommp401OduTcm4BackwardDefectIndicationAlarmSeverity		DisplayString,
				ommp401OduTcm5BackwardDefectIndicationAlarmSeverity		DisplayString,
				ommp401OduTcm6BackwardDefectIndicationAlarmSeverity		DisplayString,
				ommp401OduTcm1LossOfTandemConnectionAlarmSeverity		DisplayString,
				ommp401OduTcm2LossOfTandemConnectionAlarmSeverity		DisplayString,
				ommp401OduTcm3LossOfTandemConnectionAlarmSeverity		DisplayString,
				ommp401OduTcm4LossOfTandemConnectionAlarmSeverity		DisplayString,
				ommp401OduTcm5LossOfTandemConnectionAlarmSeverity		DisplayString,
				ommp401OduTcm6LossOfTandemConnectionAlarmSeverity		DisplayString,
				ommp401OduTcm1BackwardIncomingAlignmentErrorAlarmSeverity				DisplayString,
				ommp401OduTcm2BackwardIncomingAlignmentErrorAlarmSeverity				DisplayString,
				ommp401OduTcm3BackwardIncomingAlignmentErrorAlarmSeverity				DisplayString,
				ommp401OduTcm4BackwardIncomingAlignmentErrorAlarmSeverity				DisplayString,
				ommp401OduTcm5BackwardIncomingAlignmentErrorAlarmSeverity				DisplayString,
				ommp401OduTcm6BackwardIncomingAlignmentErrorAlarmSeverity				DisplayString,
				ommp401OpuPayloadMismatchAlarmSeverity				DisplayString,
				ommp401EthernetLossOfSignalAlarmSeverity				DisplayString,
				ommp401EthernetIngressRemoteFaultAlarmSeverity			DisplayString,
				ommp401EthernetIngressPcsErrorBlocksDetectedAlarmSeverity	DisplayString,
				ommp401EthernetIngressPcsBipErrorsDetectedAlarmSeverity		DisplayString,
				ommp401EthernetIngressOpuClientServerFailIndicationAlarmSeverity	DisplayString,
				ommp401EthernetIngressLocalFaultAlarmSeverity			DisplayString,
				ommp401EthernetIngressLossOfAlignmentAlarmSeverity		DisplayString,
				ommp401EthernetIngressLossOfAlignmentMarkerLockAlarmSeverity	DisplayString,
				ommp401EthernetIngressLossOfBlockLockAlarmSeverity		DisplayString,
				ommp401EthernetEgressRemoteFaultAlarmSeverity			DisplayString,
				ommp401EthernetEgressPcsErrorBlocksDetectedAlarmSeverity		DisplayString,
				ommp401EthernetEgressPcsBipErrorsDetectedAlarmSeverity		DisplayString,
				ommp401EthernetEgressHighBerAlarmSeverity			DisplayString,
				ommp401EthernetEgressLocalFaultAlarmSeverity			DisplayString,
				ommp401EthernetEgressLossOfAlignmentAlarmSeverity		DisplayString,
				ommp401EthernetEgressLossOfAlignmentMarkerLockAlarmSeverity	DisplayString,
				ommp401EthernetEgressLossOfBlockLockAlarmSeverity		DisplayString,
				ommp401TunableCfp2WavelengthGridSpacing				INTEGER,
				ommp401LineOtuSignalFailThreshold				INTEGER,
				ommp401LineOtuSignalDegradeThreshold				INTEGER,
				ommp401LineOtuSapiTransmitTraceMessage				DisplayString,
				ommp401LineOtuDapiTransmitTraceMessage				DisplayString,
				ommp401LineOtuOperatorSpecificTransmitTraceMessage		DisplayString,
				ommp401LineOtuSapiExpectedTraceMessage				DisplayString,
				ommp401LineOtuDapiExpectedTraceMessage				DisplayString,
				ommp401LineOtuOperatorSpecificExpectedTraceMessage		DisplayString,
				ommp401LineOduSignalFailThreshold				INTEGER,
				ommp401LineOduSignalDegradeThreshold				INTEGER,
				ommp401LineOduSapiTransmitTraceMessage				DisplayString,
				ommp401LineOduDapiTransmitTraceMessage				DisplayString,
				ommp401LineOduOperatorSpecificTransmitTraceMessage		DisplayString,
				ommp401LineOduSapiExpectedTraceMessage				DisplayString,
				ommp401LineOduDapiExpectedTraceMessage				DisplayString,
				ommp401LineOduOperatorSpecificExpectedTraceMessage		DisplayString,
				ommp401LineOtuLossOfSignalAlarmInhibit				INTEGER,
				ommp401LineOtuLossOfFrameAlarmInhibit				INTEGER,
				ommp401LineOtuOutOfFrameAlarmInhibit				INTEGER,
				ommp401LineOtuLossOfMultiFrameAlarmInhibit			INTEGER,
				ommp401LineOtuOutOfMultiFrameAlarmInhibit			INTEGER,
				ommp401LineOtuSignalDegradeAlarmInhibit				INTEGER,
				ommp401LineOtuAlarmIndicationSignalAlarmInhibit			INTEGER,
				ommp401LineOtuIncomingAlignmentErrorAlarmInhibit			INTEGER,
				ommp401LineOtuTrailTraceIdentifierMismatchAlarmInhibit		INTEGER,
				ommp401LineOtuBackwardIncomingAlignmentErrorAlarmInhibit		INTEGER,
				ommp401LineOtuBackwardDefectIndicationAlarmInhibit		INTEGER,
				ommp401LineOduSignalDegradeAlarmInhibit				INTEGER,
				ommp401LineOduAlarmIndicationSignalAlarmInhibit			INTEGER,
				ommp401LineOduTrailTraceIdentifierMismatchAlarmInhibit		INTEGER,
				ommp401LineOduLockedDefectAlarmInhibit				INTEGER,
				ommp401LineOduOpenConnectionIndicationAlarmInhibit		INTEGER,
				ommp401LineOduBackwardDefectIndicationAlarmInhibit		INTEGER,
				ommp401LineOduTcm1BackwardDefectIndicationAlarmInhibit		INTEGER,
				ommp401LineOduTcm2BackwardDefectIndicationAlarmInhibit		INTEGER,
				ommp401LineOduTcm3BackwardDefectIndicationAlarmInhibit		INTEGER,
				ommp401LineOduTcm4BackwardDefectIndicationAlarmInhibit		INTEGER,
				ommp401LineOduTcm5BackwardDefectIndicationAlarmInhibit		INTEGER,
				ommp401LineOduTcm6BackwardDefectIndicationAlarmInhibit		INTEGER,
				ommp401LineOduTcm1LossOfTandemConnectionAlarmInhibit		INTEGER,
				ommp401LineOduTcm2LossOfTandemConnectionAlarmInhibit		INTEGER,
				ommp401LineOduTcm3LossOfTandemConnectionAlarmInhibit		INTEGER,
				ommp401LineOduTcm4LossOfTandemConnectionAlarmInhibit		INTEGER,
				ommp401LineOduTcm5LossOfTandemConnectionAlarmInhibit		INTEGER,
				ommp401LineOduTcm6LossOfTandemConnectionAlarmInhibit		INTEGER,
				ommp401LineOduTcm1BackwardIncomingAlignmentErrorAlarmInhibit	INTEGER,
				ommp401LineOduTcm2BackwardIncomingAlignmentErrorAlarmInhibit	INTEGER,
				ommp401LineOduTcm3BackwardIncomingAlignmentErrorAlarmInhibit	INTEGER,
				ommp401LineOduTcm4BackwardIncomingAlignmentErrorAlarmInhibit	INTEGER,
				ommp401LineOduTcm5BackwardIncomingAlignmentErrorAlarmInhibit	INTEGER,
				ommp401LineOduTcm6BackwardIncomingAlignmentErrorAlarmInhibit	INTEGER,
				ommp401LineOpuPayloadMismatchAlarmInhibit				INTEGER,
				ommp401LineOtuLossOfSignalAlarmSeverity				DisplayString,
				ommp401LineOtuLossOfFrameAlarmSeverity				DisplayString,
				ommp401LineOtuOutOfFrameAlarmSeverity				DisplayString,
				ommp401LineOtuOutOfMultiFrameAlarmSeverity			DisplayString,
				ommp401LineOtuSignalDegradeAlarmSeverity				DisplayString,
				ommp401LineOtuAlarmIndicationSignalAlarmSeverity			DisplayString,
				ommp401LineOtuIncomingAlignmentErrorAlarmSeverity			DisplayString,
				ommp401LineOtuTrailTraceIdentifierMismatchAlarmSeverity		DisplayString,
				ommp401LineOtuBackwardIncomingAlignmentErrorAlarmSeverity		DisplayString,
				ommp401LineOtuBackwardDefectIndicationAlarmSeverity		DisplayString,
				ommp401LineOduSignalDegradeAlarmSeverity				DisplayString,
				ommp401LineOduAlarmIndicationSignalAlarmSeverity			DisplayString,
				ommp401LineOduTrailTraceIdentifierMismatchAlarmSeverity		DisplayString,
				ommp401LineOduLockedDefectAlarmSeverity				DisplayString,
				ommp401LineOduOpenConnectionIndicationAlarmSeverity		DisplayString,
				ommp401LineOduBackwardDefectIndicationAlarmSeverity		DisplayString,
				ommp401LineOduTcm1BackwardDefectIndicationAlarmSeverity		DisplayString,
				ommp401LineOduTcm2BackwardDefectIndicationAlarmSeverity		DisplayString,
				ommp401LineOduTcm3BackwardDefectIndicationAlarmSeverity		DisplayString,
				ommp401LineOduTcm4BackwardDefectIndicationAlarmSeverity		DisplayString,
				ommp401LineOduTcm5BackwardDefectIndicationAlarmSeverity		DisplayString,
				ommp401LineOduTcm6BackwardDefectIndicationAlarmSeverity		DisplayString,
				ommp401LineOduTcm1LossOfTandemConnectionAlarmSeverity		DisplayString,
				ommp401LineOduTcm2LossOfTandemConnectionAlarmSeverity		DisplayString,
				ommp401LineOduTcm3LossOfTandemConnectionAlarmSeverity		DisplayString,
				ommp401LineOduTcm4LossOfTandemConnectionAlarmSeverity		DisplayString,
				ommp401LineOduTcm5LossOfTandemConnectionAlarmSeverity		DisplayString,
				ommp401LineOduTcm6LossOfTandemConnectionAlarmSeverity		DisplayString,
				ommp401LineOduTcm1BackwardIncomingAlignmentErrorAlarmSeverity				DisplayString,
				ommp401LineOduTcm2BackwardIncomingAlignmentErrorAlarmSeverity				DisplayString,
				ommp401LineOduTcm3BackwardIncomingAlignmentErrorAlarmSeverity				DisplayString,
				ommp401LineOduTcm4BackwardIncomingAlignmentErrorAlarmSeverity				DisplayString,
				ommp401LineOduTcm5BackwardIncomingAlignmentErrorAlarmSeverity				DisplayString,
				ommp401LineOduTcm6BackwardIncomingAlignmentErrorAlarmSeverity				DisplayString,
				ommp401LineOpuPayloadMismatchAlarmSeverity						DisplayString,
				ommp401ConfigurationTableRowStatus				RowStatus
			}
		
	ommp401CardSoftwareUpgrade OBJECT-TYPE		 
		SYNTAX  DisplayString
		MAX-ACCESS read-write
		STATUS current
		DESCRIPTION
			"Valid only as SET command.
			This property upgrades the software of the OMMP401 card
			It takes the path of the software release as
			a value
			-----------------------------
			ommp401InterfaceNumber: 0
			-----------------------------
			Values:
			eg: /root/home/rel-2.0.0.tar.gz
			-----------------------------"
		::= { ommp401ConfigurationEntry 1 }

	ommp401CardSignalMonitorState OBJECT-TYPE		 
		SYNTAX  INTEGER
		MAX-ACCESS read-write
		STATUS current
		DESCRIPTION
			"This property sets or gets the card's signal
			monitoring state. Disabling card signal monitoring 
			will not provide any signal alarms and performances
			information to the user.
			-----------------------------
			ommp401InterfaceNumber: 0
			-----------------------------
			Values:
			1 - Card Signal Monitoring is enabled
			0 - Card Signal Monitoring is disabled
			-----------------------------"
		::= { ommp401ConfigurationEntry 2 }

	ommp401CardOpticalMonitorState OBJECT-TYPE		 
		SYNTAX  INTEGER
		MAX-ACCESS read-write
		STATUS current
		DESCRIPTION
			"This property sets or gets the card's optical
			monitoring state. Disabling card signal monitoring 
			will not provide any signal alarms and performances
			information to the user.
			-----------------------------
			ommp401InterfaceNumber: 0
			-----------------------------
			Values:
			1 - Card Optical Monitoring is enabled
			0 - Card Optical Monitoring is disabled
			-----------------------------"
		::= { ommp401ConfigurationEntry 3 }

	ommp401CardSoftReset OBJECT-TYPE		 
		SYNTAX  INTEGER
		MAX-ACCESS read-write
		STATUS current
		DESCRIPTION
			"Valid only as a SET command.
			Reboots the Card, Reconfigures the Card 
			i.e All Configuration Parameter	like Laser State,
			Traffic configuration, Loopback, FEC, optical and 
			signal thresholds, switching mode,
			user choice of line path, auto-negotiation, 
			TTI messages will be restored to previous state
			-----------------------------
			ommp401InterfaceNumber: 0
			-----------------------------
			Values:
			Dont care, any value
			eg: 0
			-----------------------------"
		::= { ommp401ConfigurationEntry 4 }

	ommp401CardFactoryReset OBJECT-TYPE		 
		SYNTAX  INTEGER
		MAX-ACCESS read-write
		STATUS current
		DESCRIPTION
			"Valid only as a SET command.
			Sets the Card To Factory Default State
			i.e All User Configuration Parameters like Laser State,
			Traffic configuration, Loopback, FEC, optical and 
			signal thresholds, switching mode,
			user choice of line path, auto-negotiation, TTI messages
			will be set to default state
			-----------------------------
			ommp401InterfaceNumber: 0
			-----------------------------
			Values:
			Dont care, any value
			eg: 0
			-----------------------------"
		::= { ommp401ConfigurationEntry 5 }
		
	ommp401SyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that ilarticular server. 
					If we are not providing NTP server IP address 
					then the system will be synced with the NTP server 
					which is already been registered with card. 
					If both are absent then error message will be returned
					-----------------------------
						Interface : 0
					-----------------------------
						If we want to provide NTP server IP address then
						Value should be a valid IP address as shown below
						: 192.168.21.25
						
						If we don't want to provide NTP server address then no
						need to pass any value. 
					---------------------------"
  						
  		::= { ommp401ConfigurationEntry 6 }
  		
  	ommp401SyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 192.168.21.25
							
						If we don't want to provide NTP server address, then no
						need to ilass any value. 
						---------------------------"
  						
  		::= { ommp401ConfigurationEntry 7 }
  		
  	ommp401SyncRtcWithSystemTime	 OBJECT-TYPE
		SYNTAX  		DisplayString
  		MAX-ACCESS  	read-write
  		STATUS  		current
  		DESCRIPTION	 	" when we want to manually sync the time value
  						present in RTC with the time value in linux kernel
  						we can use this OID. With this set operation, 
  						the time available with linux kernel will be updated
  						into RTC. It is not required to provide any value for 
  						this operation"
  						
  		::= { ommp401ConfigurationEntry 8 }
  		
  	ommp401UpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2017-10-31 15:20:44
						---------------------------"
						
  		::= { ommp401ConfigurationEntry 9 }
  		
  	ommp401UpdateGivenTimeIntoRtc	 OBJECT-TYPE
		SYNTAX  		DisplayString
  		MAX-ACCESS  	read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD H:M:S
						
						Example: 2017-10-31 15:20:44
						---------------------------"
						
  		::= { ommp401ConfigurationEntry 10 }
  		
  	ommp401SystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { ommp401ConfigurationEntry 11 }
		
	ommp401TrafficConfiguration OBJECT-TYPE		 
		SYNTAX  INTEGER
		MAX-ACCESS read-write
		STATUS current
		DESCRIPTION
			"Set or get Traffic configuration for all ports.
			The line port must be configured with traffic:
			Taclink - 100G
			Lumentum - 100G/200G
			NEC - 100G/200/400G.
			The client ports supports traffic:
			OTU4/100GbE
			To Unconfigure traffic on line port, all client ports
			should be unconfigured first.			
			----------------------------------------
			If line side module is Taclink CFP2:
			100G mode: supported clients ports are port3/port4.
			----------------------------------------
			If line side module is Lumentum CFP2-DCO:
			In 100G mode: supported client ports are 1/2/3/4.
			In 200G mode: supported client ports are 1/2 and 3/4(configure any two ports eg: port1 and port3).
			----------------------------------------
			If line side module is NEC CFP2:
			In 100G mode: supported client ports are port3/port4.
			In 200G mode: supported client ports are port3 and port4.
			In 400G mode: supported client ports are 1,2,3 and 4.
			----------------------------------------
			ommp401InterfaceNumber:
			1 to 5 - CLIENT-1 to CLIENT-4 and LINE-5
			----------------------------------------			
			Value: 
			For client
			00 - Un-configure 
			01 - OTU4
			02 - 100GbE
			For line
			00 - Un-configure
			01 - OTU4  (100G Line) 			
			03 - OTUC2 (200G Line)
			04 - OTUC4 (400G Line)
			-----------------------------"
		::= { ommp401ConfigurationEntry 12 }

	ommp401LoopbackState OBJECT-TYPE		 
		SYNTAX  INTEGER
		MAX-ACCESS read-write
		STATUS current
		DESCRIPTION
			"Set or get the loopback state for the
			requested port
			----------------------------------------
			If line side module is CFP2(Taclink,etc)
			Client Near end loopback can be configured
			Client Far end loopback is not supported
			Line near end loopback is not supported
			Line far end loopback can be configured
			----------------------------------------
			If line side module is CFP2-DCO(Lumentum,etc)
			Both near end loopback and far end loopback can be configured on client
			Both near end loopback and far end loopback can be configured on line			----------------------------------------
			-----------------------------
			ommp401InterfaceNumber:
			1 to 4 - CLIENT-1 to CLIENT-4
			5 - LINE-1
			-----------------------------
			Values: 
			00 - No Loopback   
			01 - Near End Loopback
			02 - Far End Loopback
			-----------------------------"
		::= { ommp401ConfigurationEntry 13 }

	ommp401PortSignalMonitorState OBJECT-TYPE		 
		SYNTAX  INTEGER
		MAX-ACCESS read-write
		STATUS current
		DESCRIPTION
			"This property sets or gets the port's signal
			monitoring state. Disabling port signal monitoring 
			will not provide any signal alarms and performances
			information to the user.
			-----------------------------
			ommp401InterfaceNumber:
			1 to 4 - CLIENT-1 to CLIENT-4
			5 - LINE-1
			-----------------------------
			Values:
			1 - Port Signal Monitoring is enabled
			0 - Port Signal Monitoring is disabled
			-----------------------------"
		::= { ommp401ConfigurationEntry 14 }

	ommp401PortOpticalMonitorState OBJECT-TYPE		 
		SYNTAX  INTEGER
		MAX-ACCESS read-write
		STATUS current
		DESCRIPTION
			"This property sets or gets the port's optical
			monitoring state. Disabling port optical monitoring 
			will not provide any optical alarms and performances
			information to the user.
			-----------------------------
			ommp401InterfaceNumber:
			1 to 4 - CLIENT-1 to CLIENT-4
			5 - LINE-1
			-----------------------------
			Values:
			1 - Port Optical Monitoring is enabled
			0 - Port Optical Monitoring is disabled
			-----------------------------"
		::= { ommp401ConfigurationEntry 15 }

	ommp401ClearSignalPerformance OBJECT-TYPE		 
		SYNTAX  INTEGER
		MAX-ACCESS read-write
		STATUS current
		DESCRIPTION
			"Valid only as a SET command.
			Clears signal performance for the requested port
			-----------------------------
			ommp401InterfaceNumber:
			1 to 4 - CLIENT-1 to CLIENT-4
			5 - LINE-1
			-----------------------------
			Values:
			Dont care, any value
			eg: 0
			-----------------------------"
		::= { ommp401ConfigurationEntry 16 }

	ommp401AlsState OBJECT-TYPE		 
		SYNTAX  INTEGER
		MAX-ACCESS read-write
		STATUS current
		DESCRIPTION
			"Set the Automatic Laser Switching(ALS) mode for
			for requested port. Based on the RX LOS state of the
			port, the transmit LASER state will be controlled
			according to the algorithm defined for ALS in
			ITUT 664 Standard
			-----------------------------
			ommp401InterfaceNumber:
			1 to 4 - CLIENT-1 to CLIENT-4
			5 - LINE-1
			-----------------------------
			Values: 
			1 - Enable ALS state
			0 - Disable ALS state
			-----------------------------" 
		::= { ommp401ConfigurationEntry 17 }

	ommp401AlsPulseRepetitionTime OBJECT-TYPE		 
		SYNTAX  INTEGER
		MAX-ACCESS read-write
		STATUS current
		DESCRIPTION
			"Pulse repetition time is the time for automatic 
			restart of CFP2 LASER once the ALS algorithm starts.
			-----------------------------
			ommp401InterfaceNumber:
			1 to 4 - CLIENT-1 to CLIENT-4
			5 - LINE-1
			-----------------------------
			Values: 
			1 seconds to 300 seconds
			-----------------------------"
		::= { ommp401ConfigurationEntry 18 }

	ommp401OtuFecConfiguration OBJECT-TYPE		 
		SYNTAX  INTEGER
		MAX-ACCESS read-write
		STATUS current
		DESCRIPTION
			"Set or Get FEC type for requested port configured with
			 OTU4/OTUC4 traffic.  
			----------------------------------------
			If line side module is CFP2(Taclink,etc)
			Fec does not supported
			----------------------------------------
			If line side module is CFP2-DCO(Lumentum,etc)
			If line is OTU4(100G), Zero FEC and OTU-4 G.709 FEC are supported
			If line is OTUC2(200G), only 15% Denali Compatible is supported
			-----------------------------
			ommp401InterfaceNumber:
			1 to 4 - CLIENT-1 to CLIENT-4
			5 - LINE-1
			-----------------------------
			Values: 
			00 - Zero FEC 
			01 - OTU-4 G.709 FEC
			03 - 15% Denali Compatible
			-----------------------------"
		::= { ommp401ConfigurationEntry 19 }

	ommp401OtuSignalFailThreshold OBJECT-TYPE		 
		SYNTAX  INTEGER
		MAX-ACCESS read-write
		STATUS current
		DESCRIPTION
			"Set or Get SM Signal Failure 
			Threshold value for the requested port configured with 
			OTU4/OTUC4 traffic.
			-----------------------------
			ommp401InterfaceNumber:
			1 to 4 - CLIENT-1 to CLIENT-4
			-----------------------------
			Values: 
			03 - 1.E -03
			04 - 1.E -04
			05 - 1.E -05
			-----------------------------" 
		::= { ommp401ConfigurationEntry 20 }

	ommp401OtuSignalDegradeThreshold OBJECT-TYPE		 
		SYNTAX  INTEGER
		MAX-ACCESS read-write
		STATUS current
		DESCRIPTION
			"Set or Get SM Signal Degrade 
			Threshold value for the requested port configured with 
			OTU4/OTUC4 traffic.
			-----------------------------
			ommp401InterfaceNumber:
			1 to 4 - CLIENT-1 to CLIENT-4
			-----------------------------
			Values:
			06 - 1.E -06
			07 - 1.E -07
			08 - 1.E -08
			09 - 1.E -09
			10 - 1.E -10(for line only)
			-----------------------------"
		::= { ommp401ConfigurationEntry 21 }

	ommp401OtuSapiTransmitTraceMessage OBJECT-TYPE
		SYNTAX DisplayString
		MAX-ACCESS read-write
		STATUS current
		DESCRIPTION
			"Set or get the 15 characters SAPI Transmit TTI message
			which is put into the outgoing OTU4/OTUC4 frame. 
			-----------------------------
			ommp401InterfaceNumber:
			1 to 4 - CLIENT-1 to CLIENT-4
			-----------------------------
			Values:
			eg: 123451234512345
			-----------------------------" 
		::= { ommp401ConfigurationEntry 22 }

	ommp401OtuDapiTransmitTraceMessage OBJECT-TYPE
		SYNTAX DisplayString
		MAX-ACCESS read-write
		STATUS current
		DESCRIPTION
			"Set or get the 15 characters DAPI Transmit TTI message
			which is put into the outgoing OTU4/OTUC4 frame. 
			-----------------------------
			ommp401InterfaceNumber:
			1 to 4 - CLIENT-1 to CLIENT-4
			-----------------------------
			Values:
			eg: 123451234512345
			-----------------------------" 
		::= { ommp401ConfigurationEntry 23 }
		
	ommp401OtuOperatorSpecificTransmitTraceMessage OBJECT-TYPE
		SYNTAX DisplayString
		MAX-ACCESS read-write
		STATUS current
		DESCRIPTION
			"Set or get the 32 characters Operator Specific Transmit
			TTI message which is put into the outgoing OTU4/OTUC4
			frame. 
			-----------------------------
			ommp401InterfaceNumber:
			1 to 4 - CLIENT-1 to CLIENT-4
			-----------------------------
			Values:
			eg: 12345123451234512345123451234500
			-----------------------------" 
		::= { ommp401ConfigurationEntry 24 }
		
	ommp401OtuSapiExpectedTraceMessage OBJECT-TYPE
		SYNTAX DisplayString
		MAX-ACCESS read-write
		STATUS current
		DESCRIPTION
			"15 characters SM SAPI Expected TTI message - Message
			set here is used for comparison with the message present
			in SM SAPI field of the incoming OTU4/OTUC4 frames.
			-----------------------------
			ommp401InterfaceNumber:
			1 to 4 - CLIENT-1 to CLIENT-4
			-----------------------------
			Values:
			eg: 123451234512345
			-----------------------------" 
		::= { ommp401ConfigurationEntry 25 }
		
	ommp401OtuDapiExpectedTraceMessage OBJECT-TYPE
		SYNTAX DisplayString
		MAX-ACCESS read-write
		STATUS current
		DESCRIPTION
			"15 characters SM DAPI Expected TTI message - Message
			set here is used for comparison with the message present
			in SM DAPI field of the incoming OTU4/OTUC4 frames.
			-----------------------------
			ommp401InterfaceNumber:
			1 to 4 - CLIENT-1 to CLIENT-4
			-----------------------------
			Values:
			eg: 123451234512345
			-----------------------------" 
		::= { ommp401ConfigurationEntry 26 }

	ommp401OtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU4/OTUC4 frames.
			-----------------------------
			ommp401InterfaceNumber:
			1 to 4 - CLIENT-1 to CLIENT-4
			-----------------------------
			Values:
			eg: 12345123451234512345123451234500
			-----------------------------" 
		::= { ommp401ConfigurationEntry 27 }

	ommp401OduSignalFailThreshold OBJECT-TYPE		 
		SYNTAX  INTEGER
		MAX-ACCESS read-write
		STATUS current
		DESCRIPTION
			"Set or Get PM Signal Failure 
			Threshold value for the requested port configured with 
			OTU4/OTUC4 traffic.
			-----------------------------
			ommp401InterfaceNumber:
			1 to 4 - CLIENT-1 to CLIENT-4
			-----------------------------
			Values: 
			03 - 1.E -03
			04 - 1.E -04
			05 - 1.E -05
			-----------------------------" 
		::= { ommp401ConfigurationEntry 28 }

	ommp401OduSignalDegradeThreshold OBJECT-TYPE		 
		SYNTAX  INTEGER
		MAX-ACCESS read-write
		STATUS current
		DESCRIPTION
			"Set or Get PM Signal Degrade 
			Threshold value for the requested port configured with 
			OTU4/OTUC4 traffic.
			-----------------------------
			ommp401InterfaceNumber:
			1 to 4 - CLIENT-1 to CLIENT-4
			-----------------------------
			Values: 
			06 - 1.E -06
			07 - 1.E -07
			08 - 1.E -08
			09 - 1.E -09
			10 - 1.E -10(for line only)
			-----------------------------" 
		::= { ommp401ConfigurationEntry 29 }

	ommp401OduSapiTransmitTraceMessage OBJECT-TYPE
		SYNTAX DisplayString
		MAX-ACCESS read-write
		STATUS current
		DESCRIPTION
			"Set or get the 15 characters SAPI Transmit TTI message
			which is put into the outgoing OTU4/OTUC4
			frame at the PM level. 
			-----------------------------
			ommp401InterfaceNumber:
			1 to 4 - CLIENT-1 to CLIENT-4
			-----------------------------
			Values:
			eg: 123451234512345
			-----------------------------" 
		::= { ommp401ConfigurationEntry 30 }
		
	ommp401OduDapiTransmitTraceMessage OBJECT-TYPE
		SYNTAX DisplayString
		MAX-ACCESS read-write
		STATUS current
		DESCRIPTION
			"Set or get the 15 characters DAPI Transmit TTI message
			which is put into the outgoing OTU4/OTUC4
			frame at the PM level. 
			-----------------------------
			ommp401InterfaceNumber:
			1 to 4 - CLIENT-1 to CLIENT-4
			-----------------------------
			Values:
			eg: 123451234512345
			-----------------------------" 
		::= { ommp401ConfigurationEntry 31 }
		
	ommp401OduOperatorSpecificTransmitTraceMessage OBJECT-TYPE
		SYNTAX DisplayString
		MAX-ACCESS read-write
		STATUS current
		DESCRIPTION
			"Set or get the 32 characters Operator Specific Transmit
			TTI message which is put into the outgoing OTU4/OTUC4
			frame at the PM level. 
			-----------------------------
			ommp401InterfaceNumber:
			1 to 4 - CLIENT-1 to CLIENT-4
			-----------------------------
			Values:
			eg: 12345123451234512345123451234500
			-----------------------------" 
		::= { ommp401ConfigurationEntry 32 }
		
	ommp401OduSapiExpectedTraceMessage OBJECT-TYPE
		SYNTAX DisplayString
		MAX-ACCESS read-write
		STATUS current
		DESCRIPTION
			"15 characters PM SAPI Expected TTI message - Message
			set here is used for comparison with the message present
			in PM SAPI field of the incoming OTU4/OTUC4 frames.
			-----------------------------
			ommp401InterfaceNumber:
			1 to 4 - CLIENT-1 to CLIENT-4
			-----------------------------
			Values:
			eg: 123451234512345
			-----------------------------" 
		::= { ommp401ConfigurationEntry 33 }

	ommp401OduDapiExpectedTraceMessage OBJECT-TYPE
		SYNTAX DisplayString
		MAX-ACCESS read-write
		STATUS current
		DESCRIPTION
			"15 characters PM DAPI Expected TTI message - Message
			set here is used for comparison with the message present
			in PM DAPI field of the incoming OTU4/OTUC4 frames.
			-----------------------------
			ommp401InterfaceNumber:
			1 to 4 - CLIENT-1 to CLIENT-4
			-----------------------------
			Values:
			eg: 123451234512345
			-----------------------------" 
		::= { ommp401ConfigurationEntry 34 }
		
	ommp401OduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU4/OTUC4 frames.
			-----------------------------
			ommp401InterfaceNumber:
			1 to 4 - CLIENT-1 to CLIENT-4
			-----------------------------
			Values:
			eg: 12345123451234512345123451234500
			-----------------------------" 
		::= { ommp401ConfigurationEntry 35 }

	ommp401TunableCfp2LaserWavelength OBJECT-TYPE		 
		SYNTAX  INTEGER
		MAX-ACCESS read-write
		STATUS current
		DESCRIPTION
			"Set or Get the CFP2 wavelength for the requested port
			-----------------------------
			ommp401InterfaceNumber:
			5 - LINE-1
			-----------------------------
			Values:
			eg: 1529.944
			-----------------------------"
		::= { ommp401ConfigurationEntry 36 }

	ommp401Cfp2LaserState OBJECT-TYPE		 
		SYNTAX  INTEGER
		MAX-ACCESS read-write
		STATUS current
		DESCRIPTION
			"Set or Get the CFP2 LASER state for the the requested
			port
			-----------------------------
			ommp401InterfaceNumber:
			5 - LINE-1
			-----------------------------
			Values: 
			00 - Laser OFF
			01 - Laser ON
			-----------------------------"
		::= { ommp401ConfigurationEntry 38 }

	ommp401Cfp2Reset OBJECT-TYPE		 
		SYNTAX  INTEGER
		MAX-ACCESS read-write
		STATUS current
		DESCRIPTION
			"Valid only as a SET command.
			Resets the CFP2.
			-----------------------------
			ommp401InterfaceNumber:
			5 - LINE-1
			-----------------------------
			Values: 
			Dont care, any value
			eg: 0
			-----------------------------"
		::= { ommp401ConfigurationEntry 39 }

	ommp401Cfp2PowerDownMode OBJECT-TYPE		 
		SYNTAX  INTEGER
		MAX-ACCESS read-write
		STATUS current
		DESCRIPTION
			"Valid only as a SET command.
			Sets the CFP2 in the Power Down mode i.e. low power 
			consumption mode.
			-----------------------------
			ommp401InterfaceNumber:
			5 - LINE-1
			-----------------------------
			Values: 
			01 - power down CFP2
			-----------------------------"
		::= { ommp401ConfigurationEntry 40 }

	ommp401Cfp2HighTemperatureAlarmThreshold OBJECT-TYPE
		SYNTAX DisplayString
		MAX-ACCESS read-write
		STATUS current
		DESCRIPTION
			"Set or Get High Temperature Alarm Threshold
			(in degree celsius) for the requested port
			-----------------------------
			ommp401InterfaceNumber:
			5 - LINE-1
			-----------------------------
			Values: 
			eg: 65 
			-----------------------------" 
		::= { ommp401ConfigurationEntry 41 }
		
	ommp401Cfp2LowTemperatureAlarmThreshold OBJECT-TYPE
		SYNTAX DisplayString
		MAX-ACCESS read-write
		STATUS current
		DESCRIPTION
			"Set or Get Low Temperature Alarm Threshold
			(in degree celsius) for the requested port
			-----------------------------
			ommp401InterfaceNumber:
			5 - LINE-1
			-----------------------------
			Values: 
			eg: 5 
			-----------------------------" 
		::= { ommp401ConfigurationEntry 42 }
		
	ommp401Cfp2HighTemperatureWarningThreshold OBJECT-TYPE
		SYNTAX DisplayString
		MAX-ACCESS read-write
		STATUS current
		DESCRIPTION
			"Set or Get High Temperature Warning Threshold
			(in degree celsius) for the requested port
			-----------------------------
			ommp401InterfaceNumber:
			5 - LINE-1
			-----------------------------
			Values: 
			eg: 60 
			-----------------------------"
		::= { ommp401ConfigurationEntry 43 }
		
	ommp401Cfp2LowTemperatureWarningThreshold OBJECT-TYPE
		SYNTAX DisplayString
		MAX-ACCESS read-write
		STATUS current
		DESCRIPTION
			"Set or Get Low Temperature Warning Threshold
			(in degree celsius) for the requested port
			-----------------------------
			ommp401InterfaceNumber:
			5 - LINE-1
			-----------------------------
			Values: 
			eg: 10 
			-----------------------------"
		::= { ommp401ConfigurationEntry 44 }
		
	ommp401Cfp2InputHighPowerAlarmThreshold OBJECT-TYPE
		SYNTAX DisplayString
		MAX-ACCESS read-write
		STATUS current
		DESCRIPTION
			"Set or Get Input High Power Alarm Threshold
			(in dbm) for the requested port
			-----------------------------
			ommp401InterfaceNumber:
			5 - LINE-1
			-----------------------------
			Values:
			eg: -9.1
			-----------------------------"
		::= { ommp401ConfigurationEntry 45 }

	ommp401Cfp2InputLowPowerAlarmThreshold OBJECT-TYPE
		SYNTAX DisplayString
		MAX-ACCESS read-write
		STATUS current
		DESCRIPTION
			"Set or Get Input Low Power Alarm Threshold
			(in dbm) for the requested port
			-----------------------------
			ommp401InterfaceNumber:
			5 - LINE-1
			-----------------------------
			Values:
			eg: -35.6
			-----------------------------"
		::= { ommp401ConfigurationEntry 46 }
		
	ommp401Cfp2InputHighPowerWarningThreshold OBJECT-TYPE
		SYNTAX DisplayString
		MAX-ACCESS read-write
		STATUS current
		DESCRIPTION
			"Set or Get Input High Power Warning Threshold
			(in dbm) for the requested port
			-----------------------------
			ommp401InterfaceNumber:
			5 - LINE-1
			-----------------------------
			Values:
			eg: -11.2
			-----------------------------"
		::= { ommp401ConfigurationEntry 47 }
		
	ommp401Cfp2InputLowPowerWarningThreshold OBJECT-TYPE
		SYNTAX DisplayString
		MAX-ACCESS read-write
		STATUS current
		DESCRIPTION
			"Set or Get Input Low Power Warning Threshold
			(in dbm) for the requested port
			-----------------------------
			ommp401InterfaceNumber:
			5 - LINE-1
			-----------------------------
			Values:
			eg: -31.3
			-----------------------------"
		::= { ommp401ConfigurationEntry 48 }
		
	ommp401Cfp2OutputHighPowerAlarmThreshold OBJECT-TYPE
		SYNTAX DisplayString
		MAX-ACCESS read-write
		STATUS current
		DESCRIPTION
			"Set or Get Output High Power Alarm Threshold
			(in dbm) for the requested port
			-----------------------------
			ommp401InterfaceNumber:
			5 - LINE-1
			-----------------------------
			Values:
			eg: +2.0
			-----------------------------"
		::= { ommp401ConfigurationEntry 49 }

	ommp401Cfp2OutputLowPowerAlarmThreshold OBJECT-TYPE
		SYNTAX DisplayString
		MAX-ACCESS read-write
		STATUS current
		DESCRIPTION
			"Set or Get Output Low Power Alarm Threshold
			(in dbm) for the requested port
			-----------------------------
			ommp401InterfaceNumber:
			5 - LINE-1
			-----------------------------
			Values:
			eg: -3.5
			-----------------------------"
		::= { ommp401ConfigurationEntry 50 }
		
	ommp401Cfp2OutputHighPowerWarningThreshold OBJECT-TYPE
		SYNTAX DisplayString
		MAX-ACCESS read-write
		STATUS current
		DESCRIPTION
			"Set or Get Output High Power Warning Threshold
			(in dbm) for the requested port
			-----------------------------
			ommp401InterfaceNumber:
			5 - LINE-1
			-----------------------------
			Values:
			eg: +1.3
			-----------------------------"
		::= { ommp401ConfigurationEntry 51 }
		
	ommp401Cfp2OutputLowPowerWarningThreshold OBJECT-TYPE
		SYNTAX DisplayString
		MAX-ACCESS read-write
		STATUS current
		DESCRIPTION
			"Set or Get Output Low Power Warning Threshold
			(in dbm) for the requested port
			-----------------------------
			ommp401InterfaceNumber:
			5 - LINE-1
			-----------------------------
			Values:
			eg: -2.5
			-----------------------------"
		::= { ommp401ConfigurationEntry 52 }
		
	ommp401Cfp2HighSupplyVoltageAlarmThreshold OBJECT-TYPE
		SYNTAX DisplayString
		MAX-ACCESS read-write
		STATUS current
		DESCRIPTION
			"Set or Get High Supply Voltage Alarm Threshold
			(in volts) for the requested port
			-----------------------------
			ommp401InterfaceNumber:
			5 - LINE-1
			-----------------------------
			Values:
			eg: +3.3
			-----------------------------"
		::= { ommp401ConfigurationEntry 53 }

	ommp401Cfp2LowSupplyVoltageAlarmThreshold OBJECT-TYPE
		SYNTAX DisplayString
		MAX-ACCESS read-write
		STATUS current
		DESCRIPTION
			"Set or Get Low Supply Voltage Alarm Threshold
			(in volts) for the requested port
			-----------------------------
			ommp401InterfaceNumber:
			5 - LINE-1
			-----------------------------
			Values:
			eg: +3.0
			-----------------------------"
		::= { ommp401ConfigurationEntry 54 }
		
	ommp401Cfp2HighSupplyVoltageWarningThreshold OBJECT-TYPE
		SYNTAX DisplayString
		MAX-ACCESS read-write
		STATUS current
		DESCRIPTION
			"Set or Get High Supply Voltage Warning Threshold
			(in volts) for the requested port
			-----------------------------
			ommp401InterfaceNumber:
			5 - LINE-1
			-----------------------------
			Values:
			eg: +3.2
			-----------------------------"
		::= { ommp401ConfigurationEntry 55 }
		
	ommp401Cfp2LowSupplyVoltageWarningThreshold OBJECT-TYPE
		SYNTAX DisplayString
		MAX-ACCESS read-write
		STATUS current
		DESCRIPTION
			"Set or Get Low Supply Voltage Warning Threshold
			(in volts) for the requested port
			-----------------------------
			ommp401InterfaceNumber:
			5 - LINE-1
			-----------------------------
			Values:
			eg: +3.1
			-----------------------------"
		::= { ommp401ConfigurationEntry 56 }

	ommp401Qsfp28LaserState OBJECT-TYPE		 
		SYNTAX  INTEGER
		MAX-ACCESS read-write
		STATUS current
		DESCRIPTION
			"Set or Get the QSFP28 LASER state for the the requested
			port
			-----------------------------
			ommp401InterfaceNumber:
			1 to 4 - CLIENT-1 to CLIENT-4
			-----------------------------
			Values: 
			01 - Laser ON
			00 - Laser OFF
			-----------------------------" 
		::= { ommp401ConfigurationEntry 57 }

	ommp401Qsfp28Reset OBJECT-TYPE		 
		SYNTAX  INTEGER
		MAX-ACCESS read-write
		STATUS current
		DESCRIPTION
			"Valid only as a SET command.
			Resets the Qsfp28.
			-----------------------------
			ommp401InterfaceNumber:
			1 to 4 - CLIENT-1 to CLIENT-4
			-----------------------------
			Values: 
			Dont care, any value
			eg: 0
			-----------------------------"
		::= { ommp401ConfigurationEntry 58 }

	ommp401Qsfp28PowerDownMode OBJECT-TYPE		 
		SYNTAX  INTEGER
		MAX-ACCESS read-write
		STATUS current
		DESCRIPTION
			"Valid only as a SET command.
			Sets the Qsfp28 in the Power Down mode i.e. low power 
			consumption mode.
			-----------------------------
			ommp401InterfaceNumber:
			1 to 4 - CLIENT-1 to CLIENT-4
			-----------------------------
			Values: 
			01 - power down Qsfp28
			-----------------------------"
		::= { ommp401ConfigurationEntry 59 }

	ommp401Qsfp28HighTemperatureAlarmThreshold OBJECT-TYPE
		SYNTAX DisplayString
		MAX-ACCESS read-write
		STATUS current
		DESCRIPTION
			"Set or Get High Temperature Alarm Threshold
			(in degree celsius) for the requested port
			-----------------------------
			ommp401InterfaceNumber:
			1 to 4 - CLIENT-1 to CLIENT-4
			-----------------------------
			Values: 
			eg: 65 
			-----------------------------" 
		::= { ommp401ConfigurationEntry 60 }
		
	ommp401Qsfp28LowTemperatureAlarmThreshold OBJECT-TYPE
		SYNTAX DisplayString
		MAX-ACCESS read-write
		STATUS current
		DESCRIPTION
			"Set or Get Low Temperature Alarm Threshold
			(in degree celsius) for the requested port
			-----------------------------
			ommp401InterfaceNumber:
			1 to 4 - CLIENT-1 to CLIENT-4
			-----------------------------
			Values: 
			eg: 5 
			-----------------------------" 
		::= { ommp401ConfigurationEntry 61 }
		
	ommp401Qsfp28HighTemperatureWarningThreshold OBJECT-TYPE
		SYNTAX DisplayString
		MAX-ACCESS read-write
		STATUS current
		DESCRIPTION
			"Set or Get High Temperature Warning Threshold
			(in degree celsius) for the requested port
			-----------------------------
			ommp401InterfaceNumber:
			1 to 4 - CLIENT-1 to CLIENT-4
			-----------------------------
			Values: 
			eg: 60 
			-----------------------------"
		::= { ommp401ConfigurationEntry 62 }
		
	ommp401Qsfp28LowTemperatureWarningThreshold OBJECT-TYPE
		SYNTAX DisplayString
		MAX-ACCESS read-write
		STATUS current
		DESCRIPTION
			"Set or Get Low Temperature Warning Threshold
			(in degree celsius) for the requested port
			-----------------------------
			ommp401InterfaceNumber:
			1 to 4 - CLIENT-1 to CLIENT-4
			-----------------------------
			Values: 
			eg: 10 
			-----------------------------"
		::= { ommp401ConfigurationEntry 63 }

	ommp401Qsfp28HighBiasCurrentAlarmThreshold OBJECT-TYPE
		SYNTAX DisplayString
		MAX-ACCESS read-write
		STATUS current
		DESCRIPTION
			"Set or Get High Bias Current Alarm Threshold
			(in milli ampere) for the requested port
			-----------------------------
			ommp401InterfaceNumber:
			1 to 4 - CLIENT-1 to CLIENT-4
			-----------------------------
			Values:
			eg: 35.6
			-----------------------------"			
		::= { ommp401ConfigurationEntry 64 }
		
	ommp401Qsfp28LowBiasCurrentAlarmThreshold OBJECT-TYPE
		SYNTAX DisplayString
		MAX-ACCESS read-write
		STATUS current
		DESCRIPTION
			"Set or Get Low Bias Current Alarm Threshold
			(in milli ampere) for the requested port
			-----------------------------
			ommp401InterfaceNumber:
			1 to 4 - CLIENT-1 to CLIENT-4
			-----------------------------
			Values:
			eg: 31.1
			-----------------------------"
		::= { ommp401ConfigurationEntry 65 }
		
	ommp401Qsfp28HighBiasCurrentWarningThreshold OBJECT-TYPE
		SYNTAX DisplayString
		MAX-ACCESS read-write
		STATUS current
		DESCRIPTION
			"Set or Get High Bias Current Warning Threshold
			(in milli ampere) for the requested port
			-----------------------------
			ommp401InterfaceNumber:
			1 to 4 - CLIENT-1 to CLIENT-4
			-----------------------------
			Values:
			eg: 34.5
			-----------------------------"
		::= { ommp401ConfigurationEntry 66 }
		
	ommp401Qsfp28LowBiasCurrentWarningThreshold OBJECT-TYPE
		SYNTAX DisplayString
		MAX-ACCESS read-write
		STATUS current
		DESCRIPTION
			"Set or Get Low Bias Current Alarm Threshold
			(in milli ampere) for the requested port
			-----------------------------
			ommp401InterfaceNumber:
			1 to 4 - CLIENT-1 to CLIENT-4
			-----------------------------
			Values:
			eg: 32.8
			-----------------------------"
		::= { ommp401ConfigurationEntry 67 }
		
	ommp401Qsfp28InputHighPowerAlarmThreshold OBJECT-TYPE
		SYNTAX DisplayString
		MAX-ACCESS read-write
		STATUS current
		DESCRIPTION
			"Set or Get Input High Power Alarm Threshold
			(in dbm) for the requested port
			-----------------------------
			ommp401InterfaceNumber:
			1 to 4 - CLIENT-1 to CLIENT-4
			-----------------------------
			Values:
			eg: -9.1
			-----------------------------"
		::= { ommp401ConfigurationEntry 68 }

	ommp401Qsfp28InputLowPowerAlarmThreshold OBJECT-TYPE
		SYNTAX DisplayString
		MAX-ACCESS read-write
		STATUS current
		DESCRIPTION
			"Set or Get Input Low Power Alarm Threshold
			(in dbm) for the requested port
			-----------------------------
			ommp401InterfaceNumber:
			1 to 4 - CLIENT-1 to CLIENT-4
			-----------------------------
			Values:
			eg: -35.6
			-----------------------------"
		::= { ommp401ConfigurationEntry 69 }
		
	ommp401Qsfp28InputHighPowerWarningThreshold OBJECT-TYPE
		SYNTAX DisplayString
		MAX-ACCESS read-write
		STATUS current
		DESCRIPTION
			"Set or Get Input High Power Warning Threshold
			(in dbm) for the requested port
			-----------------------------
			ommp401InterfaceNumber:
			1 to 4 - CLIENT-1 to CLIENT-4
			-----------------------------
			Values:
			eg: -11.2
			-----------------------------"
		::= { ommp401ConfigurationEntry 70 }
		
	ommp401Qsfp28InputLowPowerWarningThreshold OBJECT-TYPE
		SYNTAX DisplayString
		MAX-ACCESS read-write
		STATUS current
		DESCRIPTION
			"Set or Get Input Low Power Warning Threshold
			(in dbm) for the requested port
			-----------------------------
			ommp401InterfaceNumber:
			1 to 4 - CLIENT-1 to CLIENT-4
			-----------------------------
			Values:
			eg: -31.3
			-----------------------------"
		::= { ommp401ConfigurationEntry 71 }
		
	ommp401Qsfp28OutputHighPowerAlarmThreshold OBJECT-TYPE
		SYNTAX DisplayString
		MAX-ACCESS read-write
		STATUS current
		DESCRIPTION
			"Set or Get Output High Power Alarm Threshold
			(in dbm) for the requested port
			-----------------------------
			ommp401InterfaceNumber:
			1 to 4 - CLIENT-1 to CLIENT-4
			-----------------------------
			Values:
			eg: +2.0
			-----------------------------"
		::= { ommp401ConfigurationEntry 72 }

	ommp401Qsfp28OutputLowPowerAlarmThreshold OBJECT-TYPE
		SYNTAX DisplayString
		MAX-ACCESS read-write
		STATUS current
		DESCRIPTION
			"Set or Get Output Low Power Alarm Threshold
			(in dbm) for the requested port
			-----------------------------
			ommp401InterfaceNumber:
			1 to 4 - CLIENT-1 to CLIENT-4
			-----------------------------
			Values:
			eg: -3.5
			-----------------------------"
		::= { ommp401ConfigurationEntry 73 }
		
	ommp401Qsfp28OutputHighPowerWarningThreshold OBJECT-TYPE
		SYNTAX DisplayString
		MAX-ACCESS read-write
		STATUS current
		DESCRIPTION
			"Set or Get Output High Power Warning Threshold
			(in dbm) for the requested port
			-----------------------------
			ommp401InterfaceNumber:
			1 to 4 - CLIENT-1 to CLIENT-4
			-----------------------------
			Values:
			eg: +1.3
			-----------------------------"
		::= { ommp401ConfigurationEntry 74 }
		
	ommp401Qsfp28OutputLowPowerWarningThreshold OBJECT-TYPE
		SYNTAX DisplayString
		MAX-ACCESS read-write
		STATUS current
		DESCRIPTION
			"Set or Get Output Low Power Warning Threshold
			(in dbm) for the requested port
			-----------------------------
			ommp401InterfaceNumber:
			1 to 4 - CLIENT-1 to CLIENT-4
			-----------------------------
			Values:
			eg: -2.5
			-----------------------------"
		::= { ommp401ConfigurationEntry 75 }
		
	ommp401Qsfp28HighSupplyVoltageAlarmThreshold OBJECT-TYPE
		SYNTAX DisplayString
		MAX-ACCESS read-write
		STATUS current
		DESCRIPTION
			"Set or Get High Supply Voltage Alarm Threshold
			(in volts) for the requested port
			-----------------------------
			ommp401InterfaceNumber:
			1 to 4 - CLIENT-1 to CLIENT-4
			-----------------------------
			Values:
			eg: +3.3
			-----------------------------"
		::= { ommp401ConfigurationEntry 76 }

	ommp401Qsfp28LowSupplyVoltageAlarmThreshold OBJECT-TYPE
		SYNTAX DisplayString
		MAX-ACCESS read-write
		STATUS current
		DESCRIPTION
			"Set or Get Low Supply Voltage Alarm Threshold
			(in volts) for the requested port
			-----------------------------
			ommp401InterfaceNumber:
			1 to 4 - CLIENT-1 to CLIENT-4
			-----------------------------
			Values:
			eg: +3.0
			-----------------------------"
		::= { ommp401ConfigurationEntry 77 }
		
	ommp401Qsfp28HighSupplyVoltageWarningThreshold OBJECT-TYPE
		SYNTAX DisplayString
		MAX-ACCESS read-write
		STATUS current
		DESCRIPTION
			"Set or Get High Supply Voltage Warning Threshold
			(in volts) for the requested port
			-----------------------------
			ommp401InterfaceNumber:
			1 to 4 - CLIENT-1 to CLIENT-4
			-----------------------------
			Values:
			eg: +3.2
			-----------------------------"
		::= { ommp401ConfigurationEntry 78 }
		
	ommp401Qsfp28LowSupplyVoltageWarningThreshold OBJECT-TYPE
		SYNTAX DisplayString
		MAX-ACCESS read-write
		STATUS current
		DESCRIPTION
			"Set or Get Low Supply Voltage Warning Threshold
			(in volts) for the requested port
			-----------------------------
			ommp401InterfaceNumber:
			1 to 4 - CLIENT-1 to CLIENT-4
			-----------------------------
			Values:
			eg: +3.1
			-----------------------------"
		::= { ommp401ConfigurationEntry 79 }

	ommp401Cfp2InputPowerFailureAlarmInhibit  OBJECT-TYPE
		SYNTAX  INTEGER
		MAX-ACCESS  read-write
		STATUS  current
		DESCRIPTION
			"Inhibits OMMP401 CFP2 Input Power Failure Alarm
			for the requested port
			-----------------------------
			ommp401InterfaceNumber:
			5 - LINE-1
			-----------------------------
			Value:
			1 - Inhibit
			0 - Do Not Inhibit
			-----------------------------"
	::= { ommp401ConfigurationEntry 80 }

	ommp401Cfp2OutputPowerFailureAlarmInhibit  OBJECT-TYPE
		SYNTAX  INTEGER
		MAX-ACCESS  read-write
		STATUS  current
		DESCRIPTION
			"Inhibits OMMP401 CFP2 Output Power Failure Alarm
			for the requested port
			-----------------------------
			ommp401InterfaceNumber:
			5 - LINE-1
			-----------------------------
			Value:
			1 - Inhibit
			0 - Do Not Inhibit
			-----------------------------"
	::= { ommp401ConfigurationEntry 81 }

	ommp401Cfp2HighTemperatureAlarmInhibit  OBJECT-TYPE
		SYNTAX  INTEGER
		MAX-ACCESS  read-write
		STATUS  current
		DESCRIPTION
			"Inhibits OMMP401 CFP2 High Temperature Alarm
			for the requested port
			-----------------------------
			ommp401InterfaceNumber:
			5 - LINE-1
			-----------------------------
			Value:
			1 - Inhibit
			0 - Do Not Inhibit
			-----------------------------"
	::= { ommp401ConfigurationEntry 82 }

	ommp401Cfp2LowTemperatureAlarmInhibit  OBJECT-TYPE
		SYNTAX  INTEGER
		MAX-ACCESS  read-write
		STATUS  current
		DESCRIPTION
			"Inhibits OMMP401 CFP2 Low Temperature Alarm
			for the requested port
			-----------------------------
			ommp401InterfaceNumber:
			5 - LINE-1
			-----------------------------
			Value:
			1 - Inhibit
			0 - Do Not Inhibit
			-----------------------------"
	::= { ommp401ConfigurationEntry 83 }

	ommp401Cfp2HighTemperatureWarningInhibit  OBJECT-TYPE
		SYNTAX  INTEGER
		MAX-ACCESS  read-write
		STATUS  current
		DESCRIPTION
			"Inhibits OMMP401 CFP2 High Temperature Warning
			for the requested port
			-----------------------------
			ommp401InterfaceNumber:
			5 - LINE-1
			-----------------------------
			Value:
			1 - Inhibit
			0 - Do Not Inhibit
			-----------------------------"
	::= { ommp401ConfigurationEntry 84 }

	ommp401Cfp2LowTemperatureWarningInhibit  OBJECT-TYPE
		SYNTAX  INTEGER
		MAX-ACCESS  read-write
		STATUS  current
		DESCRIPTION
			"Inhibits OMMP401 CFP2 Low Temperature Warning
			for the requested port
			-----------------------------
			ommp401InterfaceNumber:
			5 - LINE-1
			-----------------------------
			Value:
			1 - Inhibit
			0 - Do Not Inhibit
			-----------------------------"
	::= { ommp401ConfigurationEntry 85 }

	ommp401Cfp2InputHighPowerAlarmInhibit  OBJECT-TYPE
		SYNTAX  INTEGER
		MAX-ACCESS  read-write
		STATUS  current
		DESCRIPTION
			"Inhibits OMMP401 CFP2 Input High Power Alarm
			for the requested port
			-----------------------------
			ommp401InterfaceNumber:
			5 - LINE-1
			-----------------------------
			Value:
			1 - Inhibit
			0 - Do Not Inhibit
			-----------------------------"
	::= { ommp401ConfigurationEntry 86 }

	ommp401Cfp2InputLowPowerAlarmInhibit  OBJECT-TYPE
		SYNTAX  INTEGER
		MAX-ACCESS  read-write
		STATUS  current
		DESCRIPTION
			"Inhibits OMMP401 CFP2 Input Low Power Alarm
			for the requested port
			-----------------------------
			ommp401InterfaceNumber:
			5 - LINE-1
			-----------------------------
			Value:
			1 - Inhibit
			0 - Do Not Inhibit
			-----------------------------"
	::= { ommp401ConfigurationEntry 87 }

	ommp401Cfp2InputHighPowerWarningInhibit  OBJECT-TYPE
		SYNTAX  INTEGER
		MAX-ACCESS  read-write
		STATUS  current
		DESCRIPTION
			"Inhibits OMMP401 CFP2 Input High Power Warning
			for the requested port
			-----------------------------
			ommp401InterfaceNumber:
			5 - LINE-1
			-----------------------------
			Value:
			1 - Inhibit
			0 - Do Not Inhibit
			-----------------------------"
	::= { ommp401ConfigurationEntry 88 }

	ommp401Cfp2InputLowPowerWarningInhibit  OBJECT-TYPE
		SYNTAX  INTEGER
		MAX-ACCESS  read-write
		STATUS  current
		DESCRIPTION
			"Inhibits OMMP401 CFP2 Input Low Power Warning
			for the requested port
			-----------------------------
			ommp401InterfaceNumber:
			5 - LINE-1
			-----------------------------
			Value:
			1 - Inhibit
			0 - Do Not Inhibit
			-----------------------------"
	::= { ommp401ConfigurationEntry 89 }

	ommp401Cfp2OutputHighPowerAlarmInhibit  OBJECT-TYPE
		SYNTAX  INTEGER
		MAX-ACCESS  read-write
		STATUS  current
		DESCRIPTION
			"Inhibits OMMP401 CFP2 Output High Power Alarm
			for the requested port
			-----------------------------
			ommp401InterfaceNumber:
			5 - LINE-1
			-----------------------------
			Value:
			1 - Inhibit
			0 - Do Not Inhibit
			-----------------------------"
	::= { ommp401ConfigurationEntry 90 }

	ommp401Cfp2OutputLowPowerAlarmInhibit  OBJECT-TYPE
		SYNTAX  INTEGER
		MAX-ACCESS  read-write
		STATUS  current
		DESCRIPTION
			"Inhibits OMMP401 CFP2 Output Low Power Alarm
			for the requested port
			-----------------------------
			ommp401InterfaceNumber:
			5 - LINE-1
			-----------------------------
			Value:
			1 - Inhibit
			0 - Do Not Inhibit
			-----------------------------"
	::= { ommp401ConfigurationEntry 91 }

	ommp401Cfp2OutputHighPowerWarningInhibit  OBJECT-TYPE
		SYNTAX  INTEGER
		MAX-ACCESS  read-write
		STATUS  current
		DESCRIPTION
			"Inhibits OMMP401 CFP2 Output High Power Warning
			for the requested port
			-----------------------------
			ommp401InterfaceNumber:
			5 - LINE-1
			-----------------------------
			Value:
			1 - Inhibit
			0 - Do Not Inhibit
			-----------------------------"
	::= { ommp401ConfigurationEntry 92 }

	ommp401Cfp2OutputLowPowerWarningInhibit  OBJECT-TYPE
		SYNTAX  INTEGER
		MAX-ACCESS  read-write
		STATUS  current
		DESCRIPTION
			"Inhibits OMMP401 CFP2 Output Low Power Warning
			for the requested port
			-----------------------------
			ommp401InterfaceNumber:
			5 - LINE-1
			-----------------------------
			Value:
			1 - Inhibit
			0 - Do Not Inhibit
			-----------------------------"
	::= { ommp401ConfigurationEntry 93 }

	ommp401Cfp2HighSupplyVoltageAlarmInhibit  OBJECT-TYPE
		SYNTAX  INTEGER
		MAX-ACCESS  read-write
		STATUS  current
		DESCRIPTION
			"Inhibits OMMP401 CFP2 High Supply Voltage Alarm
			for the requested port
			-----------------------------
			ommp401InterfaceNumber:
			5 - LINE-1
			-----------------------------
			Value:
			1 - Inhibit
			0 - Do Not Inhibit
			-----------------------------"
	::= { ommp401ConfigurationEntry 94 }

	ommp401Cfp2LowSupplyVoltageAlarmInhibit  OBJECT-TYPE
		SYNTAX  INTEGER
		MAX-ACCESS  read-write
		STATUS  current
		DESCRIPTION
			"Inhibits OMMP401 CFP2 Low Supply Voltage Alarm
			for the requested port
			-----------------------------
			ommp401InterfaceNumber:
			5 - LINE-1
			-----------------------------
			Value:
			1 - Inhibit
			0 - Do Not Inhibit
			-----------------------------"
	::= { ommp401ConfigurationEntry 95 }

	ommp401Cfp2HighSupplyVoltageWarningInhibit  OBJECT-TYPE
		SYNTAX  INTEGER
		MAX-ACCESS  read-write
		STATUS  current
		DESCRIPTION
			"Inhibits OMMP401 CFP2 High Supply Voltage Warning
			for the requested port
			-----------------------------
			ommp401InterfaceNumber:
			5 - LINE-1
			-----------------------------
			Value:
			1 - Inhibit
			0 - Do Not Inhibit
			-----------------------------"
	::= { ommp401ConfigurationEntry 96 }

	ommp401Cfp2LowSupplyVoltageWarningInhibit  OBJECT-TYPE
		SYNTAX  INTEGER
		MAX-ACCESS  read-write
		STATUS  current
		DESCRIPTION
			"Inhibits OMMP401 CFP2 Low Supply Voltage Warning
			for the requested port
			-----------------------------
			ommp401InterfaceNumber:
			5 - LINE-1
			-----------------------------
			Value:
			1 - Inhibit
			0 - Do Not Inhibit
			-----------------------------"
	::= { ommp401ConfigurationEntry 97 }

	ommp401Cfp2PresenceAbsenceNotificationInhibit  OBJECT-TYPE
		SYNTAX  INTEGER
		MAX-ACCESS  read-write
		STATUS  current
		DESCRIPTION
			"Inhibits OMMP401 CFP2 Presence Absence Notification
			for the requested port
			-----------------------------
			ommp401InterfaceNumber:
			5 - LINE-1
			-----------------------------
			Value:
			1 - Inhibit
			0 - Do Not Inhibit
			-----------------------------"
	::= { ommp401ConfigurationEntry 98 }

	ommp401Qsfp28InputPowerFailureAlarmInhibit  OBJECT-TYPE
		SYNTAX  INTEGER
		MAX-ACCESS  read-write
		STATUS  current
		DESCRIPTION
			"Inhibits OMMP401 QSFP28 Input Power Failure Alarm
			for the requested port
			-----------------------------
			ommp401InterfaceNumber:
			1 to 4 - CLIENT-1 to CLIENT-4
			-----------------------------
			Value:
			1 - Inhibit
			0 - Do Not Inhibit
			-----------------------------"
	::= { ommp401ConfigurationEntry 99 }

	ommp401Qsfp28OutputPowerFailureAlarmInhibit  OBJECT-TYPE
		SYNTAX  INTEGER
		MAX-ACCESS  read-write
		STATUS  current
		DESCRIPTION
			"Inhibits OMMP401 QSFP28 Output Power Failure Alarm
			for the requested port
			-----------------------------
			ommp401InterfaceNumber:
			1 to 4 - CLIENT-1 to CLIENT-4
			-----------------------------
			Value:
			1 - Inhibit
			0 - Do Not Inhibit
			-----------------------------"
	::= { ommp401ConfigurationEntry 100 }

	ommp401Qsfp28HighTemperatureAlarmInhibit  OBJECT-TYPE
		SYNTAX  INTEGER
		MAX-ACCESS  read-write
		STATUS  current
		DESCRIPTION
			"Inhibits OMMP401 QSFP28 High Temperature Alarm
			for the requested port
			-----------------------------
			ommp401InterfaceNumber:
			1 to 4 - CLIENT-1 to CLIENT-4
			-----------------------------
			Value:
			1 - Inhibit
			0 - Do Not Inhibit
			-----------------------------"
	::= { ommp401ConfigurationEntry 101 }

	ommp401Qsfp28LowTemperatureAlarmInhibit  OBJECT-TYPE
		SYNTAX  INTEGER
		MAX-ACCESS  read-write
		STATUS  current
		DESCRIPTION
			"Inhibits OMMP401 QSFP28 Low Temperature Alarm
			for the requested port
			-----------------------------
			ommp401InterfaceNumber:
			1 to 4 - CLIENT-1 to CLIENT-4
			-----------------------------
			Value:
			1 - Inhibit
			0 - Do Not Inhibit
			-----------------------------"
	::= { ommp401ConfigurationEntry 102 }

	ommp401Qsfp28HighTemperatureWarningInhibit  OBJECT-TYPE
		SYNTAX  INTEGER
		MAX-ACCESS  read-write
		STATUS  current
		DESCRIPTION
			"Inhibits OMMP401 QSFP28 High Temperature Warning
			for the requested port
			-----------------------------
			ommp401InterfaceNumber:
			1 to 4 - CLIENT-1 to CLIENT-4
			-----------------------------
			Value:
			1 - Inhibit
			0 - Do Not Inhibit
			-----------------------------"
	::= { ommp401ConfigurationEntry 103 }

	ommp401Qsfp28LowTemperatureWarningInhibit  OBJECT-TYPE
		SYNTAX  INTEGER
		MAX-ACCESS  read-write
		STATUS  current
		DESCRIPTION
			"Inhibits OMMP401 QSFP28 Low Temperature Warning
			for the requested port
			-----------------------------
			ommp401InterfaceNumber:
			1 to 4 - CLIENT-1 to CLIENT-4
			-----------------------------
			Value:
			1 - Inhibit
			0 - Do Not Inhibit
			-----------------------------"
	::= { ommp401ConfigurationEntry 104 }

	ommp401Qsfp28HighBiasCurrentAlarmInhibit  OBJECT-TYPE
		SYNTAX  INTEGER
		MAX-ACCESS  read-write
		STATUS  current
		DESCRIPTION
			"Inhibits OMMP401 QSFP28 High Bias Current Alarm
			for the requested port
			-----------------------------
			ommp401InterfaceNumber:
			1 to 4 - CLIENT-1 to CLIENT-4
			-----------------------------
			Value:
			1 - Inhibit
			0 - Do Not Inhibit
			-----------------------------"
	::= { ommp401ConfigurationEntry 105 }

	ommp401Qsfp28LowBiasCurrentAlarmInhibit  OBJECT-TYPE
		SYNTAX  INTEGER
		MAX-ACCESS  read-write
		STATUS  current
		DESCRIPTION
			"Inhibits OMMP401 QSFP28 Low Bias Current Alarm
			for the requested port
			-----------------------------
			ommp401InterfaceNumber:
			1 to 4 - CLIENT-1 to CLIENT-4
			-----------------------------
			Value:
			1 - Inhibit
			0 - Do Not Inhibit
			-----------------------------"
	::= { ommp401ConfigurationEntry 106 }

	ommp401Qsfp28HighBiasCurrentWarningInhibit  OBJECT-TYPE
		SYNTAX  INTEGER
		MAX-ACCESS  read-write
		STATUS  current
		DESCRIPTION
			"Inhibits OMMP401 QSFP28 High Bias Current Warning
			for the requested port
			-----------------------------
			ommp401InterfaceNumber:
			1 to 4 - CLIENT-1 to CLIENT-4
			-----------------------------
			Value:
			1 - Inhibit
			0 - Do Not Inhibit
			-----------------------------"
	::= { ommp401ConfigurationEntry 107 }

	ommp401Qsfp28LowBiasCurrentWarningInhibit  OBJECT-TYPE
		SYNTAX  INTEGER
		MAX-ACCESS  read-write
		STATUS  current
		DESCRIPTION
			"Inhibits OMMP401 QSFP28 Low Bias Current Warning
			for the requested port
			-----------------------------
			ommp401InterfaceNumber:
			1 to 4 - CLIENT-1 to CLIENT-4
			-----------------------------
			Value:
			1 - Inhibit
			0 - Do Not Inhibit
			-----------------------------"
	::= { ommp401ConfigurationEntry 108 }

	ommp401Qsfp28InputHighPowerAlarmInhibit  OBJECT-TYPE
		SYNTAX  INTEGER
		MAX-ACCESS  read-write
		STATUS  current
		DESCRIPTION
			"Inhibits OMMP401 QSFP28 Input High Power Alarm
			for the requested port
			-----------------------------
			ommp401InterfaceNumber:
			1 to 4 - CLIENT-1 to CLIENT-4
			-----------------------------
			Value:
			1 - Inhibit
			0 - Do Not Inhibit
			-----------------------------"
	::= { ommp401ConfigurationEntry 109 }

	ommp401Qsfp28InputLowPowerAlarmInhibit  OBJECT-TYPE
		SYNTAX  INTEGER
		MAX-ACCESS  read-write
		STATUS  current
		DESCRIPTION
			"Inhibits OMMP401 QSFP28 Input Low Power Alarm
			for the requested port
			-----------------------------
			ommp401InterfaceNumber:
			1 to 4 - CLIENT-1 to CLIENT-4
			-----------------------------
			Value:
			1 - Inhibit
			0 - Do Not Inhibit
			-----------------------------"
	::= { ommp401ConfigurationEntry 110 }

	ommp401Qsfp28InputHighPowerWarningInhibit  OBJECT-TYPE
		SYNTAX  INTEGER
		MAX-ACCESS  read-write
		STATUS  current
		DESCRIPTION
			"Inhibits OMMP401 QSFP28 Input High Power Warning
			for the requested port
			-----------------------------
			ommp401InterfaceNumber:
			1 to 4 - CLIENT-1 to CLIENT-4
			-----------------------------
			Value:
			1 - Inhibit
			0 - Do Not Inhibit
			-----------------------------"
	::= { ommp401ConfigurationEntry 111 }

	ommp401Qsfp28InputLowPowerWarningInhibit  OBJECT-TYPE
		SYNTAX  INTEGER
		MAX-ACCESS  read-write
		STATUS  current
		DESCRIPTION
			"Inhibits OMMP401 QSFP28 Input Low Power Warning
			for the requested port
			-----------------------------
			ommp401InterfaceNumber:
			1 to 4 - CLIENT-1 to CLIENT-4
			-----------------------------
			Value:
			1 - Inhibit
			0 - Do Not Inhibit
			-----------------------------"
	::= { ommp401ConfigurationEntry 112 }

	ommp401Qsfp28OutputHighPowerAlarmInhibit  OBJECT-TYPE
		SYNTAX  INTEGER
		MAX-ACCESS  read-write
		STATUS  current
		DESCRIPTION
			"Inhibits OMMP401 QSFP28 Output High Power Alarm
			for the requested port
			-----------------------------
			ommp401InterfaceNumber:
			1 to 4 - CLIENT-1 to CLIENT-4
			-----------------------------
			Value:
			1 - Inhibit
			0 - Do Not Inhibit
			-----------------------------"
	::= { ommp401ConfigurationEntry 113 }

	ommp401Qsfp28OutputLowPowerAlarmInhibit  OBJECT-TYPE
		SYNTAX  INTEGER
		MAX-ACCESS  read-write
		STATUS  current
		DESCRIPTION
			"Inhibits OMMP401 QSFP28 Output Low Power Alarm
			for the requested port
			-----------------------------
			ommp401InterfaceNumber:
			1 to 4 - CLIENT-1 to CLIENT-4
			-----------------------------
			Value:
			1 - Inhibit
			0 - Do Not Inhibit
			-----------------------------"
	::= { ommp401ConfigurationEntry 114 }

	ommp401Qsfp28OutputHighPowerWarningInhibit  OBJECT-TYPE
		SYNTAX  INTEGER
		MAX-ACCESS  read-write
		STATUS  current
		DESCRIPTION
			"Inhibits OMMP401 QSFP28 Output High Power Warning
			for the requested port
			-----------------------------
			ommp401InterfaceNumber:
			1 to 4 - CLIENT-1 to CLIENT-4
			-----------------------------
			Value:
			1 - Inhibit
			0 - Do Not Inhibit
			-----------------------------"
	::= { ommp401ConfigurationEntry 115 }

	ommp401Qsfp28OutputLowPowerWarningInhibit  OBJECT-TYPE
		SYNTAX  INTEGER
		MAX-ACCESS  read-write
		STATUS  current
		DESCRIPTION
			"Inhibits OMMP401 QSFP28 Output Low Power Warning
			for the requested port
			-----------------------------
			ommp401InterfaceNumber:
			1 to 4 - CLIENT-1 to CLIENT-4
			-----------------------------
			Value:
			1 - Inhibit
			0 - Do Not Inhibit
			-----------------------------"
	::= { ommp401ConfigurationEntry 116 }

	ommp401Qsfp28HighSupplyVoltageAlarmInhibit  OBJECT-TYPE
		SYNTAX  INTEGER
		MAX-ACCESS  read-write
		STATUS  current
		DESCRIPTION
			"Inhibits OMMP401 QSFP28 High Supply Voltage Alarm
			for the requested port
			-----------------------------
			ommp401InterfaceNumber:
			1 to 4 - CLIENT-1 to CLIENT-4
			-----------------------------
			Value:
			1 - Inhibit
			0 - Do Not Inhibit
			-----------------------------"
	::= { ommp401ConfigurationEntry 117 }

	ommp401Qsfp28LowSupplyVoltageAlarmInhibit  OBJECT-TYPE
		SYNTAX  INTEGER
		MAX-ACCESS  read-write
		STATUS  current
		DESCRIPTION
			"Inhibits OMMP401 QSFP28 Low Supply Voltage Alarm
			for the requested port
			-----------------------------
			ommp401InterfaceNumber:
			1 to 4 - CLIENT-1 to CLIENT-4
			-----------------------------
			Value:
			1 - Inhibit
			0 - Do Not Inhibit
			-----------------------------"
	::= { ommp401ConfigurationEntry 118 }

	ommp401Qsfp28HighSupplyVoltageWarningInhibit  OBJECT-TYPE
		SYNTAX  INTEGER
		MAX-ACCESS  read-write
		STATUS  current
		DESCRIPTION
			"Inhibits OMMP401 QSFP28 High Supply Voltage Warning
			for the requested port
			-----------------------------
			ommp401InterfaceNumber:
			1 to 4 - CLIENT-1 to CLIENT-4
			-----------------------------
			Value:
			1 - Inhibit
			0 - Do Not Inhibit
			-----------------------------"
	::= { ommp401ConfigurationEntry 119 }

	ommp401Qsfp28LowSupplyVoltageWarningInhibit  OBJECT-TYPE
		SYNTAX  INTEGER
		MAX-ACCESS  read-write
		STATUS  current
		DESCRIPTION
			"Inhibits OMMP401 QSFP28 Low Supply Voltage Warning
			for the requested port
			-----------------------------
			ommp401InterfaceNumber:
			1 to 4 - CLIENT-1 to CLIENT-4
			-----------------------------
			Value:
			1 - Inhibit
			0 - Do Not Inhibit
			-----------------------------"
	::= { ommp401ConfigurationEntry 120 }

	ommp401Qsfp28PresenceAbsenceNotificationInhibit  OBJECT-TYPE
		SYNTAX  INTEGER
		MAX-ACCESS  read-write
		STATUS  current
		DESCRIPTION
			"Inhibits OMMP401 QSFP28 Presence Absence Notification
			for the requested port
			-----------------------------
			ommp401InterfaceNumber:
			1 to 4 - CLIENT-1 to CLIENT-4
			-----------------------------
			Value:
			1 - Inhibit
			0 - Do Not Inhibit
			-----------------------------"
	::= { ommp401ConfigurationEntry 121 }

	ommp401OtuLossOfSignalAlarmInhibit  OBJECT-TYPE
		SYNTAX  INTEGER
		MAX-ACCESS  read-write
		STATUS  current
		DESCRIPTION
			"Inhibits OMMP401 OTU Loss Of Signal Alarm
			for the requested port
			-----------------------------
			ommp401InterfaceNumber:
			1 to 4 - CLIENT-1 to CLIENT-4
			-----------------------------
			Value:
			1 - Inhibit
			0 - Do Not Inhibit
			-----------------------------"
	::= { ommp401ConfigurationEntry 122 }

	ommp401OtuLossOfFrameAlarmInhibit  OBJECT-TYPE
		SYNTAX  INTEGER
		MAX-ACCESS  read-write
		STATUS  current
		DESCRIPTION
			"Inhibits OMMP401 OTU Loss Of Frame Alarm
			for the requested port
			-----------------------------
			ommp401InterfaceNumber:
			1 to 4 - CLIENT-1 to CLIENT-4
			-----------------------------
			Value:
			1 - Inhibit
			0 - Do Not Inhibit
			-----------------------------"
	::= { ommp401ConfigurationEntry 123 }

	ommp401OtuOutOfFrameAlarmInhibit  OBJECT-TYPE
		SYNTAX  INTEGER
		MAX-ACCESS  read-write
		STATUS  current
		DESCRIPTION
			"Inhibits OMMP401 OTU Out Of Frame Alarm
			for the requested port
			-----------------------------
			ommp401InterfaceNumber:
			1 to 4 - CLIENT-1 to CLIENT-4
			-----------------------------
			Value:
			1 - Inhibit
			0 - Do Not Inhibit
			-----------------------------"
	::= { ommp401ConfigurationEntry 124 }

	ommp401OtuLossOfMultiFrameAlarmInhibit  OBJECT-TYPE
		SYNTAX  INTEGER
		MAX-ACCESS  read-write
		STATUS  current
		DESCRIPTION
			"Inhibits OMMP401 OTU Loss Of Multi Frame Alarm
			for the requested port
			-----------------------------
			ommp401InterfaceNumber:
			1 to 4 - CLIENT-1 to CLIENT-4
			-----------------------------
			Value:
			1 - Inhibit
			0 - Do Not Inhibit
			-----------------------------"
	::= { ommp401ConfigurationEntry 125 }

	ommp401OtuOutOfMultiFrameAlarmInhibit  OBJECT-TYPE
		SYNTAX  INTEGER
		MAX-ACCESS  read-write
		STATUS  current
		DESCRIPTION
			"Inhibits OMMP401 OTU Out Of Multi Frame Alarm
			for the requested port
			-----------------------------
			ommp401InterfaceNumber:
			1 to 4 - CLIENT-1 to CLIENT-4
			-----------------------------
			Value:
			1 - Inhibit
			0 - Do Not Inhibit
			-----------------------------"
	::= { ommp401ConfigurationEntry 126 }

	ommp401OtuSignalDegradeAlarmInhibit  OBJECT-TYPE
		SYNTAX  INTEGER
		MAX-ACCESS  read-write
		STATUS  current
		DESCRIPTION
			"Inhibits OMMP401 OTU Signal Degrade Alarm
			for the requested port
			-----------------------------
			ommp401InterfaceNumber:
			1 to 4 - CLIENT-1 to CLIENT-4
			-----------------------------
			Value:
			1 - Inhibit
			0 - Do Not Inhibit
			-----------------------------"
	::= { ommp401ConfigurationEntry 128 }

	ommp401OtuAlarmIndicationSignalAlarmInhibit  OBJECT-TYPE
		SYNTAX  INTEGER
		MAX-ACCESS  read-write
		STATUS  current
		DESCRIPTION
			"Inhibits OMMP401 OTU Alarm Indication Signal Alarm
			for the requested port
			-----------------------------
			ommp401InterfaceNumber:
			1 to 4 - CLIENT-1 to CLIENT-4
			-----------------------------
			Value:
			1 - Inhibit
			0 - Do Not Inhibit
			-----------------------------"
	::= { ommp401ConfigurationEntry 129 }

	ommp401OtuIncomingAlignmentErrorAlarmInhibit  OBJECT-TYPE
		SYNTAX  INTEGER
		MAX-ACCESS  read-write
		STATUS  current
		DESCRIPTION
			"Inhibits OMMP401 OTU Incoming Alignment Error Alarm
			for the requested port
			-----------------------------
			ommp401InterfaceNumber:
			1 to 4 - CLIENT-1 to CLIENT-4
			-----------------------------
			Value:
			1 - Inhibit
			0 - Do Not Inhibit
			-----------------------------"
	::= { ommp401ConfigurationEntry 130 }

	ommp401OtuTrailTraceIdentifierMismatchAlarmInhibit  OBJECT-TYPE
		SYNTAX  INTEGER
		MAX-ACCESS  read-write
		STATUS  current
		DESCRIPTION
			"Inhibits OMMP401 OTU Sapi Trace Identifier Mismatch Alarm
			for the requested port
			-----------------------------
			ommp401InterfaceNumber:
			1 to 4 - CLIENT-1 to CLIENT-4
			-----------------------------
			Value:
			1 - Inhibit
			0 - Do Not Inhibit
			-----------------------------"
	::= { ommp401ConfigurationEntry 131 }
	
	ommp401OtuBackwardIncomingAlignmentErrorAlarmInhibit  OBJECT-TYPE
		SYNTAX  INTEGER
		MAX-ACCESS  read-write
		STATUS  current
		DESCRIPTION
			"Inhibits OMMP401 OTU Backward Incoming Alignment Error Alarm
			for the requested port
			-----------------------------
			ommp401InterfaceNumber:
			1 to 4 - CLIENT-1 to CLIENT-4
			-----------------------------
			Value:
			1 - Inhibit
			0 - Do Not Inhibit
			-----------------------------"
	::= { ommp401ConfigurationEntry 132 }

	ommp401OtuBackwardDefectIndicationAlarmInhibit  OBJECT-TYPE
		SYNTAX  INTEGER
		MAX-ACCESS  read-write
		STATUS  current
		DESCRIPTION
			"Inhibits OMMP401 OTU Backward Defect Indication Alarm
			for the requested port
			-----------------------------
			ommp401InterfaceNumber:
			1 to 4 - CLIENT-1 to CLIENT-4
			-----------------------------
			Value:
			1 - Inhibit
			0 - Do Not Inhibit
			-----------------------------"
	::= { ommp401ConfigurationEntry 133 }

	ommp401OduSignalDegradeAlarmInhibit  OBJECT-TYPE
		SYNTAX  INTEGER
		MAX-ACCESS  read-write
		STATUS  current
		DESCRIPTION
			"Inhibits OMMP401 ODU Signal Degrade Alarm
			for the requested port
			-----------------------------
			ommp401InterfaceNumber:
			1 to 4 - CLIENT-1 to CLIENT-4
			-----------------------------
			Value:
			1 - Inhibit
			0 - Do Not Inhibit
			-----------------------------"
	::= { ommp401ConfigurationEntry 135 }

	ommp401OduAlarmIndicationSignalAlarmInhibit  OBJECT-TYPE
		SYNTAX  INTEGER
		MAX-ACCESS  read-write
		STATUS  current
		DESCRIPTION
			"Inhibits OMMP401 ODU Alarm Indication Signal Alarm
			for the requested port
			-----------------------------
			ommp401InterfaceNumber:
			1 to 4 - CLIENT-1 to CLIENT-4
			-----------------------------
			Value:
			1 - Inhibit
			0 - Do Not Inhibit
			-----------------------------"
	::= { ommp401ConfigurationEntry 136 }

	ommp401OduTrailTraceIdentifierMismatchAlarmInhibit  OBJECT-TYPE
		SYNTAX  INTEGER
		MAX-ACCESS  read-write
		STATUS  current
		DESCRIPTION
			"Inhibits OMMP401 OTU Sapi Trace Identifier Mismatch Alarm
			for the requested port
			-----------------------------
			ommp401InterfaceNumber:
			1 to 4 - CLIENT-1 to CLIENT-4
			-----------------------------
			Value:
			1 - Inhibit
			0 - Do Not Inhibit
			-----------------------------"
	::= { ommp401ConfigurationEntry 137 }
	
	ommp401OduLockedDefectAlarmInhibit  OBJECT-TYPE
		SYNTAX  INTEGER
		MAX-ACCESS  read-write
		STATUS  current
		DESCRIPTION
			"Inhibits OMMP401 ODU Locked Defect Alarm
			for the requested port
			-----------------------------
			ommp401InterfaceNumber:
			1 to 4 - CLIENT-1 to CLIENT-4
			-----------------------------
			Value:
			1 - Inhibit
			0 - Do Not Inhibit
			-----------------------------"
	::= { ommp401ConfigurationEntry 138 }

	ommp401OduOpenConnectionIndicationAlarmInhibit  OBJECT-TYPE
		SYNTAX  INTEGER
		MAX-ACCESS  read-write
		STATUS  current
		DESCRIPTION
			"Inhibits OMMP401 ODU Open Connection Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 139 }

	ommp401OduBackwardDefectIndicationAlarmInhibit  OBJECT-TYPE
		SYNTAX  INTEGER
		MAX-ACCESS  read-write
		STATUS  current
		DESCRIPTION
			"Inhibits OMMP401 ODU Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 140 }

	ommp401OduTcm1BackwardDefectIndicationAlarmInhibit  OBJECT-TYPE
		SYNTAX  INTEGER
		MAX-ACCESS  read-write
		STATUS  current
		DESCRIPTION
			"Inhibits OMMP401 ODU TCM1 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 147 }

	ommp401OduTcm2BackwardDefectIndicationAlarmInhibit  OBJECT-TYPE
		SYNTAX  INTEGER
		MAX-ACCESS  read-write
		STATUS  current
		DESCRIPTION
			"Inhibits OMMP401 ODU TCM2 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 148 }

	ommp401OduTcm3BackwardDefectIndicationAlarmInhibit  OBJECT-TYPE
		SYNTAX  INTEGER
		MAX-ACCESS  read-write
		STATUS  current
		DESCRIPTION
			"Inhibits OMMP401 ODU TCM3 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 149 }

	ommp401OduTcm4BackwardDefectIndicationAlarmInhibit  OBJECT-TYPE
		SYNTAX  INTEGER
		MAX-ACCESS  read-write
		STATUS  current
		DESCRIPTION
			"Inhibits OMMP401 ODU TCM4 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 150 }

	ommp401OduTcm5BackwardDefectIndicationAlarmInhibit  OBJECT-TYPE
		SYNTAX  INTEGER
		MAX-ACCESS  read-write
		STATUS  current
		DESCRIPTION
			"Inhibits OMMP401 ODU TCM5 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 151 }

	ommp401OduTcm6BackwardDefectIndicationAlarmInhibit  OBJECT-TYPE
		SYNTAX  INTEGER
		MAX-ACCESS  read-write
		STATUS  current
		DESCRIPTION
			"Inhibits OMMP401 ODU TCM6 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 152 }

	ommp401OduTcm1LossOfTandemConnectionAlarmInhibit  OBJECT-TYPE
		SYNTAX  INTEGER
		MAX-ACCESS  read-write
		STATUS  current
		DESCRIPTION
			"Inhibits OMMP401 ODU TCM1 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 159 }

	ommp401OduTcm2LossOfTandemConnectionAlarmInhibit  OBJECT-TYPE
		SYNTAX  INTEGER
		MAX-ACCESS  read-write
		STATUS  current
		DESCRIPTION
			"Inhibits OMMP401 ODU TCM2 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 160 }

	ommp401OduTcm3LossOfTandemConnectionAlarmInhibit  OBJECT-TYPE
		SYNTAX  INTEGER
		MAX-ACCESS  read-write
		STATUS  current
		DESCRIPTION
			"Inhibits OMMP401 ODU TCM3 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 161 }

	ommp401OduTcm4LossOfTandemConnectionAlarmInhibit  OBJECT-TYPE
		SYNTAX  INTEGER
		MAX-ACCESS  read-write
		STATUS  current
		DESCRIPTION
			"Inhibits OMMP401 ODU TCM4 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 162 }

	ommp401OduTcm5LossOfTandemConnectionAlarmInhibit  OBJECT-TYPE
		SYNTAX  INTEGER
		MAX-ACCESS  read-write
		STATUS  current
		DESCRIPTION
			"Inhibits OMMP401 ODU TCM5 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 163 }

	ommp401OduTcm6LossOfTandemConnectionAlarmInhibit  OBJECT-TYPE
		SYNTAX  INTEGER
		MAX-ACCESS  read-write
		STATUS  current
		DESCRIPTION
			"Inhibits OMMP401 ODU TCM6 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 164 }

	ommp401OduTcm1BackwardIncomingAlignmentErrorAlarmInhibit  OBJECT-TYPE
		SYNTAX  INTEGER
		MAX-ACCESS  read-write
		STATUS  current
		DESCRIPTION
			"Inhibits OMMP401 ODU TCM1 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 165 }

	ommp401OduTcm2BackwardIncomingAlignmentErrorAlarmInhibit  OBJECT-TYPE
		SYNTAX  INTEGER
		MAX-ACCESS  read-write
		STATUS  current
		DESCRIPTION
			"Inhibits OMMP401 ODU TCM2 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 166 }

	ommp401OduTcm3BackwardIncomingAlignmentErrorAlarmInhibit  OBJECT-TYPE
		SYNTAX  INTEGER
		MAX-ACCESS  read-write
		STATUS  current
		DESCRIPTION
			"Inhibits OMMP401 ODU TCM3 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 167 }

	ommp401OduTcm4BackwardIncomingAlignmentErrorAlarmInhibit  OBJECT-TYPE
		SYNTAX  INTEGER
		MAX-ACCESS  read-write
		STATUS  current
		DESCRIPTION
			"Inhibits OMMP401 ODU TCM4 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 168 }

	ommp401OduTcm5BackwardIncomingAlignmentErrorAlarmInhibit  OBJECT-TYPE
		SYNTAX  INTEGER
		MAX-ACCESS  read-write
		STATUS  current
		DESCRIPTION
			"Inhibits OMMP401 ODU TCM5 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 169 }

	ommp401OduTcm6BackwardIncomingAlignmentErrorAlarmInhibit  OBJECT-TYPE
		SYNTAX  INTEGER
		MAX-ACCESS  read-write
		STATUS  current
		DESCRIPTION
			"Inhibits OMMP401 ODU TCM6 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 170 }

	ommp401OpuPayloadMismatchAlarmInhibit  OBJECT-TYPE
		SYNTAX  INTEGER
		MAX-ACCESS  read-write
		STATUS  current	
		DESCRIPTION
			"Inhibits OMMP401 OPU Payload Mismatch Alarm
			for the requested port
			-----------------------------
			ommp401InterfaceNumber:
			1 to 4 - CLIENT-1 to CLIENT-4
			-----------------------------
			Value:
			1 - Inhibit
			0 - Do Not Inhibit
			-----------------------------"
	::= { ommp401ConfigurationEntry 177 }

	ommp401EthernetLossOfSignalAlarmInhibit  OBJECT-TYPE
		SYNTAX  INTEGER
		MAX-ACCESS  read-write
		STATUS  current
		DESCRIPTION
			"Inhibits OMMP401 Ethernet Loss Of Signal Alarm
			for the requested port
			-----------------------------
			ommp401InterfaceNumber:
			1 to 4 - CLIENT-1 to CLIENT-4
			-----------------------------
			Value:
			1 - Inhibit
			0 - Do Not Inhibit
			-----------------------------"
	::= { ommp401ConfigurationEntry 178 }

	ommp401EthernetIngressRemoteFaultAlarmInhibit  OBJECT-TYPE
		SYNTAX  INTEGER
		MAX-ACCESS  read-write
		STATUS  current
		DESCRIPTION
			"Inhibits OMMP401 Ethernet Ingress Remote Fault 
			Alarm for the requested port
			-----------------------------
			ommp401InterfaceNumber:
			1 to 4 - CLIENT-1 to CLIENT-4
			-----------------------------
			Value:
			1 - Inhibit
			0 - Do Not Inhibit
			-----------------------------"
	::= { ommp401ConfigurationEntry 179 }

	ommp401EthernetIngressPcsErrorBlocksDetectedAlarmInhibit  OBJECT-TYPE
		SYNTAX  INTEGER
		MAX-ACCESS  read-write
		STATUS  current
		DESCRIPTION
			"Inhibits OMMP401 Ethernet Ingress Pcs Error Blocks Detected Alarm
			for the requested port
			-----------------------------
			ommp401InterfaceNumber:
			1 to 4 - CLIENT-1 to CLIENT-4
			-----------------------------
			Value:
			1 - Inhibit
			0 - Do Not Inhibit
			-----------------------------"
	::= { ommp401ConfigurationEntry 180 }

	ommp401EthernetIngressPcsBipErrorsDetectedAlarmInhibit  OBJECT-TYPE
		SYNTAX  INTEGER
		MAX-ACCESS  read-write
		STATUS  current
		DESCRIPTION
			"Inhibits OMMP401 Ethernet Ingress Pcs Bip Errors Detected Alarm
			for the requested port
			-----------------------------
			ommp401InterfaceNumber:
			1 to 4 - CLIENT-1 to CLIENT-4
			-----------------------------
			Value:
			1 - Inhibit
			0 - Do Not Inhibit
			-----------------------------"
	::= { ommp401ConfigurationEntry 181 }

	ommp401EthernetIngressOpuClientServerFailIndicationAlarmInhibit  OBJECT-TYPE
		SYNTAX  INTEGER
		MAX-ACCESS  read-write
		STATUS  current
		DESCRIPTION
			"Inhibits OMMP401 Ethernet Ingress Opu Client Server Fail Indication Alarm
			for the requested port
			-----------------------------
			ommp401InterfaceNumber:
			1 to 4 - CLIENT-1 to CLIENT-4
			-----------------------------
			Value:
			1 - Inhibit
			0 - Do Not Inhibit
			-----------------------------"
	::= { ommp401ConfigurationEntry 182 }

	ommp401EthernetIngressLocalFaultAlarmInhibit  OBJECT-TYPE
		SYNTAX  INTEGER
		MAX-ACCESS  read-write
		STATUS  current
		DESCRIPTION
			"Inhibits OMMP401 Ethernet Ingress Local Fault Alarm
			for the requested port
			-----------------------------
			ommp401InterfaceNumber:
			1 to 4 - CLIENT-1 to CLIENT-4
			-----------------------------
			Value:
			1 - Inhibit
			0 - Do Not Inhibit
			-----------------------------"
	::= { ommp401ConfigurationEntry 183 }

	ommp401EthernetIngressLossOfAlignmentAlarmInhibit  OBJECT-TYPE
		SYNTAX  INTEGER
		MAX-ACCESS  read-write
		STATUS  current
		DESCRIPTION
			"Inhibits OMMP401 Ethernet Ingress Loss Of Alignment 
			Alarm for the requested port
			-----------------------------
			ommp401InterfaceNumber:
			1 to 4 - CLIENT-1 to CLIENT-4
			-----------------------------
			Value:
			1 - Inhibit
			0 - Do Not Inhibit
			-----------------------------"
	::= { ommp401ConfigurationEntry 184 }

	ommp401EthernetIngressLossOfAlignmentMarkerLockAlarmInhibit  OBJECT-TYPE
		SYNTAX  INTEGER
		MAX-ACCESS  read-write
		STATUS  current
		DESCRIPTION
			"Inhibits OMMP401 Ethernet Ingress Loss Of Alignment Marker Alarm
			for the requested port
			-----------------------------
			ommp401InterfaceNumber:
			1 to 4 - CLIENT-1 to CLIENT-4
			-----------------------------
			Value:
			1 - Inhibit
			0 - Do Not Inhibit
			-----------------------------"
	::= { ommp401ConfigurationEntry 185 }

	ommp401EthernetIngressLossOfBlockLockAlarmInhibit  OBJECT-TYPE
		SYNTAX  INTEGER
		MAX-ACCESS  read-write
		STATUS  current
		DESCRIPTION
			"Inhibits OMMP401 Ethernet Ingress Loss Of Block Lock Alarm
			for the requested port
			-----------------------------
			ommp401InterfaceNumber:
			1 to 4 - CLIENT-1 to CLIENT-4
			-----------------------------
			Value:
			1 - Inhibit
			0 - Do Not Inhibit
			-----------------------------"
	::= { ommp401ConfigurationEntry 186 }

	ommp401EthernetEgressRemoteFaultAlarmInhibit  OBJECT-TYPE
		SYNTAX  INTEGER
		MAX-ACCESS  read-write
		STATUS  current
		DESCRIPTION
			"Inhibits OMMP401 Ethernet Egress Remote Fault Alarm
			for the requested port
			-----------------------------
			ommp401InterfaceNumber:
			1 to 4 - CLIENT-1 to CLIENT-4
			-----------------------------
			Value:
			1 - Inhibit
			0 - Do Not Inhibit
			-----------------------------"
	::= { ommp401ConfigurationEntry 187 }

	ommp401EthernetEgressPcsErrorBlocksDetectedAlarmInhibit  OBJECT-TYPE
		SYNTAX  INTEGER
		MAX-ACCESS  read-write
		STATUS  current
		DESCRIPTION
			"Inhibits OMMP401 Ethernet Egress Pcs Error Blocks Detected Alarm
			for the requested port
			-----------------------------
			ommp401InterfaceNumber:
			1 to 4 - CLIENT-1 to CLIENT-4
			-----------------------------
			Value:
			1 - Inhibit
			0 - Do Not Inhibit
			-----------------------------"
	::= { ommp401ConfigurationEntry 188 }

	ommp401EthernetEgressPcsBipErrorsDetectedAlarmInhibit  OBJECT-TYPE
		SYNTAX  INTEGER
		MAX-ACCESS  read-write
		STATUS  current
		DESCRIPTION
			"Inhibits OMMP401 Ethernet Egress Pcs Bip Errors Detected Alarm
			for the requested port
			-----------------------------
			ommp401InterfaceNumber:
			1 to 4 - CLIENT-1 to CLIENT-4
			-----------------------------
			Value:
			1 - Inhibit
			0 - Do Not Inhibit
			-----------------------------"
	::= { ommp401ConfigurationEntry 189 }

	ommp401EthernetEgressHighBerAlarmInhibit  OBJECT-TYPE
		SYNTAX  INTEGER
		MAX-ACCESS  read-write
		STATUS  current
		DESCRIPTION
			"Inhibits OMMP401 Ethernet Egress High BER Alarm
			for the requested port
			-----------------------------
			ommp401InterfaceNumber:
			1 to 4 - CLIENT-1 to CLIENT-4
			-----------------------------
			Value:
			1 - Inhibit
			0 - Do Not Inhibit
			-----------------------------"
	::= { ommp401ConfigurationEntry 190 }

	ommp401EthernetEgressLocalFaultAlarmInhibit  OBJECT-TYPE
		SYNTAX  INTEGER
		MAX-ACCESS  read-write
		STATUS  current
		DESCRIPTION
			"Inhibits OMMP401 Ethernet Egress Local Fault Alarm
			for the requested port
			-----------------------------
			ommp401InterfaceNumber:
			1 to 4 - CLIENT-1 to CLIENT-4
			-----------------------------
			Value:
			1 - Inhibit
			0 - Do Not Inhibit
			-----------------------------"
	::= { ommp401ConfigurationEntry 191 }

	ommp401EthernetEgressLossOfAlignmentAlarmInhibit  OBJECT-TYPE
		SYNTAX  INTEGER
		MAX-ACCESS  read-write
		STATUS  current
		DESCRIPTION
			"Inhibits OMMP401 Ethernet Egress Loss Of Alignment 
			Alarm for the requested port
			-----------------------------
			ommp401InterfaceNumber:
			1 to 4 - CLIENT-1 to CLIENT-4
			-----------------------------
			Value:
			1 - Inhibit
			0 - Do Not Inhibit
			-----------------------------"
	::= { ommp401ConfigurationEntry 192 }

	ommp401EthernetEgressLossOfAlignmentMarkerLockAlarmInhibit  OBJECT-TYPE
		SYNTAX  INTEGER
		MAX-ACCESS  read-write
		STATUS  current
		DESCRIPTION
			"Inhibits OMMP401 Ethernet Egress Loss Of Alignment Marker Alarm
			for the requested port
			-----------------------------
			ommp401InterfaceNumber:
			1 to 4 - CLIENT-1 to CLIENT-4
			-----------------------------
			Value:
			1 - Inhibit
			0 - Do Not Inhibit
			-----------------------------"
	::= { ommp401ConfigurationEntry 193 }

	ommp401EthernetEgressLossOfBlockLockAlarmInhibit  OBJECT-TYPE
		SYNTAX  INTEGER
		MAX-ACCESS  read-write
		STATUS  current
		DESCRIPTION
			"Inhibits OMMP401 Ethernet Egress Loss Of Block Lock Alarm
			for the requested port
			-----------------------------
			ommp401InterfaceNumber:
			1 to 4 - CLIENT-1 to CLIENT-4
			-----------------------------
			Value:
			1 - Inhibit
			0 - Do Not Inhibit
			-----------------------------"
	::= { ommp401ConfigurationEntry 194 }

	ommp401Cfp2InputPowerFailureAlarmSeverity OBJECT-TYPE
		SYNTAX  DisplayString
		MAX-ACCESS  read-write
		STATUS  current
		DESCRIPTION
			"Set or Get the alarm severity level of the
			OMMP401 CFP2 Input Power Failure Alarm   
			for requested port
			-----------------------------
			ommp401InterfaceNumber:
			5 - LINE-1
			-----------------------------
			Value:
			critical
			major
			minor
			deferred
			---------------------------"
	::= { ommp401ConfigurationEntry 195 }

	ommp401Cfp2OutputPowerFailureAlarmSeverity OBJECT-TYPE
		SYNTAX  DisplayString
		MAX-ACCESS  read-write
		STATUS  current
		DESCRIPTION
			"Set or Get the alarm severity level of the
			OMMP401 CFP2 Output Power Failure Alarm   
			for requested port
			-----------------------------
			ommp401InterfaceNumber:
			5 - LINE-1
			-----------------------------
			Value:
			critical
			major
			minor
			deferred
			---------------------------"
	::= { ommp401ConfigurationEntry 196 }

	ommp401Cfp2HighTemperatureAlarmSeverity OBJECT-TYPE
		SYNTAX  DisplayString
		MAX-ACCESS  read-write
		STATUS  current
		DESCRIPTION
			"Set or Get the alarm severity level of the
			OMMP401 CFP2 High Temperature Alarm   
			for requested port
			-----------------------------
			ommp401InterfaceNumber:
			5 - LINE-1
			-----------------------------
			Value:
			critical
			major
			minor
			deferred
			---------------------------"
	::= { ommp401ConfigurationEntry 197 }

	ommp401Cfp2LowTemperatureAlarmSeverity OBJECT-TYPE
		SYNTAX  DisplayString
		MAX-ACCESS  read-write
		STATUS  current
		DESCRIPTION
			"Set or Get the alarm severity level of the
			OMMP401 CFP2 Low Temperature Alarm   
			for requested port
			-----------------------------
			ommp401InterfaceNumber:
			5 - LINE-1
			-----------------------------
			Value:
			critical
			major
			minor
			deferred
			---------------------------"
	::= { ommp401ConfigurationEntry 198 }

	ommp401Cfp2HighTemperatureWarningSeverity OBJECT-TYPE
		SYNTAX  DisplayString
		MAX-ACCESS  read-write
		STATUS  current
		DESCRIPTION
			"Set or Get the alarm severity level of the
			OMMP401 CFP2 High Temperature Warning   
			for requested port
			-----------------------------
			ommp401InterfaceNumber:
			5 - LINE-1
			-----------------------------
			Value:
			critical
			major
			minor
			deferred
			---------------------------"
	::= { ommp401ConfigurationEntry 199 }

	ommp401Cfp2LowTemperatureWarningSeverity OBJECT-TYPE
		SYNTAX  DisplayString
		MAX-ACCESS  read-write
		STATUS  current
		DESCRIPTION
			"Set or Get the alarm severity level of the
			OMMP401 CFP2 Low Temperature Warning   
			for requested port
			-----------------------------
			ommp401InterfaceNumber:
			5 - LINE-1
			-----------------------------
			Value:
			critical
			major
			minor
			deferred
			---------------------------"
	::= { ommp401ConfigurationEntry 200 }

	ommp401Cfp2InputHighPowerAlarmSeverity OBJECT-TYPE
		SYNTAX  DisplayString
		MAX-ACCESS  read-write
		STATUS  current
		DESCRIPTION
			"Set or Get the alarm severity level of the
			OMMP401 CFP2 Input High Power Alarm   
			for requested port
			-----------------------------
			ommp401InterfaceNumber:
			5 - LINE-1
			-----------------------------
			Value:
			critical
			major
			minor
			deferred
			---------------------------"
	::= { ommp401ConfigurationEntry 201 }

	ommp401Cfp2InputLowPowerAlarmSeverity OBJECT-TYPE
		SYNTAX  DisplayString
		MAX-ACCESS  read-write
		STATUS  current
		DESCRIPTION
			"Set or Get the alarm severity level of the
			OMMP401 CFP2 Input Low Power Alarm   
			for requested port
			-----------------------------
			ommp401InterfaceNumber:
			5 - LINE-1
			-----------------------------
			Value:
			critical
			major
			minor
			deferred
			---------------------------"
	::= { ommp401ConfigurationEntry 202 }

	ommp401Cfp2InputHighPowerWarningSeverity OBJECT-TYPE
		SYNTAX  DisplayString
		MAX-ACCESS  read-write
		STATUS  current
		DESCRIPTION
			"Set or Get the alarm severity level of the
			OMMP401 CFP2 Input High Power Warning   
			for requested port
			-----------------------------
			ommp401InterfaceNumber:
			5 - LINE-1
			-----------------------------
			Value:
			critical
			major
			minor
			deferred
			---------------------------"
	::= { ommp401ConfigurationEntry 203 }

	ommp401Cfp2InputLowPowerWarningSeverity OBJECT-TYPE
		SYNTAX  DisplayString
		MAX-ACCESS  read-write
		STATUS  current
		DESCRIPTION
			"Set or Get the alarm severity level of the
			OMMP401 CFP2 Input Low Power Warning   
			for requested port
			-----------------------------
			ommp401InterfaceNumber:
			5 - LINE-1
			-----------------------------
			Value:
			critical
			major
			minor
			deferred
			---------------------------"
	::= { ommp401ConfigurationEntry 204 }

	ommp401Cfp2OutputHighPowerAlarmSeverity OBJECT-TYPE
		SYNTAX  DisplayString
		MAX-ACCESS  read-write
		STATUS  current
		DESCRIPTION
			"Set or Get the alarm severity level of the
			OMMP401 CFP2 Output High Power Alarm   
			for requested port
			-----------------------------
			ommp401InterfaceNumber:
			5 - LINE-1
			-----------------------------
			Value:
			critical
			major
			minor
			deferred
			---------------------------"
	::= { ommp401ConfigurationEntry 205 }

	ommp401Cfp2OutputLowPowerAlarmSeverity OBJECT-TYPE
		SYNTAX  DisplayString
		MAX-ACCESS  read-write
		STATUS  current
		DESCRIPTION
			"Set or Get the alarm severity level of the
			OMMP401 CFP2 Output Low Power Alarm   
			for requested port
			-----------------------------
			ommp401InterfaceNumber:
			5 - LINE-1
			-----------------------------
			Value:
			critical
			major
			minor
			deferred
			---------------------------"
	::= { ommp401ConfigurationEntry 206 }

	ommp401Cfp2OutputHighPowerWarningSeverity OBJECT-TYPE
		SYNTAX  DisplayString
		MAX-ACCESS  read-write
		STATUS  current
		DESCRIPTION
			"Set or Get the alarm severity level of the
			OMMP401 CFP2 Output High Power Warning   
			for requested port
			-----------------------------
			ommp401InterfaceNumber:
			5 - LINE-1
			-----------------------------
			Value:
			critical
			major
			minor
			deferred
			---------------------------"
	::= { ommp401ConfigurationEntry 207 }

	ommp401Cfp2OutputLowPowerWarningSeverity OBJECT-TYPE
		SYNTAX  DisplayString
		MAX-ACCESS  read-write
		STATUS  current
		DESCRIPTION
			"Set or Get the alarm severity level of the
			OMMP401 CFP2 Output Low Power Warning   
			for requested port
			-----------------------------
			ommp401InterfaceNumber:
			5 - LINE-1
			-----------------------------
			Value:
			critical
			major
			minor
			deferred
			---------------------------"
	::= { ommp401ConfigurationEntry 208 }

	ommp401Cfp2HighSupplyVoltageAlarmSeverity OBJECT-TYPE
		SYNTAX  DisplayString
		MAX-ACCESS  read-write
		STATUS  current
		DESCRIPTION
			"Set or Get the alarm severity level of the
			OMMP401 CFP2 High Supply Voltage Alarm   
			for requested port
			-----------------------------
			ommp401InterfaceNumber:
			5 - LINE-1
			-----------------------------
			Value:
			critical
			major
			minor
			deferred
			---------------------------"
	::= { ommp401ConfigurationEntry 209 }

	ommp401Cfp2LowSupplyVoltageAlarmSeverity OBJECT-TYPE
		SYNTAX  DisplayString
		MAX-ACCESS  read-write
		STATUS  current
		DESCRIPTION
			"Set or Get the alarm severity level of the
			OMMP401 CFP2 Low Supply Voltage Alarm   
			for requested port
			-----------------------------
			ommp401InterfaceNumber:
			5 - LINE-1
			-----------------------------
			Value:
			critical
			major
			minor
			deferred
			---------------------------"
	::= { ommp401ConfigurationEntry 210 }

	ommp401Cfp2HighSupplyVoltageWarningSeverity OBJECT-TYPE
		SYNTAX  DisplayString
		MAX-ACCESS  read-write
		STATUS  current
		DESCRIPTION
			"Set or Get the alarm severity level of the
			OMMP401 CFP2 High Supply Voltage Warning   
			for requested port
			-----------------------------
			ommp401InterfaceNumber:
			5 - LINE-1
			-----------------------------
			Value:
			critical
			major
			minor
			deferred
			---------------------------"
	::= { ommp401ConfigurationEntry 211 }

	ommp401Cfp2LowSupplyVoltageWarningSeverity OBJECT-TYPE
		SYNTAX  DisplayString
		MAX-ACCESS  read-write
		STATUS  current
		DESCRIPTION
			"Set or Get the alarm severity level of the
			OMMP401 CFP2 Low Supply Voltage Warning   
			for requested port
			-----------------------------
			ommp401InterfaceNumber:
			5 - LINE-1
			-----------------------------
			Value:
			critical
			major
			minor
			deferred
			---------------------------"
	::= { ommp401ConfigurationEntry 212 }

	ommp401Cfp2PresenceAbsenceNotificationSeverity OBJECT-TYPE
		SYNTAX  DisplayString
		MAX-ACCESS  read-write
		STATUS  current
		DESCRIPTION
			"Set or Get the alarm severity level of the
			OMMP401 CFP2 Presence Absence Notification   
			for requested port
			-----------------------------
			ommp401InterfaceNumber:
			5 - LINE-1
			-----------------------------
			Value:
			critical
			major
			minor
			deferred
			---------------------------"
	::= { ommp401ConfigurationEntry 213 }

	ommp401Qsfp28InputPowerFailureAlarmSeverity OBJECT-TYPE
		SYNTAX  DisplayString
		MAX-ACCESS  read-write
		STATUS  current
		DESCRIPTION
			"Set or Get the alarm severity level of the
			OMMP401 QSFP28 Input Power Failure Alarm   
			for requested port
			-----------------------------
			ommp401InterfaceNumber:
			1 to 4 - CLIENT-1 to CLIENT-4
			-----------------------------
			Value:
			critical
			major
			minor
			deferred
			---------------------------"
	::= { ommp401ConfigurationEntry 214 }

	ommp401Qsfp28OutputPowerFailureAlarmSeverity OBJECT-TYPE
		SYNTAX  DisplayString
		MAX-ACCESS  read-write
		STATUS  current
		DESCRIPTION
			"Set or Get the alarm severity level of the
			OMMP401 QSFP28 Output Power Failure Alarm   
			for requested port
			-----------------------------
			ommp401InterfaceNumber:
			1 to 4 - CLIENT-1 to CLIENT-4
			-----------------------------
			Value:
			critical
			major
			minor
			deferred
			---------------------------"
	::= { ommp401ConfigurationEntry 215 }

	ommp401Qsfp28HighTemperatureAlarmSeverity OBJECT-TYPE
		SYNTAX  DisplayString
		MAX-ACCESS  read-write
		STATUS  current
		DESCRIPTION
			"Set or Get the alarm severity level of the
			OMMP401 QSFP28 High Temperature Alarm   
			for requested port
			-----------------------------
			ommp401InterfaceNumber:
			1 to 4 - CLIENT-1 to CLIENT-4
			-----------------------------
			Value:
			critical
			major
			minor
			deferred
			---------------------------"
	::= { ommp401ConfigurationEntry 216 }

	ommp401Qsfp28LowTemperatureAlarmSeverity OBJECT-TYPE
		SYNTAX  DisplayString
		MAX-ACCESS  read-write
		STATUS  current
		DESCRIPTION
			"Set or Get the alarm severity level of the
			OMMP401 QSFP28 Low Temperature Alarm   
			for requested port
			-----------------------------
			ommp401InterfaceNumber:
			1 to 4 - CLIENT-1 to CLIENT-4
			-----------------------------
			Value:
			critical
			major
			minor
			deferred
			---------------------------"
	::= { ommp401ConfigurationEntry 217 }

	ommp401Qsfp28HighTemperatureWarningSeverity OBJECT-TYPE
		SYNTAX  DisplayString
		MAX-ACCESS  read-write
		STATUS  current
		DESCRIPTION
			"Set or Get the alarm severity level of the
			OMMP401 QSFP28 High Temperature Warning   
			for requested port
			-----------------------------
			ommp401InterfaceNumber:
			1 to 4 - CLIENT-1 to CLIENT-4
			-----------------------------
			Value:
			critical
			major
			minor
			deferred
			---------------------------"
	::= { ommp401ConfigurationEntry 218 }

	ommp401Qsfp28LowTemperatureWarningSeverity OBJECT-TYPE
		SYNTAX  DisplayString
		MAX-ACCESS  read-write
		STATUS  current
		DESCRIPTION
			"Set or Get the alarm severity level of the
			OMMP401 QSFP28 Low Temperature Warning   
			for requested port
			-----------------------------
			ommp401InterfaceNumber:
			1 to 4 - CLIENT-1 to CLIENT-4
			-----------------------------
			Value:
			critical
			major
			minor
			deferred
			---------------------------"
	::= { ommp401ConfigurationEntry 219 }

	ommp401Qsfp28HighBiasCurrentAlarmSeverity OBJECT-TYPE
		SYNTAX  DisplayString
		MAX-ACCESS  read-write
		STATUS  current
		DESCRIPTION
			"Set or Get the alarm severity level of the
			OMMP401 QSFP28 High Bias Current Alarm   
			for requested port
			-----------------------------
			ommp401InterfaceNumber:
			1 to 4 - CLIENT-1 to CLIENT-4
			-----------------------------
			Value:
			critical
			major
			minor
			deferred
			---------------------------"
	::= { ommp401ConfigurationEntry 220 }

	ommp401Qsfp28LowBiasCurrentAlarmSeverity OBJECT-TYPE
		SYNTAX  DisplayString
		MAX-ACCESS  read-write
		STATUS  current
		DESCRIPTION
			"Set or Get the alarm severity level of the
			OMMP401 QSFP28 Low Bias Current Alarm   
			for requested port
			-----------------------------
			ommp401InterfaceNumber:
			1 to 4 - CLIENT-1 to CLIENT-4
			-----------------------------
			Value:
			critical
			major
			minor
			deferred
			---------------------------"
	::= { ommp401ConfigurationEntry 221 }

	ommp401Qsfp28HighBiasCurrentWarningSeverity OBJECT-TYPE
		SYNTAX  DisplayString
		MAX-ACCESS  read-write
		STATUS  current
		DESCRIPTION
			"Set or Get the alarm severity level of the
			OMMP401 QSFP28 High Bias Current Warning   
			for requested port
			-----------------------------
			ommp401InterfaceNumber:
			1 to 4 - CLIENT-1 to CLIENT-4
			-----------------------------
			Value:
			critical
			major
			minor
			deferred
			---------------------------"
	::= { ommp401ConfigurationEntry 222 }

	ommp401Qsfp28LowBiasCurrentWarningSeverity OBJECT-TYPE
		SYNTAX  DisplayString
		MAX-ACCESS  read-write
		STATUS  current
		DESCRIPTION
			"Set or Get the alarm severity level of the
			OMMP401 QSFP28 Low Bias Current Warning   
			for requested port
			-----------------------------
			ommp401InterfaceNumber:
			1 to 4 - CLIENT-1 to CLIENT-4
			-----------------------------
			Value:
			critical
			major
			minor
			deferred
			---------------------------"
	::= { ommp401ConfigurationEntry 223 }

	ommp401Qsfp28InputHighPowerAlarmSeverity OBJECT-TYPE
		SYNTAX  DisplayString
		MAX-ACCESS  read-write
		STATUS  current
		DESCRIPTION
			"Set or Get the alarm severity level of the
			OMMP401 QSFP28 Input High Power Alarm   
			for requested port
			-----------------------------
			ommp401InterfaceNumber:
			1 to 4 - CLIENT-1 to CLIENT-4
			-----------------------------
			Value:
			critical
			major
			minor
			deferred
			---------------------------"
	::= { ommp401ConfigurationEntry 224 }

	ommp401Qsfp28InputLowPowerAlarmSeverity OBJECT-TYPE
		SYNTAX  DisplayString
		MAX-ACCESS  read-write
		STATUS  current
		DESCRIPTION
			"Set or Get the alarm severity level of the
			OMMP401 QSFP28 Input Low Power Alarm   
			for requested port
			-----------------------------
			ommp401InterfaceNumber:
			1 to 4 - CLIENT-1 to CLIENT-4
			-----------------------------
			Value:
			critical
			major
			minor
			deferred
			---------------------------"
	::= { ommp401ConfigurationEntry 225 }

	ommp401Qsfp28InputHighPowerWarningSeverity OBJECT-TYPE
		SYNTAX  DisplayString
		MAX-ACCESS  read-write
		STATUS  current
		DESCRIPTION
			"Set or Get the alarm severity level of the
			OMMP401 QSFP28 Input High Power Warning   
			for requested port
			-----------------------------
			ommp401InterfaceNumber:
			1 to 4 - CLIENT-1 to CLIENT-4
			-----------------------------
			Value:
			critical
			major
			minor
			deferred
			---------------------------"
	::= { ommp401ConfigurationEntry 226 }

	ommp401Qsfp28InputLowPowerWarningSeverity OBJECT-TYPE
		SYNTAX  DisplayString
		MAX-ACCESS  read-write
		STATUS  current
		DESCRIPTION
			"Set or Get the alarm severity level of the
			OMMP401 QSFP28 Input Low Power Warning   
			for requested port
			-----------------------------
			ommp401InterfaceNumber:
			1 to 4 - CLIENT-1 to CLIENT-4
			-----------------------------
			Value:
			critical
			major
			minor
			deferred
			---------------------------"
	::= { ommp401ConfigurationEntry 227 }

	ommp401Qsfp28OutputHighPowerAlarmSeverity OBJECT-TYPE
		SYNTAX  DisplayString
		MAX-ACCESS  read-write
		STATUS  current
		DESCRIPTION
			"Set or Get the alarm severity level of the
			OMMP401 QSFP28 Output High Power Alarm   
			for requested port
			-----------------------------
			ommp401InterfaceNumber:
			1 to 4 - CLIENT-1 to CLIENT-4
			-----------------------------
			Value:
			critical
			major
			minor
			deferred
			---------------------------"
	::= { ommp401ConfigurationEntry 228 }

	ommp401Qsfp28OutputLowPowerAlarmSeverity OBJECT-TYPE
		SYNTAX  DisplayString
		MAX-ACCESS  read-write
		STATUS  current
		DESCRIPTION
			"Set or Get the alarm severity level of the
			OMMP401 QSFP28 Output Low Power Alarm   
			for requested port
			-----------------------------
			ommp401InterfaceNumber:
			1 to 4 - CLIENT-1 to CLIENT-4
			-----------------------------
			Value:
			critical
			major
			minor
			deferred
			---------------------------"
	::= { ommp401ConfigurationEntry 229 }

	ommp401Qsfp28OutputHighPowerWarningSeverity OBJECT-TYPE
		SYNTAX  DisplayString
		MAX-ACCESS  read-write
		STATUS  current
		DESCRIPTION
			"Set or Get the alarm severity level of the
			OMMP401 QSFP28 Output High Power Warning   
			for requested port
			-----------------------------
			ommp401InterfaceNumber:
			1 to 4 - CLIENT-1 to CLIENT-4
			-----------------------------
			Value:
			critical
			major
			minor
			deferred
			---------------------------"
	::= { ommp401ConfigurationEntry 230 }

	ommp401Qsfp28OutputLowPowerWarningSeverity OBJECT-TYPE
		SYNTAX  DisplayString
		MAX-ACCESS  read-write
		STATUS  current
		DESCRIPTION
			"Set or Get the alarm severity level of the
			OMMP401 QSFP28 Output Low Power Warning   
			for requested port
			-----------------------------
			ommp401InterfaceNumber:
			1 to 4 - CLIENT-1 to CLIENT-4
			-----------------------------
			Value:
			critical
			major
			minor
			deferred
			---------------------------"
	::= { ommp401ConfigurationEntry 231 }

	ommp401Qsfp28HighSupplyVoltageAlarmSeverity OBJECT-TYPE
		SYNTAX  DisplayString
		MAX-ACCESS  read-write
		STATUS  current
		DESCRIPTION
			"Set or Get the alarm severity level of the
			OMMP401 QSFP28 High Supply Voltage Alarm   
			for requested port
			-----------------------------
			ommp401InterfaceNumber:
			1 to 4 - CLIENT-1 to CLIENT-4
			-----------------------------
			Value:
			critical
			major
			minor
			deferred
			---------------------------"
	::= { ommp401ConfigurationEntry 232 }

	ommp401Qsfp28LowSupplyVoltageAlarmSeverity OBJECT-TYPE
		SYNTAX  DisplayString
		MAX-ACCESS  read-write
		STATUS  current
		DESCRIPTION
			"Set or Get the alarm severity level of the
			OMMP401 QSFP28 Low Supply Voltage Alarm   
			for requested port
			-----------------------------
			ommp401InterfaceNumber:
			1 to 4 - CLIENT-1 to CLIENT-4
			-----------------------------
			Value:
			critical
			major
			minor
			deferred
			---------------------------"
	::= { ommp401ConfigurationEntry 233 }

	ommp401Qsfp28HighSupplyVoltageWarningSeverity OBJECT-TYPE
		SYNTAX  DisplayString
		MAX-ACCESS  read-write
		STATUS  current
		DESCRIPTION
			"Set or Get the alarm severity level of the
			OMMP401 QSFP28 High Supply Voltage Warning   
			for requested port
			-----------------------------
			ommp401InterfaceNumber:
			1 to 4 - CLIENT-1 to CLIENT-4
			-----------------------------
			Value:
			critical
			major
			minor
			deferred
			---------------------------"
	::= { ommp401ConfigurationEntry 234 }

	ommp401Qsfp28LowSupplyVoltageWarningSeverity OBJECT-TYPE
		SYNTAX  DisplayString
		MAX-ACCESS  read-write
		STATUS  current
		DESCRIPTION
			"Set or Get the alarm severity level of the
			OMMP401 QSFP28 Low Supply Voltage Warning   
			for requested port
			-----------------------------
			ommp401InterfaceNumber:
			1 to 4 - CLIENT-1 to CLIENT-4
			-----------------------------
			Value:
			critical
			major
			minor
			deferred
			---------------------------"
	::= { ommp401ConfigurationEntry 235 }

	ommp401Qsfp28PresenceAbsenceNotificationSeverity OBJECT-TYPE
		SYNTAX  DisplayString
		MAX-ACCESS  read-write
		STATUS  current
		DESCRIPTION
			"Set or Get the alarm severity level of the
			OMMP401 QSFP28 Presence Absence Notification   
			for requested port
			-----------------------------
			ommp401InterfaceNumber:
			1 to 4 - CLIENT-1 to CLIENT-4
			5 - LINE-1
			-----------------------------
			Value:
			critical
			major
			minor
			deferred
			---------------------------"
	::= { ommp401ConfigurationEntry 236 }

	ommp401OtuLossOfSignalAlarmSeverity  OBJECT-TYPE
		SYNTAX  DisplayString
		MAX-ACCESS  read-write
		STATUS  current
		DESCRIPTION
			"Set or Get the alarm severity level of the OMMP401 OTU Loss Of Signal Alarm
			for the requested port
			-----------------------------
			ommp401InterfaceNumber:
			1 to 4 - CLIENT-1 to CLIENT-4
			-----------------------------
			Value:
			critical
			major
			minor
			deferred
			-----------------------------"
	::= { ommp401ConfigurationEntry 237 }

	ommp401OtuLossOfFrameAlarmSeverity  OBJECT-TYPE
		SYNTAX  DisplayString
		MAX-ACCESS  read-write
		STATUS  current
		DESCRIPTION
			"Set or Get the alarm severity level of the OMMP401 OTU Loss Of Frame Alarm
			for the requested port
			-----------------------------
			ommp401InterfaceNumber:
			1 to 4 - CLIENT-1 to CLIENT-4
			-----------------------------
			Value:
			critical
			major
			minor
			deferred
			-----------------------------"
	::= { ommp401ConfigurationEntry 238 }

	ommp401OtuOutOfFrameAlarmSeverity  OBJECT-TYPE
		SYNTAX  DisplayString
		MAX-ACCESS  read-write
		STATUS  current
		DESCRIPTION
			"Set or Get the alarm severity level of the OMMP401 OTU Out Of Frame Alarm
			for the requested port
			-----------------------------
			ommp401InterfaceNumber:
			1 to 4 - CLIENT-1 to CLIENT-4
			-----------------------------
			Value:
			critical
			major
			minor
			deferred
			-----------------------------"
	::= { ommp401ConfigurationEntry 239 }

	ommp401OtuOutOfMultiFrameAlarmSeverity  OBJECT-TYPE
		SYNTAX  DisplayString
		MAX-ACCESS  read-write
		STATUS  current
		DESCRIPTION
			"Set or Get the alarm severity level of the OMMP401 OTU Out Of Multi Frame Alarm
			for the requested port
			-----------------------------
			ommp401InterfaceNumber:
			1 to 4 - CLIENT-1 to CLIENT-4
			-----------------------------
			Value:
			critical
			major
			minor
			deferred
			-----------------------------"
	::= { ommp401ConfigurationEntry 240 }

	ommp401OtuSignalDegradeAlarmSeverity  OBJECT-TYPE
		SYNTAX  DisplayString
		MAX-ACCESS  read-write
		STATUS  current
		DESCRIPTION
			"Set or Get the alarm severity level of the OMMP401 OTU Signal Degrade Alarm
			for the requested port
			-----------------------------
			ommp401InterfaceNumber:
			1 to 4 - CLIENT-1 to CLIENT-4
			-----------------------------
			Value:
			critical
			major
			minor
			deferred
			-----------------------------"
	::= { ommp401ConfigurationEntry 242 }

	ommp401OtuAlarmIndicationSignalAlarmSeverity  OBJECT-TYPE
		SYNTAX  DisplayString
		MAX-ACCESS  read-write
		STATUS  current
		DESCRIPTION
			"Set or Get the alarm severity level of the OMMP401 OTU Alarm Indication Signal Alarm
			for the requested port
			-----------------------------
			ommp401InterfaceNumber:
			1 to 4 - CLIENT-1 to CLIENT-4
			-----------------------------
			Value:
			critical
			major
			minor
			deferred
			-----------------------------"
	::= { ommp401ConfigurationEntry 243 }

	ommp401OtuIncomingAlignmentErrorAlarmSeverity  OBJECT-TYPE
		SYNTAX  DisplayString
		MAX-ACCESS  read-write
		STATUS  current
		DESCRIPTION
			"Set or Get the alarm severity level of the OMMP401 OTU Incoming Alignment Error Alarm
			for the requested port
			-----------------------------
			ommp401InterfaceNumber:
			1 to 4 - CLIENT-1 to CLIENT-4
			-----------------------------
			Value:
			critical
			major
			minor
			deferred
			-----------------------------"
	::= { ommp401ConfigurationEntry 244 }

	ommp401OtuTrailTraceIdentifierMismatchAlarmSeverity  OBJECT-TYPE
		SYNTAX  DisplayString
		MAX-ACCESS  read-write
		STATUS  current
		DESCRIPTION
			"Set or Get the alarm severity level of the OMMP401 OTU Sapi Trace Identifier Mismatch Alarm
			for the requested port
			-----------------------------
			ommp401InterfaceNumber:
			1 to 4 - CLIENT-1 to CLIENT-4
			-----------------------------
			Value:
			critical
			major
			minor
			deferred
			-----------------------------"
	::= { ommp401ConfigurationEntry 245 }
	
	ommp401OtuBackwardIncomingAlignmentErrorAlarmSeverity  OBJECT-TYPE
		SYNTAX  DisplayString
		MAX-ACCESS  read-write
		STATUS  current
		DESCRIPTION
			"Set or Get the alarm severity level of the OMMP401 OTU Backward Incoming Alignment Error Alarm
			for the requested port
			-----------------------------
			ommp401InterfaceNumber:
			1 to 4 - CLIENT-1 to CLIENT-4
			-----------------------------
			Value:
			critical
			major
			minor
			deferred
			-----------------------------"
	::= { ommp401ConfigurationEntry 246 }

	ommp401OtuBackwardDefectIndicationAlarmSeverity  OBJECT-TYPE
		SYNTAX  DisplayString
		MAX-ACCESS  read-write
		STATUS  current
		DESCRIPTION
			"Set or Get the alarm severity level of the OMMP401 OTU Backward Defect Indication Alarm
			for the requested port
			-----------------------------
			ommp401InterfaceNumber:
			1 to 4 - CLIENT-1 to CLIENT-4
			-----------------------------
			Value:
			critical
			major
			minor
			deferred
			-----------------------------"
	::= { ommp401ConfigurationEntry 247 }

	ommp401OduSignalDegradeAlarmSeverity  OBJECT-TYPE
		SYNTAX  DisplayString
		MAX-ACCESS  read-write
		STATUS  current
		DESCRIPTION
			"Set or Get the alarm severity level of the OMMP401 ODU Signal Degrade Alarm
			for the requested port
			-----------------------------
			ommp401InterfaceNumber:
			1 to 4 - CLIENT-1 to CLIENT-4
			-----------------------------
			Value:
			critical
			major
			minor
			deferred
			-----------------------------"
	::= { ommp401ConfigurationEntry 249 }

	ommp401OduAlarmIndicationSignalAlarmSeverity  OBJECT-TYPE
		SYNTAX  DisplayString
		MAX-ACCESS  read-write
		STATUS  current
		DESCRIPTION
			"Set or Get the alarm severity level of the OMMP401 ODU Alarm Indication Signal Alarm
			for the requested port
			-----------------------------
			ommp401InterfaceNumber:
			1 to 4 - CLIENT-1 to CLIENT-4
			-----------------------------
			Value:
			critical
			major
			minor
			deferred
			-----------------------------"
	::= { ommp401ConfigurationEntry 250 }

	ommp401OduTrailTraceIdentifierMismatchAlarmSeverity  OBJECT-TYPE
		SYNTAX  DisplayString
		MAX-ACCESS  read-write
		STATUS  current
		DESCRIPTION
			"Set or Get the alarm severity level of the OMMP401 OTU Sapi Trace Identifier Mismatch Alarm
			for the requested port
			-----------------------------
			ommp401InterfaceNumber:
			1 to 4 - CLIENT-1 to CLIENT-4
			-----------------------------
			Value:
			critical
			major
			minor
			deferred
			-----------------------------"
	::= { ommp401ConfigurationEntry 251 }

	ommp401OduLockedDefectAlarmSeverity  OBJECT-TYPE
		SYNTAX  DisplayString
		MAX-ACCESS  read-write
		STATUS  current
		DESCRIPTION
			"Set or Get the alarm severity level of the OMMP401 ODU Locked Defect Alarm
			for the requested port
			-----------------------------
			ommp401InterfaceNumber:
			1 to 4 - CLIENT-1 to CLIENT-4
			-----------------------------
			Value:
			critical
			major
			minor
			deferred
			-----------------------------"
	::= { ommp401ConfigurationEntry 252 }

	ommp401OduOpenConnectionIndicationAlarmSeverity  OBJECT-TYPE
		SYNTAX  DisplayString
		MAX-ACCESS  read-write
		STATUS  current
		DESCRIPTION
			"Set or Get the alarm severity level of the OMMP401 ODU Open Connection Indication
			Alarm for the requested port
			-----------------------------
			ommp401InterfaceNumber:
			1 to 4 - CLIENT-1 to CLIENT-4
			-----------------------------
			Value:
			critical
			major
			minor
			deferred
			-----------------------------"
	::= { ommp401ConfigurationEntry 253 }

	ommp401OduBackwardDefectIndicationAlarmSeverity  OBJECT-TYPE
		SYNTAX  DisplayString
		MAX-ACCESS  read-write
		STATUS  current
		DESCRIPTION
			"Set or Get the alarm severity level of the OMMP401 ODU Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 254 }

	ommp401OduTcm1BackwardDefectIndicationAlarmSeverity  OBJECT-TYPE
		SYNTAX  DisplayString
		MAX-ACCESS  read-write
		STATUS  current
		DESCRIPTION
			"Set or Get the alarm severity level of the OMMP401 ODU TCM1 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 261 }

	ommp401OduTcm2BackwardDefectIndicationAlarmSeverity  OBJECT-TYPE
		SYNTAX  DisplayString
		MAX-ACCESS  read-write
		STATUS  current
		DESCRIPTION
			"Set or Get the alarm severity level of the OMMP401 ODU TCM2 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 262 }

	ommp401OduTcm3BackwardDefectIndicationAlarmSeverity  OBJECT-TYPE
		SYNTAX  DisplayString
		MAX-ACCESS  read-write
		STATUS  current
		DESCRIPTION
			"Set or Get the alarm severity level of the OMMP401 ODU TCM3 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 263 }

	ommp401OduTcm4BackwardDefectIndicationAlarmSeverity  OBJECT-TYPE
		SYNTAX  DisplayString
		MAX-ACCESS  read-write
		STATUS  current
		DESCRIPTION
			"Set or Get the alarm severity level of the OMMP401 ODU TCM4 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 264 }

	ommp401OduTcm5BackwardDefectIndicationAlarmSeverity  OBJECT-TYPE
		SYNTAX  DisplayString
		MAX-ACCESS  read-write
		STATUS  current
		DESCRIPTION
			"Set or Get the alarm severity level of the OMMP401 ODU TCM5 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 265 }

	ommp401OduTcm6BackwardDefectIndicationAlarmSeverity  OBJECT-TYPE
		SYNTAX  DisplayString
		MAX-ACCESS  read-write
		STATUS  current
		DESCRIPTION
			"Set or Get the alarm severity level of the OMMP401 ODU TCM6 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 266 }

	ommp401OduTcm1LossOfTandemConnectionAlarmSeverity  OBJECT-TYPE
		SYNTAX  DisplayString
		MAX-ACCESS  read-write
		STATUS  current
		DESCRIPTION
			"Set or Get the alarm severity level of the OMMP401 ODU TCM1 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 273 }

	ommp401OduTcm2LossOfTandemConnectionAlarmSeverity  OBJECT-TYPE
		SYNTAX  DisplayString
		MAX-ACCESS  read-write
		STATUS  current
		DESCRIPTION
			"Set or Get the alarm severity level of the OMMP401 ODU TCM2 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 274 }

	ommp401OduTcm3LossOfTandemConnectionAlarmSeverity  OBJECT-TYPE
		SYNTAX  DisplayString
		MAX-ACCESS  read-write
		STATUS  current
		DESCRIPTION
			"Set or Get the alarm severity level of the OMMP401 ODU TCM3 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 275 }

	ommp401OduTcm4LossOfTandemConnectionAlarmSeverity  OBJECT-TYPE
		SYNTAX  DisplayString
		MAX-ACCESS  read-write
		STATUS  current
		DESCRIPTION
			"Set or Get the alarm severity level of the OMMP401 ODU TCM4 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 276 }

	ommp401OduTcm5LossOfTandemConnectionAlarmSeverity  OBJECT-TYPE
		SYNTAX  DisplayString
		MAX-ACCESS  read-write
		STATUS  current
		DESCRIPTION
			"Set or Get the alarm severity level of the OMMP401 ODU TCM5 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 277 }

	ommp401OduTcm6LossOfTandemConnectionAlarmSeverity  OBJECT-TYPE
		SYNTAX  DisplayString
		MAX-ACCESS  read-write
		STATUS  current
		DESCRIPTION
			"Set or Get the alarm severity level of the OMMP401 ODU TCM6 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 278 }

	ommp401OduTcm1BackwardIncomingAlignmentErrorAlarmSeverity  OBJECT-TYPE
		SYNTAX  DisplayString
		MAX-ACCESS  read-write
		STATUS  current
		DESCRIPTION
			"Set or Get the alarm severity level of the OMMP401 ODU TCM1 Locked Defect
			Alarm for the requested port
			-----------------------------
			ommp401InterfaceNumber:
			1 to 4 - CLIENT-1 to CLIENT-4
			-----------------------------
			Value:
			critical
			major
			minor
			deferred
			-----------------------------"
	::= { ommp401ConfigurationEntry 279 }

	ommp401OduTcm2BackwardIncomingAlignmentErrorAlarmSeverity  OBJECT-TYPE
		SYNTAX  DisplayString
		MAX-ACCESS  read-write
		STATUS  current
		DESCRIPTION
			"Set or Get the alarm severity level of the OMMP401 ODU TCM2 Locked Defect
			Alarm for the requested port
			-----------------------------
			ommp401InterfaceNumber:
			1 to 4 - CLIENT-1 to CLIENT-4
			-----------------------------
			Value:
			critical
			major
			minor
			deferred
			-----------------------------"
	::= { ommp401ConfigurationEntry 280 }

	ommp401OduTcm3BackwardIncomingAlignmentErrorAlarmSeverity  OBJECT-TYPE
		SYNTAX  DisplayString
		MAX-ACCESS  read-write
		STATUS  current
		DESCRIPTION
			"Set or Get the alarm severity level of the OMMP401 ODU TCM3 Locked Defect
			Alarm for the requested port
			-----------------------------
			ommp401InterfaceNumber:
			1 to 4 - CLIENT-1 to CLIENT-4
			-----------------------------
			Value:
			critical
			major
			minor
			deferred
			-----------------------------"
	::= { ommp401ConfigurationEntry 281 }

	ommp401OduTcm4BackwardIncomingAlignmentErrorAlarmSeverity  OBJECT-TYPE
		SYNTAX  DisplayString
		MAX-ACCESS  read-write
		STATUS  current
		DESCRIPTION
			"Set or Get the alarm severity level of the OMMP401 ODU TCM4 Locked Defect
			Alarm for the requested port
			-----------------------------
			ommp401InterfaceNumber:
			1 to 4 - CLIENT-1 to CLIENT-4
			-----------------------------
			Value:
			critical
			major
			minor
			deferred
			-----------------------------"
	::= { ommp401ConfigurationEntry 282 }

	ommp401OduTcm5BackwardIncomingAlignmentErrorAlarmSeverity  OBJECT-TYPE
		SYNTAX  DisplayString
		MAX-ACCESS  read-write
		STATUS  current
		DESCRIPTION
			"Set or Get the alarm severity level of the OMMP401 ODU TCM5 Locked Defect
			Alarm for the requested port
			-----------------------------
			ommp401InterfaceNumber:
			1 to 4 - CLIENT-1 to CLIENT-4
			-----------------------------
			Value:
			critical
			major
			minor
			deferred
			-----------------------------"
	::= { ommp401ConfigurationEntry 283 }

	ommp401OduTcm6BackwardIncomingAlignmentErrorAlarmSeverity  OBJECT-TYPE
		SYNTAX  DisplayString
		MAX-ACCESS  read-write
		STATUS  current
		DESCRIPTION
			"Set or Get the alarm severity level of the OMMP401 ODU TCM6 Locked Defect
			Alarm for the requested port
			-----------------------------
			ommp401InterfaceNumber:
			1 to 4 - CLIENT-1 to CLIENT-4
			-----------------------------
			Value:
			critical
			major
			minor
			deferred
			-----------------------------"
	::= { ommp401ConfigurationEntry 284 }

	ommp401OpuPayloadMismatchAlarmSeverity  OBJECT-TYPE
		SYNTAX  DisplayString
		MAX-ACCESS  read-write
		STATUS  current
		DESCRIPTION
			"Set or Get the alarm severity level of the OMMP401 OPU Payload Mismatch Alarm
			for the requested port
			-----------------------------
			ommp401InterfaceNumber:
			1 to 4 - CLIENT-1 to CLIENT-4
			-----------------------------
			Value:
			critical
			major
			minor
			deferred
			-----------------------------"
	::= { ommp401ConfigurationEntry 291 }

	ommp401EthernetLossOfSignalAlarmSeverity  OBJECT-TYPE
		SYNTAX  DisplayString
		MAX-ACCESS  read-write
		STATUS  current
		DESCRIPTION
			"Set or Get the alarm severity level of the OMMP401 Ethernet Loss Of Signal Alarm
			for the requested port
			-----------------------------
			ommp401InterfaceNumber:
			1 to 4 - CLIENT-1 to CLIENT-4
			-----------------------------
			Value:
			Critical
			major
			minor
			deferred
			-----------------------------"
	::= { ommp401ConfigurationEntry 292 }

	ommp401EthernetIngressRemoteFaultAlarmSeverity  OBJECT-TYPE
		SYNTAX  DisplayString
		MAX-ACCESS  read-write
		STATUS  current
		DESCRIPTION
			"Set or Get the alarm severity level of the OMMP401 Ethernet Ingress Remote Fault 
			Alarm for the requested port
			-----------------------------
			ommp401InterfaceNumber:
			1 to 4 - CLIENT-1 to CLIENT-4
			-----------------------------
			Value:
			critical
			major
			minor
			deferred
			-----------------------------"
	::= { ommp401ConfigurationEntry 293 }

	ommp401EthernetIngressPcsErrorBlocksDetectedAlarmSeverity  OBJECT-TYPE
		SYNTAX  DisplayString
		MAX-ACCESS  read-write
		STATUS  current
		DESCRIPTION
			"Set or Get the alarm severity level of the OMMP401 Ethernet Ingress Pcs Error Blocks Detected Alarm
			for the requested port
			-----------------------------
			ommp401InterfaceNumber:
			1 to 4 - CLIENT-1 to CLIENT-4
			-----------------------------
			Value:
			critical
			major
			minor
			deferred
			-----------------------------"
	::= { ommp401ConfigurationEntry 294 }

	ommp401EthernetIngressPcsBipErrorsDetectedAlarmSeverity  OBJECT-TYPE
		SYNTAX  DisplayString
		MAX-ACCESS  read-write
		STATUS  current
		DESCRIPTION
			"Set or Get the alarm severity level of the OMMP401 Ethernet Ingress Pcs Bip Errors Detected Alarm
			for the requested port
			-----------------------------
			ommp401InterfaceNumber:
			1 to 4 - CLIENT-1 to CLIENT-4
			-----------------------------
			Value:
			critical
			major
			minor
			deferred
			-----------------------------"
	::= { ommp401ConfigurationEntry 295 }

	ommp401EthernetIngressOpuClientServerFailIndicationAlarmSeverity  OBJECT-TYPE
		SYNTAX  DisplayString
		MAX-ACCESS  read-write
		STATUS  current
		DESCRIPTION
			"Set or Get the alarm severity level of the OMMP401 Ethernet Ingress Opu Client Server Fail Indication Alarm
			for the requested port
			-----------------------------
			ommp401InterfaceNumber:
			1 to 4 - CLIENT-1 to CLIENT-4
			-----------------------------
			Value:
			critical
			major
			minor
			deferred
			-----------------------------"
	::= { ommp401ConfigurationEntry 296 }

	ommp401EthernetIngressLocalFaultAlarmSeverity  OBJECT-TYPE
		SYNTAX  DisplayString
		MAX-ACCESS  read-write
		STATUS  current
		DESCRIPTION
			"Set or Get the alarm severity level of the OMMP401 Ethernet Ingress Local Fault Alarm
			for the requested port
			-----------------------------
			ommp401InterfaceNumber:
			1 to 4 - CLIENT-1 to CLIENT-4
			-----------------------------
			Value:
			critical
			major
			minor
			deferred
			-----------------------------"
	::= { ommp401ConfigurationEntry 297 }

	ommp401EthernetIngressLossOfAlignmentAlarmSeverity  OBJECT-TYPE
		SYNTAX  DisplayString
		MAX-ACCESS  read-write
		STATUS  current
		DESCRIPTION
			"Set or Get the alarm severity level of the OMMP401 Ethernet Ingress Loss Of Alignment 
			Alarm for the requested port
			-----------------------------
			ommp401InterfaceNumber:
			1 to 4 - CLIENT-1 to CLIENT-4
			-----------------------------
			Value:
			critical
			major
			minor
			deferred
			-----------------------------"
	::= { ommp401ConfigurationEntry 298 }

	ommp401EthernetIngressLossOfAlignmentMarkerLockAlarmSeverity  OBJECT-TYPE
		SYNTAX  DisplayString
		MAX-ACCESS  read-write
		STATUS  current
		DESCRIPTION
			"Set or Get the alarm severity level of the OMMP401 Ethernet Ingress Loss Of Alignment Marker Alarm
			for the requested port
			-----------------------------
			ommp401InterfaceNumber:
			1 to 4 - CLIENT-1 to CLIENT-4
			-----------------------------
			Value:
			critical
			major
			minor
			deferred
			-----------------------------"
	::= { ommp401ConfigurationEntry 299 }

	ommp401EthernetIngressLossOfBlockLockAlarmSeverity  OBJECT-TYPE
		SYNTAX  DisplayString
		MAX-ACCESS  read-write
		STATUS  current
		DESCRIPTION
			"Set or Get the alarm severity level of the OMMP401 Ethernet Ingress Loss Of Block Lock Alarm
			for the requested port
			-----------------------------
			ommp401InterfaceNumber:
			1 to 4 - CLIENT-1 to CLIENT-4
			-----------------------------
			Value:
			critical
			major
			minor
			deferred
			-----------------------------"
	::= { ommp401ConfigurationEntry 300 }

	ommp401EthernetEgressRemoteFaultAlarmSeverity  OBJECT-TYPE
		SYNTAX  DisplayString
		MAX-ACCESS  read-write
		STATUS  current
		DESCRIPTION
			"Set or Get the alarm severity level of the OMMP401 Ethernet Egress Remote Fault Alarm
			for the requested port
			-----------------------------
			ommp401InterfaceNumber:
			1 to 4 - CLIENT-1 to CLIENT-4
			-----------------------------
			Value:
			critical
			major
			minor
			deferred
			-----------------------------"
	::= { ommp401ConfigurationEntry 301 }

	ommp401EthernetEgressPcsErrorBlocksDetectedAlarmSeverity  OBJECT-TYPE
		SYNTAX  DisplayString
		MAX-ACCESS  read-write
		STATUS  current
		DESCRIPTION
			"Set or Get the alarm severity level of the OMMP401 Ethernet Egress Pcs Error Blocks Detected Alarm
			for the requested port
			-----------------------------
			ommp401InterfaceNumber:
			1 to 4 - CLIENT-1 to CLIENT-4
			-----------------------------
			Value:
			critical
			major
			minor
			deferred
			-----------------------------"
	::= { ommp401ConfigurationEntry 302 }

	ommp401EthernetEgressPcsBipErrorsDetectedAlarmSeverity  OBJECT-TYPE
		SYNTAX  DisplayString
		MAX-ACCESS  read-write
		STATUS  current
		DESCRIPTION
			"Set or Get the alarm severity level of the OMMP401 Ethernet Egress Pcs Bip Errors Detected Alarm
			for the requested port
			-----------------------------
			ommp401InterfaceNumber:
			1 to 4 - CLIENT-1 to CLIENT-4
			-----------------------------
			Value:
			critical
			major
			minor
			deferred
			-----------------------------"
	::= { ommp401ConfigurationEntry 303 }

	ommp401EthernetEgressHighBerAlarmSeverity  OBJECT-TYPE
		SYNTAX  DisplayString
		MAX-ACCESS  read-write
		STATUS  current
		DESCRIPTION
			"Set or Get the alarm severity level of the OMMP401 Ethernet Egress High BER Alarm
			for the requested port
			-----------------------------
			ommp401InterfaceNumber:
			1 to 4 - CLIENT-1 to CLIENT-4
			-----------------------------
			Value:
			critical
			major
			minor
			deferred
			-----------------------------"
	::= { ommp401ConfigurationEntry 304 }

	ommp401EthernetEgressLocalFaultAlarmSeverity  OBJECT-TYPE
		SYNTAX  DisplayString
		MAX-ACCESS  read-write
		STATUS  current
		DESCRIPTION
			"Set or Get the alarm severity level of the OMMP401 Ethernet Egress Local Fault Alarm
			for the requested port
			-----------------------------
			ommp401InterfaceNumber:
			1 to 4 - CLIENT-1 to CLIENT-4
			-----------------------------
			Value:
			critical
			major
			minor
			deferred
			-----------------------------"
	::= { ommp401ConfigurationEntry 305 }

	ommp401EthernetEgressLossOfAlignmentAlarmSeverity  OBJECT-TYPE
		SYNTAX  DisplayString
		MAX-ACCESS  read-write
		STATUS  current
		DESCRIPTION
			"Set or Get the alarm severity level of the OMMP401 Ethernet Egress Loss Of Alignment 
			Alarm for the requested port
			-----------------------------
			ommp401InterfaceNumber:
			1 to 4 - CLIENT-1 to CLIENT-4
			-----------------------------
			Value:
			critical
			major
			minor
			deferred
			-----------------------------"
	::= { ommp401ConfigurationEntry 306 }

	ommp401EthernetEgressLossOfAlignmentMarkerLockAlarmSeverity  OBJECT-TYPE
		SYNTAX  DisplayString
		MAX-ACCESS  read-write
		STATUS  current
		DESCRIPTION
			"Set or Get the alarm severity level of the OMMP401 Ethernet Egress Loss Of Alignment Marker Alarm
			for the requested port
			-----------------------------
			ommp401InterfaceNumber:
			1 to 4 - CLIENT-1 to CLIENT-4
			-----------------------------
			Value:
			critical
			major
			minor
			deferred
			-----------------------------"
	::= { ommp401ConfigurationEntry 307 }

	ommp401EthernetEgressLossOfBlockLockAlarmSeverity  OBJECT-TYPE
		SYNTAX  DisplayString
		MAX-ACCESS  read-write
		STATUS  current
		DESCRIPTION
			"Set or Get the alarm severity level of the OMMP401 Ethernet Egress Loss Of Block Lock Alarm
			for the requested port
			-----------------------------
			ommp401InterfaceNumber:
			1 to 4 - CLIENT-1 to CLIENT-4
			-----------------------------
			Value:
			critical
			major
			minor
			deferred
			-----------------------------"
	::= { ommp401ConfigurationEntry 308 }

	ommp401TunableCfp2WavelengthGridSpacing  OBJECT-TYPE
		SYNTAX  INTEGER
		MAX-ACCESS  read-write
		STATUS  current
		DESCRIPTION
			"This property gives difference in the wavelength
			between two channels In GHz.
			-----------------------------
			ommp401InterfaceNumber:
			5 - LINE-1
			-----------------------------
			Values:
			eg: 100
			-----------------------------"
	::= { ommp401ConfigurationEntry 309 }
	
	ommp401LineOtuSignalFailThreshold OBJECT-TYPE		 
		SYNTAX  INTEGER
		MAX-ACCESS read-write
		STATUS current
		DESCRIPTION
			"Set or Get SM Signal Failure 
			Threshold value for the requested port configured with 
			OTU4/OTUC4 traffic.
			-----------------------------
			ommp401InterfaceNumber:
			1 to 4 - CLIENT-1 to CLIENT-4
			-----------------------------
			Values: 
			03 - 1.E -03
			04 - 1.E -04
			05 - 1.E -05
			-----------------------------" 
		::= { ommp401ConfigurationEntry 310 }

	ommp401LineOtuSignalDegradeThreshold OBJECT-TYPE		 
		SYNTAX  INTEGER
		MAX-ACCESS read-write
		STATUS current
		DESCRIPTION
			"Set or Get SM Signal Degrade 
			Threshold value for the requested port configured with 
			OTU4/OTUC4 traffic.
			-----------------------------
			ommp401InterfaceNumber:
			1 to 4 - CLIENT-1 to CLIENT-4
			-----------------------------
			Values:
			06 - 1.E -06
			07 - 1.E -07
			08 - 1.E -08
			09 - 1.E -09
			10 - 1.E -10(for line only)
			-----------------------------"
		::= { ommp401ConfigurationEntry 311 }

	ommp401LineOtuSapiTransmitTraceMessage OBJECT-TYPE
		SYNTAX DisplayString
		MAX-ACCESS read-write
		STATUS current
		DESCRIPTION
			"Set or get the 15 characters SAPI Transmit TTI message
			which is put into the outgoing OTU4/OTUC4 frame. 
			-----------------------------
			ommp401InterfaceNumber:
			1 to 4 - CLIENT-1 to CLIENT-4
			-----------------------------
			Values:
			eg: 123451234512345
			-----------------------------" 
		::= { ommp401ConfigurationEntry 312 }

	ommp401LineOtuDapiTransmitTraceMessage OBJECT-TYPE
		SYNTAX DisplayString
		MAX-ACCESS read-write
		STATUS current
		DESCRIPTION
			"Set or get the 15 characters DAPI Transmit TTI message
			which is put into the outgoing OTU4/OTUC4 frame. 
			-----------------------------
			ommp401InterfaceNumber:
			1 to 4 - CLIENT-1 to CLIENT-4
			-----------------------------
			Values:
			eg: 123451234512345
			-----------------------------" 
		::= { ommp401ConfigurationEntry 313 }
		
	ommp401LineOtuOperatorSpecificTransmitTraceMessage OBJECT-TYPE
		SYNTAX DisplayString
		MAX-ACCESS read-write
		STATUS current
		DESCRIPTION
			"Set or get the 32 characters Operator Specific Transmit
			TTI message which is put into the outgoing OTU4/OTUC4
			frame. 
			-----------------------------
			ommp401InterfaceNumber:
			1 to 4 - CLIENT-1 to CLIENT-4
			-----------------------------
			Values:
			eg: 12345123451234512345123451234500
			-----------------------------" 
		::= { ommp401ConfigurationEntry 314 }
		
	ommp401LineOtuSapiExpectedTraceMessage OBJECT-TYPE
		SYNTAX DisplayString
		MAX-ACCESS read-write
		STATUS current
		DESCRIPTION
			"15 characters SM SAPI Expected TTI message - Message
			set here is used for comparison with the message present
			in SM SAPI field of the incoming OTU4/OTUC4 frames.
			-----------------------------
			ommp401InterfaceNumber:
			1 to 4 - CLIENT-1 to CLIENT-4
			-----------------------------
			Values:
			eg: 123451234512345
			-----------------------------" 
		::= { ommp401ConfigurationEntry 315 }
		
	ommp401LineOtuDapiExpectedTraceMessage OBJECT-TYPE
		SYNTAX DisplayString
		MAX-ACCESS read-write
		STATUS current
		DESCRIPTION
			"15 characters SM DAPI Expected TTI message - Message
			set here is used for comparison with the message present
			in SM DAPI field of the incoming OTU4/OTUC4 frames.
			-----------------------------
			ommp401InterfaceNumber:
			1 to 4 - CLIENT-1 to CLIENT-4
			-----------------------------
			Values:
			eg: 123451234512345
			-----------------------------" 
		::= { ommp401ConfigurationEntry 316 }

	ommp401LineOtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU4/OTUC4 frames.
			-----------------------------
			ommp401InterfaceNumber:
			1 to 4 - CLIENT-1 to CLIENT-4
			-----------------------------
			Values:
			eg: 12345123451234512345123451234500
			-----------------------------" 
		::= { ommp401ConfigurationEntry 317 }

	ommp401LineOduSignalFailThreshold OBJECT-TYPE		 
		SYNTAX  INTEGER
		MAX-ACCESS read-write
		STATUS current
		DESCRIPTION
			"Set or Get PM Signal Failure 
			Threshold value for the requested port configured with 
			OTU4/OTUC4 traffic.
			-----------------------------
			ommp401InterfaceNumber:
			1 to 4 - CLIENT-1 to CLIENT-4
			-----------------------------
			Values: 
			03 - 1.E -03
			04 - 1.E -04
			05 - 1.E -05
			-----------------------------" 
		::= { ommp401ConfigurationEntry 318 }

	ommp401LineOduSignalDegradeThreshold OBJECT-TYPE		 
		SYNTAX  INTEGER
		MAX-ACCESS read-write
		STATUS current
		DESCRIPTION
			"Set or Get PM Signal Degrade 
			Threshold value for the requested port configured with 
			OTU4/OTUC4 traffic.
			-----------------------------
			ommp401InterfaceNumber:
			1 to 4 - CLIENT-1 to CLIENT-4
			-----------------------------
			Values: 
			06 - 1.E -06
			07 - 1.E -07
			08 - 1.E -08
			09 - 1.E -09
			10 - 1.E -10(for line only)
			-----------------------------" 
		::= { ommp401ConfigurationEntry 319 }

	ommp401LineOduSapiTransmitTraceMessage OBJECT-TYPE
		SYNTAX DisplayString
		MAX-ACCESS read-write
		STATUS current
		DESCRIPTION
			"Set or get the 15 characters SAPI Transmit TTI message
			which is put into the outgoing OTU4/OTUC4
			frame at the PM level. 
			-----------------------------
			ommp401InterfaceNumber:
			1 to 4 - CLIENT-1 to CLIENT-4
			-----------------------------
			Values:
			eg: 123451234512345
			-----------------------------" 
		::= { ommp401ConfigurationEntry 320 }
		
	ommp401LineOduDapiTransmitTraceMessage OBJECT-TYPE
		SYNTAX DisplayString
		MAX-ACCESS read-write
		STATUS current
		DESCRIPTION
			"Set or get the 15 characters DAPI Transmit TTI message
			which is put into the outgoing OTU4/OTUC4
			frame at the PM level. 
			-----------------------------
			ommp401InterfaceNumber:
			1 to 4 - CLIENT-1 to CLIENT-4
			-----------------------------
			Values:
			eg: 123451234512345
			-----------------------------" 
		::= { ommp401ConfigurationEntry 321 }
		
	ommp401LineOduOperatorSpecificTransmitTraceMessage OBJECT-TYPE
		SYNTAX DisplayString
		MAX-ACCESS read-write
		STATUS current
		DESCRIPTION
			"Set or get the 32 characters Operator Specific Transmit
			TTI message which is put into the outgoing OTU4/OTUC4
			frame at the PM level. 
			-----------------------------
			ommp401InterfaceNumber:
			1 to 4 - CLIENT-1 to CLIENT-4
			-----------------------------
			Values:
			eg: 12345123451234512345123451234500
			-----------------------------" 
		::= { ommp401ConfigurationEntry 322 }
		
	ommp401LineOduSapiExpectedTraceMessage OBJECT-TYPE
		SYNTAX DisplayString
		MAX-ACCESS read-write
		STATUS current
		DESCRIPTION
			"15 characters PM SAPI Expected TTI message - Message
			set here is used for comparison with the message present
			in PM SAPI field of the incoming OTU4/OTUC4 frames.
			-----------------------------
			ommp401InterfaceNumber:
			1 to 4 - CLIENT-1 to CLIENT-4
			-----------------------------
			Values:
			eg: 123451234512345
			-----------------------------" 
		::= { ommp401ConfigurationEntry 323 }

	ommp401LineOduDapiExpectedTraceMessage OBJECT-TYPE
		SYNTAX DisplayString
		MAX-ACCESS read-write
		STATUS current
		DESCRIPTION
			"15 characters PM DAPI Expected TTI message - Message
			set here is used for comparison with the message present
			in PM DAPI field of the incoming OTU4/OTUC4 frames.
			-----------------------------
			ommp401InterfaceNumber:
			1 to 4 - CLIENT-1 to CLIENT-4
			-----------------------------
			Values:
			eg: 123451234512345
			-----------------------------" 
		::= { ommp401ConfigurationEntry 324 }
		
	ommp401LineOduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU4/OTUC4 frames.
			-----------------------------
			ommp401InterfaceNumber:
			1 to 4 - CLIENT-1 to CLIENT-4
			-----------------------------
			Values:
			eg: 12345123451234512345123451234500
			-----------------------------" 
		::= { ommp401ConfigurationEntry 325 }
		
	ommp401LineOtuLossOfSignalAlarmInhibit  OBJECT-TYPE
		SYNTAX  INTEGER
		MAX-ACCESS  read-write
		STATUS  current
		DESCRIPTION
			"Inhibits OMMP401 OTU Loss Of Signal Alarm
			for the requested port
			-----------------------------
			ommp401InterfaceNumber:
			1 to 4 - CLIENT-1 to CLIENT-4
			-----------------------------
			Value:
			1 - Inhibit
			0 - Do Not Inhibit
			-----------------------------"
	::= { ommp401ConfigurationEntry 326 }

	ommp401LineOtuLossOfFrameAlarmInhibit  OBJECT-TYPE
		SYNTAX  INTEGER
		MAX-ACCESS  read-write
		STATUS  current
		DESCRIPTION
			"Inhibits OMMP401 OTU Loss Of Frame Alarm
			for the requested port
			-----------------------------
			ommp401InterfaceNumber:
			1 to 4 - CLIENT-1 to CLIENT-4
			-----------------------------
			Value:
			1 - Inhibit
			0 - Do Not Inhibit
			-----------------------------"
	::= { ommp401ConfigurationEntry 327 }

	ommp401LineOtuOutOfFrameAlarmInhibit  OBJECT-TYPE
		SYNTAX  INTEGER
		MAX-ACCESS  read-write
		STATUS  current
		DESCRIPTION
			"Inhibits OMMP401 OTU Out Of Frame Alarm
			for the requested port
			-----------------------------
			ommp401InterfaceNumber:
			1 to 4 - CLIENT-1 to CLIENT-4
			-----------------------------
			Value:
			1 - Inhibit
			0 - Do Not Inhibit
			-----------------------------"
	::= { ommp401ConfigurationEntry 328 }

	ommp401LineOtuLossOfMultiFrameAlarmInhibit  OBJECT-TYPE
		SYNTAX  INTEGER
		MAX-ACCESS  read-write
		STATUS  current
		DESCRIPTION
			"Inhibits OMMP401 OTU Loss Of Multi Frame Alarm
			for the requested port
			-----------------------------
			ommp401InterfaceNumber:
			1 to 4 - CLIENT-1 to CLIENT-4
			-----------------------------
			Value:
			1 - Inhibit
			0 - Do Not Inhibit
			-----------------------------"
	::= { ommp401ConfigurationEntry 329 }

	ommp401LineOtuOutOfMultiFrameAlarmInhibit  OBJECT-TYPE
		SYNTAX  INTEGER
		MAX-ACCESS  read-write
		STATUS  current
		DESCRIPTION
			"Inhibits OMMP401 OTU Out Of Multi Frame Alarm
			for the requested port
			-----------------------------
			ommp401InterfaceNumber:
			1 to 4 - CLIENT-1 to CLIENT-4
			-----------------------------
			Value:
			1 - Inhibit
			0 - Do Not Inhibit
			-----------------------------"
	::= { ommp401ConfigurationEntry 330 }

	ommp401LineOtuSignalDegradeAlarmInhibit  OBJECT-TYPE
		SYNTAX  INTEGER
		MAX-ACCESS  read-write
		STATUS  current
		DESCRIPTION
			"Inhibits OMMP401 OTU Signal Degrade Alarm
			for the requested port
			-----------------------------
			ommp401InterfaceNumber:
			1 to 4 - CLIENT-1 to CLIENT-4
			-----------------------------
			Value:
			1 - Inhibit
			0 - Do Not Inhibit
			-----------------------------"
	::= { ommp401ConfigurationEntry 331 }

	ommp401LineOtuAlarmIndicationSignalAlarmInhibit  OBJECT-TYPE
		SYNTAX  INTEGER
		MAX-ACCESS  read-write
		STATUS  current
		DESCRIPTION
			"Inhibits OMMP401 OTU Alarm Indication Signal Alarm
			for the requested port
			-----------------------------
			ommp401InterfaceNumber:
			1 to 4 - CLIENT-1 to CLIENT-4
			-----------------------------
			Value:
			1 - Inhibit
			0 - Do Not Inhibit
			-----------------------------"
	::= { ommp401ConfigurationEntry 332 }

	ommp401LineOtuIncomingAlignmentErrorAlarmInhibit  OBJECT-TYPE
		SYNTAX  INTEGER
		MAX-ACCESS  read-write
		STATUS  current
		DESCRIPTION
			"Inhibits OMMP401 OTU Incoming Alignment Error Alarm
			for the requested port
			-----------------------------
			ommp401InterfaceNumber:
			1 to 4 - CLIENT-1 to CLIENT-4
			-----------------------------
			Value:
			1 - Inhibit
			0 - Do Not Inhibit
			-----------------------------"
	::= { ommp401ConfigurationEntry 333 }

	ommp401LineOtuTrailTraceIdentifierMismatchAlarmInhibit  OBJECT-TYPE
		SYNTAX  INTEGER
		MAX-ACCESS  read-write
		STATUS  current
		DESCRIPTION
			"Inhibits OMMP401 OTU Sapi Trace Identifier Mismatch Alarm
			for the requested port
			-----------------------------
			ommp401InterfaceNumber:
			1 to 4 - CLIENT-1 to CLIENT-4
			-----------------------------
			Value:
			1 - Inhibit
			0 - Do Not Inhibit
			-----------------------------"
	::= { ommp401ConfigurationEntry 334 }
	
	ommp401LineOtuBackwardIncomingAlignmentErrorAlarmInhibit  OBJECT-TYPE
		SYNTAX  INTEGER
		MAX-ACCESS  read-write
		STATUS  current
		DESCRIPTION
			"Inhibits OMMP401 OTU Backward Incoming Alignment Error Alarm
			for the requested port
			-----------------------------
			ommp401InterfaceNumber:
			1 to 4 - CLIENT-1 to CLIENT-4
			-----------------------------
			Value:
			1 - Inhibit
			0 - Do Not Inhibit
			-----------------------------"
	::= { ommp401ConfigurationEntry 335 }

	ommp401LineOtuBackwardDefectIndicationAlarmInhibit  OBJECT-TYPE
		SYNTAX  INTEGER
		MAX-ACCESS  read-write
		STATUS  current
		DESCRIPTION
			"Inhibits OMMP401 OTU Backward Defect Indication Alarm
			for the requested port
			-----------------------------
			ommp401InterfaceNumber:
			1 to 4 - CLIENT-1 to CLIENT-4
			-----------------------------
			Value:
			1 - Inhibit
			0 - Do Not Inhibit
			-----------------------------"
	::= { ommp401ConfigurationEntry 336 }

	ommp401LineOduSignalDegradeAlarmInhibit  OBJECT-TYPE
		SYNTAX  INTEGER
		MAX-ACCESS  read-write
		STATUS  current
		DESCRIPTION
			"Inhibits OMMP401 ODU Signal Degrade Alarm
			for the requested port
			-----------------------------
			ommp401InterfaceNumber:
			1 to 4 - CLIENT-1 to CLIENT-4
			-----------------------------
			Value:
			1 - Inhibit
			0 - Do Not Inhibit
			-----------------------------"
	::= { ommp401ConfigurationEntry 337 }

	ommp401LineOduAlarmIndicationSignalAlarmInhibit  OBJECT-TYPE
		SYNTAX  INTEGER
		MAX-ACCESS  read-write
		STATUS  current
		DESCRIPTION
			"Inhibits OMMP401 ODU Alarm Indication Signal Alarm
			for the requested port
			-----------------------------
			ommp401InterfaceNumber:
			1 to 4 - CLIENT-1 to CLIENT-4
			-----------------------------
			Value:
			1 - Inhibit
			0 - Do Not Inhibit
			-----------------------------"
	::= { ommp401ConfigurationEntry 338 }

	ommp401LineOduTrailTraceIdentifierMismatchAlarmInhibit  OBJECT-TYPE
		SYNTAX  INTEGER
		MAX-ACCESS  read-write
		STATUS  current
		DESCRIPTION
			"Inhibits OMMP401 OTU Sapi Trace Identifier Mismatch Alarm
			for the requested port
			-----------------------------
			ommp401InterfaceNumber:
			1 to 4 - CLIENT-1 to CLIENT-4
			-----------------------------
			Value:
			1 - Inhibit
			0 - Do Not Inhibit
			-----------------------------"
	::= { ommp401ConfigurationEntry 339 }
	
	ommp401LineOduLockedDefectAlarmInhibit  OBJECT-TYPE
		SYNTAX  INTEGER
		MAX-ACCESS  read-write
		STATUS  current
		DESCRIPTION
			"Inhibits OMMP401 ODU Locked Defect Alarm
			for the requested port
			-----------------------------
			ommp401InterfaceNumber:
			1 to 4 - CLIENT-1 to CLIENT-4
			-----------------------------
			Value:
			1 - Inhibit
			0 - Do Not Inhibit
			-----------------------------"
	::= { ommp401ConfigurationEntry 340 }

	ommp401LineOduOpenConnectionIndicationAlarmInhibit  OBJECT-TYPE
		SYNTAX  INTEGER
		MAX-ACCESS  read-write
		STATUS  current
		DESCRIPTION
			"Inhibits OMMP401 ODU Open Connection Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 341 }

	ommp401LineOduBackwardDefectIndicationAlarmInhibit  OBJECT-TYPE
		SYNTAX  INTEGER
		MAX-ACCESS  read-write
		STATUS  current
		DESCRIPTION
			"Inhibits OMMP401 ODU Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 342 }

	ommp401LineOduTcm1BackwardDefectIndicationAlarmInhibit  OBJECT-TYPE
		SYNTAX  INTEGER
		MAX-ACCESS  read-write
		STATUS  current
		DESCRIPTION
			"Inhibits OMMP401 ODU TCM1 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 343 }

	ommp401LineOduTcm2BackwardDefectIndicationAlarmInhibit  OBJECT-TYPE
		SYNTAX  INTEGER
		MAX-ACCESS  read-write
		STATUS  current
		DESCRIPTION
			"Inhibits OMMP401 ODU TCM2 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 344 }

	ommp401LineOduTcm3BackwardDefectIndicationAlarmInhibit  OBJECT-TYPE
		SYNTAX  INTEGER
		MAX-ACCESS  read-write
		STATUS  current
		DESCRIPTION
			"Inhibits OMMP401 ODU TCM3 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 345 }

	ommp401LineOduTcm4BackwardDefectIndicationAlarmInhibit  OBJECT-TYPE
		SYNTAX  INTEGER
		MAX-ACCESS  read-write
		STATUS  current
		DESCRIPTION
			"Inhibits OMMP401 ODU TCM4 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 346 }

	ommp401LineOduTcm5BackwardDefectIndicationAlarmInhibit  OBJECT-TYPE
		SYNTAX  INTEGER
		MAX-ACCESS  read-write
		STATUS  current
		DESCRIPTION
			"Inhibits OMMP401 ODU TCM5 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 347 }

	ommp401LineOduTcm6BackwardDefectIndicationAlarmInhibit  OBJECT-TYPE
		SYNTAX  INTEGER
		MAX-ACCESS  read-write
		STATUS  current
		DESCRIPTION
			"Inhibits OMMP401 ODU TCM6 Backward Defect Indication
			Alarm for the requested port
			-----------------------------
			ommp401InterfaceNumber:
			1 to 4 - CLIENT-1 to CLIENT-4
			-----------------------------
			Value:
			1 - Inhibit
			0 - Do Not Inhibit
			-----------------------------"
	::= { ommp401ConfigurationEntry 348 }

	ommp401LineOduTcm1LossOfTandemConnectionAlarmInhibit  OBJECT-TYPE
		SYNTAX  INTEGER
		MAX-ACCESS  read-write
		STATUS  current
		DESCRIPTION
			"Inhibits OMMP401 ODU TCM1 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 349 }

	ommp401LineOduTcm2LossOfTandemConnectionAlarmInhibit  OBJECT-TYPE
		SYNTAX  INTEGER
		MAX-ACCESS  read-write
		STATUS  current
		DESCRIPTION
			"Inhibits OMMP401 ODU TCM2 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 350 }

	ommp401LineOduTcm3LossOfTandemConnectionAlarmInhibit  OBJECT-TYPE
		SYNTAX  INTEGER
		MAX-ACCESS  read-write
		STATUS  current
		DESCRIPTION
			"Inhibits OMMP401 ODU TCM3 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 351 }

	ommp401LineOduTcm4LossOfTandemConnectionAlarmInhibit  OBJECT-TYPE
		SYNTAX  INTEGER
		MAX-ACCESS  read-write
		STATUS  current
		DESCRIPTION
			"Inhibits OMMP401 ODU TCM4 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 352 }

	ommp401LineOduTcm5LossOfTandemConnectionAlarmInhibit  OBJECT-TYPE
		SYNTAX  INTEGER
		MAX-ACCESS  read-write
		STATUS  current
		DESCRIPTION
			"Inhibits OMMP401 ODU TCM5 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 353 }

	ommp401LineOduTcm6LossOfTandemConnectionAlarmInhibit  OBJECT-TYPE
		SYNTAX  INTEGER
		MAX-ACCESS  read-write
		STATUS  current
		DESCRIPTION
			"Inhibits OMMP401 ODU TCM6 Loss Of Tandem Connection
			Alarm for the requested port
			-----------------------------
			ommp401InterfaceNumber:
			1 to 4 - CLIENT-1 to CLIENT-4
			-----------------------------
			Value:
			1 - Inhibit
			0 - Do Not Inhibit
			-----------------------------"
	::= { ommp401ConfigurationEntry 354 }

	ommp401LineOduTcm1BackwardIncomingAlignmentErrorAlarmInhibit  OBJECT-TYPE
		SYNTAX  INTEGER
		MAX-ACCESS  read-write
		STATUS  current
		DESCRIPTION
			"Inhibits OMMP401 ODU TCM1 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 355 }

	ommp401LineOduTcm2BackwardIncomingAlignmentErrorAlarmInhibit  OBJECT-TYPE
		SYNTAX  INTEGER
		MAX-ACCESS  read-write
		STATUS  current
		DESCRIPTION
			"Inhibits OMMP401 ODU TCM2 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 356 }

	ommp401LineOduTcm3BackwardIncomingAlignmentErrorAlarmInhibit  OBJECT-TYPE
		SYNTAX  INTEGER
		MAX-ACCESS  read-write
		STATUS  current
		DESCRIPTION
			"Inhibits OMMP401 ODU TCM3 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 357 }

	ommp401LineOduTcm4BackwardIncomingAlignmentErrorAlarmInhibit  OBJECT-TYPE
		SYNTAX  INTEGER
		MAX-ACCESS  read-write
		STATUS  current
		DESCRIPTION
			"Inhibits OMMP401 ODU TCM4 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 358 }

	ommp401LineOduTcm5BackwardIncomingAlignmentErrorAlarmInhibit  OBJECT-TYPE
		SYNTAX  INTEGER
		MAX-ACCESS  read-write
		STATUS  current
		DESCRIPTION
			"Inhibits OMMP401 ODU TCM5 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 359 }

	ommp401LineOduTcm6BackwardIncomingAlignmentErrorAlarmInhibit  OBJECT-TYPE
		SYNTAX  INTEGER
		MAX-ACCESS  read-write
		STATUS  current
		DESCRIPTION
			"Inhibits OMMP401 ODU TCM6 Locked Defect
			Alarm for the requested port
			-----------------------------
			ommp401InterfaceNumber:
			1 to 4 - CLIENT-1 to CLIENT-4
			-----------------------------
			Value:
			1 - Inhibit
			0 - Do Not Inhibit
			-----------------------------"
	::= { ommp401ConfigurationEntry 360 }

	ommp401LineOpuPayloadMismatchAlarmInhibit  OBJECT-TYPE
		SYNTAX  INTEGER
		MAX-ACCESS  read-write
		STATUS  current	
		DESCRIPTION
			"Inhibits OMMP401 OPU Payload Mismatch Alarm
			for the requested port
			-----------------------------
			ommp401InterfaceNumber:
			1 to 4 - CLIENT-1 to CLIENT-4
			-----------------------------
			Value:
			1 - Inhibit
			0 - Do Not Inhibit
			-----------------------------"
	::= { ommp401ConfigurationEntry 361 }
	
	ommp401LineOtuLossOfSignalAlarmSeverity  OBJECT-TYPE
		SYNTAX  DisplayString
		MAX-ACCESS  read-write
		STATUS  current
		DESCRIPTION
			"Set or Get the alarm severity level of the OMMP401 OTU Loss Of Signal Alarm
			for the requested port
			-----------------------------
			ommp401InterfaceNumber:
			1 to 4 - CLIENT-1 to CLIENT-4
			-----------------------------
			Value:
			critical
			major
			minor
			deferred
			-----------------------------"
	::= { ommp401ConfigurationEntry 362 }

	ommp401LineOtuLossOfFrameAlarmSeverity  OBJECT-TYPE
		SYNTAX  DisplayString
		MAX-ACCESS  read-write
		STATUS  current
		DESCRIPTION
			"Set or Get the alarm severity level of the OMMP401 OTU Loss Of Frame Alarm
			for the requested port
			-----------------------------
			ommp401InterfaceNumber:
			1 to 4 - CLIENT-1 to CLIENT-4
			-----------------------------
			Value:
			critical
			major
			minor
			deferred
			-----------------------------"
	::= { ommp401ConfigurationEntry 363 }

	ommp401LineOtuOutOfFrameAlarmSeverity  OBJECT-TYPE
		SYNTAX  DisplayString
		MAX-ACCESS  read-write
		STATUS  current
		DESCRIPTION
			"Set or Get the alarm severity level of the OMMP401 OTU Out Of Frame Alarm
			for the requested port
			-----------------------------
			ommp401InterfaceNumber:
			1 to 4 - CLIENT-1 to CLIENT-4
			-----------------------------
			Value:
			critical
			major
			minor
			deferred
			-----------------------------"
	::= { ommp401ConfigurationEntry 364 }

	ommp401LineOtuOutOfMultiFrameAlarmSeverity  OBJECT-TYPE
		SYNTAX  DisplayString
		MAX-ACCESS  read-write
		STATUS  current
		DESCRIPTION
			"Set or Get the alarm severity level of the OMMP401 OTU Out Of Multi Frame Alarm
			for the requested port
			-----------------------------
			ommp401InterfaceNumber:
			1 to 4 - CLIENT-1 to CLIENT-4
			-----------------------------
			Value:
			critical
			major
			minor
			deferred
			-----------------------------"
	::= { ommp401ConfigurationEntry 365 }

	ommp401LineOtuSignalDegradeAlarmSeverity  OBJECT-TYPE
		SYNTAX  DisplayString
		MAX-ACCESS  read-write
		STATUS  current
		DESCRIPTION
			"Set or Get the alarm severity level of the OMMP401 OTU Signal Degrade Alarm
			for the requested port
			-----------------------------
			ommp401InterfaceNumber:
			1 to 4 - CLIENT-1 to CLIENT-4
			-----------------------------
			Value:
			critical
			major
			minor
			deferred
			-----------------------------"
	::= { ommp401ConfigurationEntry 366 }

	ommp401LineOtuAlarmIndicationSignalAlarmSeverity  OBJECT-TYPE
		SYNTAX  DisplayString
		MAX-ACCESS  read-write
		STATUS  current
		DESCRIPTION
			"Set or Get the alarm severity level of the OMMP401 OTU Alarm Indication Signal Alarm
			for the requested port
			-----------------------------
			ommp401InterfaceNumber:
			1 to 4 - CLIENT-1 to CLIENT-4
			-----------------------------
			Value:
			critical
			major
			minor
			deferred
			-----------------------------"
	::= { ommp401ConfigurationEntry 367 }

	ommp401LineOtuIncomingAlignmentErrorAlarmSeverity  OBJECT-TYPE
		SYNTAX  DisplayString
		MAX-ACCESS  read-write
		STATUS  current
		DESCRIPTION
			"Set or Get the alarm severity level of the OMMP401 OTU Incoming Alignment Error Alarm
			for the requested port
			-----------------------------
			ommp401InterfaceNumber:
			1 to 4 - CLIENT-1 to CLIENT-4
			-----------------------------
			Value:
			critical
			major
			minor
			deferred
			-----------------------------"
	::= { ommp401ConfigurationEntry 368 }

	ommp401LineOtuTrailTraceIdentifierMismatchAlarmSeverity  OBJECT-TYPE
		SYNTAX  DisplayString
		MAX-ACCESS  read-write
		STATUS  current
		DESCRIPTION
			"Set or Get the alarm severity level of the OMMP401 OTU Sapi Trace Identifier Mismatch Alarm
			for the requested port
			-----------------------------
			ommp401InterfaceNumber:
			1 to 4 - CLIENT-1 to CLIENT-4
			-----------------------------
			Value:
			critical
			major
			minor
			deferred
			-----------------------------"
	::= { ommp401ConfigurationEntry 369 }
	
	ommp401LineOtuBackwardIncomingAlignmentErrorAlarmSeverity  OBJECT-TYPE
		SYNTAX  DisplayString
		MAX-ACCESS  read-write
		STATUS  current
		DESCRIPTION
			"Set or Get the alarm severity level of the OMMP401 OTU Backward Incoming Alignment Error Alarm
			for the requested port
			-----------------------------
			ommp401InterfaceNumber:
			1 to 4 - CLIENT-1 to CLIENT-4
			-----------------------------
			Value:
			critical
			major
			minor
			deferred
			-----------------------------"
	::= { ommp401ConfigurationEntry 370 }

	ommp401LineOtuBackwardDefectIndicationAlarmSeverity  OBJECT-TYPE
		SYNTAX  DisplayString
		MAX-ACCESS  read-write
		STATUS  current
		DESCRIPTION
			"Set or Get the alarm severity level of the OMMP401 OTU Backward Defect Indication Alarm
			for the requested port
			-----------------------------
			ommp401InterfaceNumber:
			1 to 4 - CLIENT-1 to CLIENT-4
			-----------------------------
			Value:
			critical
			major
			minor
			deferred
			-----------------------------"
	::= { ommp401ConfigurationEntry 371 }

	ommp401LineOduSignalDegradeAlarmSeverity  OBJECT-TYPE
		SYNTAX  DisplayString
		MAX-ACCESS  read-write
		STATUS  current
		DESCRIPTION
			"Set or Get the alarm severity level of the OMMP401 ODU Signal Degrade Alarm
			for the requested port
			-----------------------------
			ommp401InterfaceNumber:
			1 to 4 - CLIENT-1 to CLIENT-4
			-----------------------------
			Value:
			critical
			major
			minor
			deferred
			-----------------------------"
	::= { ommp401ConfigurationEntry 372 }

	ommp401LineOduAlarmIndicationSignalAlarmSeverity  OBJECT-TYPE
		SYNTAX  DisplayString
		MAX-ACCESS  read-write
		STATUS  current
		DESCRIPTION
			"Set or Get the alarm severity level of the OMMP401 ODU Alarm Indication Signal Alarm
			for the requested port
			-----------------------------
			ommp401InterfaceNumber:
			1 to 4 - CLIENT-1 to CLIENT-4
			-----------------------------
			Value:
			critical
			major
			minor
			deferred
			-----------------------------"
	::= { ommp401ConfigurationEntry 373 }

	ommp401LineOduTrailTraceIdentifierMismatchAlarmSeverity  OBJECT-TYPE
		SYNTAX  DisplayString
		MAX-ACCESS  read-write
		STATUS  current
		DESCRIPTION
			"Set or Get the alarm severity level of the OMMP401 OTU Sapi Trace Identifier Mismatch Alarm
			for the requested port
			-----------------------------
			ommp401InterfaceNumber:
			1 to 4 - CLIENT-1 to CLIENT-4
			-----------------------------
			Value:
			critical
			major
			minor
			deferred
			-----------------------------"
	::= { ommp401ConfigurationEntry 374 }

	ommp401LineOduLockedDefectAlarmSeverity  OBJECT-TYPE
		SYNTAX  DisplayString
		MAX-ACCESS  read-write
		STATUS  current
		DESCRIPTION
			"Set or Get the alarm severity level of the OMMP401 ODU Locked Defect Alarm
			for the requested port
			-----------------------------
			ommp401InterfaceNumber:
			1 to 4 - CLIENT-1 to CLIENT-4
			-----------------------------
			Value:
			critical
			major
			minor
			deferred
			-----------------------------"
	::= { ommp401ConfigurationEntry 375 }

	ommp401LineOduOpenConnectionIndicationAlarmSeverity  OBJECT-TYPE
		SYNTAX  DisplayString
		MAX-ACCESS  read-write
		STATUS  current
		DESCRIPTION
			"Set or Get the alarm severity level of the OMMP401 ODU Open Connection Indication
			Alarm for the requested port
			-----------------------------
			ommp401InterfaceNumber:
			1 to 4 - CLIENT-1 to CLIENT-4
			-----------------------------
			Value:
			critical
			major
			minor
			deferred
			-----------------------------"
	::= { ommp401ConfigurationEntry 376 }

	ommp401LineOduBackwardDefectIndicationAlarmSeverity  OBJECT-TYPE
		SYNTAX  DisplayString
		MAX-ACCESS  read-write
		STATUS  current
		DESCRIPTION
			"Set or Get the alarm severity level of the OMMP401 ODU Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 377 }

	ommp401LineOduTcm1BackwardDefectIndicationAlarmSeverity  OBJECT-TYPE
		SYNTAX  DisplayString
		MAX-ACCESS  read-write
		STATUS  current
		DESCRIPTION
			"Set or Get the alarm severity level of the OMMP401 ODU TCM1 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 378 }

	ommp401LineOduTcm2BackwardDefectIndicationAlarmSeverity  OBJECT-TYPE
		SYNTAX  DisplayString
		MAX-ACCESS  read-write
		STATUS  current
		DESCRIPTION
			"Set or Get the alarm severity level of the OMMP401 ODU TCM2 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 379 }

	ommp401LineOduTcm3BackwardDefectIndicationAlarmSeverity  OBJECT-TYPE
		SYNTAX  DisplayString
		MAX-ACCESS  read-write
		STATUS  current
		DESCRIPTION
			"Set or Get the alarm severity level of the OMMP401 ODU TCM3 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 380 }

	ommp401LineOduTcm4BackwardDefectIndicationAlarmSeverity  OBJECT-TYPE
		SYNTAX  DisplayString
		MAX-ACCESS  read-write
		STATUS  current
		DESCRIPTION
			"Set or Get the alarm severity level of the OMMP401 ODU TCM4 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 381 }

	ommp401LineOduTcm5BackwardDefectIndicationAlarmSeverity  OBJECT-TYPE
		SYNTAX  DisplayString
		MAX-ACCESS  read-write
		STATUS  current
		DESCRIPTION
			"Set or Get the alarm severity level of the OMMP401 ODU TCM5 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 382 }

	ommp401LineOduTcm6BackwardDefectIndicationAlarmSeverity  OBJECT-TYPE
		SYNTAX  DisplayString
		MAX-ACCESS  read-write
		STATUS  current
		DESCRIPTION
			"Set or Get the alarm severity level of the OMMP401 ODU TCM6 Backward Defect Indication
			Alarm for the requested port
			-----------------------------
			ommp401InterfaceNumber:
			1 to 4 - CLIENT-1 to CLIENT-4
			-----------------------------
			Value:
			critical
			major
			minor
			deferred
			-----------------------------"
	::= { ommp401ConfigurationEntry 383 }

	ommp401LineOduTcm1LossOfTandemConnectionAlarmSeverity  OBJECT-TYPE
		SYNTAX  DisplayString
		MAX-ACCESS  read-write
		STATUS  current
		DESCRIPTION
			"Set or Get the alarm severity level of the OMMP401 ODU TCM1 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 384 }

	ommp401LineOduTcm2LossOfTandemConnectionAlarmSeverity  OBJECT-TYPE
		SYNTAX  DisplayString
		MAX-ACCESS  read-write
		STATUS  current
		DESCRIPTION
			"Set or Get the alarm severity level of the OMMP401 ODU TCM2 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 385 }

	ommp401LineOduTcm3LossOfTandemConnectionAlarmSeverity  OBJECT-TYPE
		SYNTAX  DisplayString
		MAX-ACCESS  read-write
		STATUS  current
		DESCRIPTION
			"Set or Get the alarm severity level of the OMMP401 ODU TCM3 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 386 }

	ommp401LineOduTcm4LossOfTandemConnectionAlarmSeverity  OBJECT-TYPE
		SYNTAX  DisplayString
		MAX-ACCESS  read-write
		STATUS  current
		DESCRIPTION
			"Set or Get the alarm severity level of the OMMP401 ODU TCM4 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 387 }

	ommp401LineOduTcm5LossOfTandemConnectionAlarmSeverity  OBJECT-TYPE
		SYNTAX  DisplayString
		MAX-ACCESS  read-write
		STATUS  current
		DESCRIPTION
			"Set or Get the alarm severity level of the OMMP401 ODU TCM5 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 388 }

	ommp401LineOduTcm6LossOfTandemConnectionAlarmSeverity  OBJECT-TYPE
		SYNTAX  DisplayString
		MAX-ACCESS  read-write
		STATUS  current
		DESCRIPTION
			"Set or Get the alarm severity level of the OMMP401 ODU TCM6 Loss Of Tandem Connection
			Alarm for the requested port
			-----------------------------
			ommp401InterfaceNumber:
			1 to 4 - CLIENT-1 to CLIENT-4
			-----------------------------
			Value:
			critical
			major
			minor
			deferred
			-----------------------------"
	::= { ommp401ConfigurationEntry 389 }

	ommp401LineOduTcm1BackwardIncomingAlignmentErrorAlarmSeverity  OBJECT-TYPE
		SYNTAX  DisplayString
		MAX-ACCESS  read-write
		STATUS  current
		DESCRIPTION
			"Set or Get the alarm severity level of the OMMP401 ODU TCM1 Locked Defect
			Alarm for the requested port
			-----------------------------
			ommp401InterfaceNumber:
			1 to 4 - CLIENT-1 to CLIENT-4
			-----------------------------
			Value:
			critical
			major
			minor
			deferred
			-----------------------------"
	::= { ommp401ConfigurationEntry 390 }

	ommp401LineOduTcm2BackwardIncomingAlignmentErrorAlarmSeverity  OBJECT-TYPE
		SYNTAX  DisplayString
		MAX-ACCESS  read-write
		STATUS  current
		DESCRIPTION
			"Set or Get the alarm severity level of the OMMP401 ODU TCM2 Locked Defect
			Alarm for the requested port
			-----------------------------
			ommp401InterfaceNumber:
			1 to 4 - CLIENT-1 to CLIENT-4
			-----------------------------
			Value:
			critical
			major
			minor
			deferred
			-----------------------------"
	::= { ommp401ConfigurationEntry 391 }

	ommp401LineOduTcm3BackwardIncomingAlignmentErrorAlarmSeverity  OBJECT-TYPE
		SYNTAX  DisplayString
		MAX-ACCESS  read-write
		STATUS  current
		DESCRIPTION
			"Set or Get the alarm severity level of the OMMP401 ODU TCM3 Locked Defect
			Alarm for the requested port
			-----------------------------
			ommp401InterfaceNumber:
			1 to 4 - CLIENT-1 to CLIENT-4
			-----------------------------
			Value:
			critical
			major
			minor
			deferred
			-----------------------------"
	::= { ommp401ConfigurationEntry 392 }

	ommp401LineOduTcm4BackwardIncomingAlignmentErrorAlarmSeverity  OBJECT-TYPE
		SYNTAX  DisplayString
		MAX-ACCESS  read-write
		STATUS  current
		DESCRIPTION
			"Set or Get the alarm severity level of the OMMP401 ODU TCM4 Locked Defect
			Alarm for the requested port
			-----------------------------
			ommp401InterfaceNumber:
			1 to 4 - CLIENT-1 to CLIENT-4
			-----------------------------
			Value:
			critical
			major
			minor
			deferred
			-----------------------------"
	::= { ommp401ConfigurationEntry 393 }

	ommp401LineOduTcm5BackwardIncomingAlignmentErrorAlarmSeverity  OBJECT-TYPE
		SYNTAX  DisplayString
		MAX-ACCESS  read-write
		STATUS  current
		DESCRIPTION
			"Set or Get the alarm severity level of the OMMP401 ODU TCM5 Locked Defect
			Alarm for the requested port
			-----------------------------
			ommp401InterfaceNumber:
			1 to 4 - CLIENT-1 to CLIENT-4
			-----------------------------
			Value:
			critical
			major
			minor
			deferred
			-----------------------------"
	::= { ommp401ConfigurationEntry 394 }

	ommp401LineOduTcm6BackwardIncomingAlignmentErrorAlarmSeverity  OBJECT-TYPE
		SYNTAX  DisplayString
		MAX-ACCESS  read-write
		STATUS  current
		DESCRIPTION
			"Set or Get the alarm severity level of the OMMP401 ODU TCM6 Locked Defect
			Alarm for the requested port
			-----------------------------
			ommp401InterfaceNumber:
			1 to 4 - CLIENT-1 to CLIENT-4
			-----------------------------
			Value:
			critical
			major
			minor
			deferred
			-----------------------------"
	::= { ommp401ConfigurationEntry 395 }

	ommp401LineOpuPayloadMismatchAlarmSeverity  OBJECT-TYPE
		SYNTAX  DisplayString
		MAX-ACCESS  read-write
		STATUS  current
		DESCRIPTION
			"Set or Get the alarm severity level of the OMMP401 OPU Payload Mismatch Alarm
			for the requested port
			-----------------------------
			ommp401InterfaceNumber:
			1 to 4 - CLIENT-1 to CLIENT-4
			-----------------------------
			Value:
			critical
			major
			minor
			deferred
			-----------------------------"
	::= { ommp401ConfigurationEntry 396 }

	ommp401ConfigurationTableRowStatus OBJECT-TYPE
              SYNTAX      RowStatus
              MAX-ACCESS  read-write
              STATUS      current
              DESCRIPTION
			"*****************************
			This is MIB realted property,
			NOT to be considered as a card property
			*****************************"
              ::= { ommp401ConfigurationEntry 397 }	


--*****************************************************************************
--				    ALARMS
--*****************************************************************************
                 
	ommp401AlarmQueryTable OBJECT-TYPE
	      SYNTAX  SEQUENCE OF Ommp401AlarmQueryEntry 
              MAX-ACCESS  not-accessible
              STATUS  current
              DESCRIPTION
                      "Gives Optical and Signal Alarms status of the OMMP401 card"
		::= { ommp401AlarmQuery 1 }	

	ommp401AlarmQueryEntry   OBJECT-TYPE
              SYNTAX  Ommp401AlarmQueryEntry 
              MAX-ACCESS  not-accessible
              STATUS  current
              DESCRIPTION 
              	""
		INDEX   { node, rack , subRack , slot , ommp401InterfaceNumber }
		::= { ommp401AlarmQueryTable 1 }
	
	Ommp401AlarmQueryEntry ::= 
			SEQUENCE {					
					ommp401Cfp2InputPowerFailureAlarm					DisplayString,
					ommp401Cfp2OutputPowerFailureAlarm					DisplayString,
					ommp401Cfp2HighTemperatureAlarm					DisplayString,
					ommp401Cfp2LowTemperatureAlarm					DisplayString,
					ommp401Cfp2HighTemperatureWarning					DisplayString,
					ommp401Cfp2LowTemperatureWarning					DisplayString,
					ommp401Cfp2InputHighPowerAlarm					DisplayString,
					ommp401Cfp2InputLowPowerAlarm						DisplayString,
					ommp401Cfp2InputHighPowerWarning					DisplayString,
					ommp401Cfp2InputLowPowerWarning					DisplayString,
					ommp401Cfp2OutputHighPowerAlarm					DisplayString,
					ommp401Cfp2OutputLowPowerAlarm					DisplayString,
					ommp401Cfp2OutputHighPowerWarning					DisplayString,
					ommp401Cfp2OutputLowPowerWarning					DisplayString,
					ommp401Cfp2HighSupplyVoltageAlarm					DisplayString,
					ommp401Cfp2LowSupplyVoltageAlarm					DisplayString,
					ommp401Cfp2HighSupplyVoltageWarning					DisplayString,
					ommp401Cfp2LowSupplyVoltageWarning					DisplayString,
					ommp401Cfp2PresenceAbsenceNotification				DisplayString,
					ommp401Qsfp28InputPowerFailureAlarm					DisplayString,
					ommp401Qsfp28OutputPowerFailureAlarm					DisplayString,
					ommp401Qsfp28HighTemperatureAlarm					DisplayString,
					ommp401Qsfp28LowTemperatureAlarm					DisplayString,
					ommp401Qsfp28HighTemperatureWarning					DisplayString,
					ommp401Qsfp28LowTemperatureWarning					DisplayString,
					ommp401Qsfp28HighBiasCurrentAlarm					DisplayString,
					ommp401Qsfp28LowBiasCurrentAlarm					DisplayString,
					ommp401Qsfp28HighBiasCurrentWarning					DisplayString,
					ommp401Qsfp28LowBiasCurrentWarning					DisplayString,
					ommp401Qsfp28InputHighPowerAlarm					DisplayString,
					ommp401Qsfp28InputLowPowerAlarm						DisplayString,
					ommp401Qsfp28InputHighPowerWarning					DisplayString,
					ommp401Qsfp28InputLowPowerWarning					DisplayString,
					ommp401Qsfp28OutputHighPowerAlarm					DisplayString,
					ommp401Qsfp28OutputLowPowerAlarm					DisplayString,
					ommp401Qsfp28OutputHighPowerWarning					DisplayString,
					ommp401Qsfp28OutputLowPowerWarning					DisplayString,
					ommp401Qsfp28HighSupplyVoltageAlarm					DisplayString,
					ommp401Qsfp28LowSupplyVoltageAlarm					DisplayString,
					ommp401Qsfp28HighSupplyVoltageWarning					DisplayString,
					ommp401Qsfp28LowSupplyVoltageWarning					DisplayString,
					ommp401Qsfp28PresenceAbsenceNotification				DisplayString,
					ommp401OtuLossOfSignalAlarm				DisplayString,
					ommp401OtuLossOfFrameAlarm				DisplayString,
					ommp401OtuOutOfFrameAlarm				DisplayString,
					ommp401OtuLossOfMultiFrameAlarm			DisplayString,
					ommp401OtuOutOfMultiFrameAlarm			DisplayString,
					ommp401OtuSignalFailAlarm				DisplayString,
					ommp401OtuSignalDegradeAlarm				DisplayString,
					ommp401OtuAlarmIndicationSignalAlarm			DisplayString,
					ommp401OtuIncomingAlignmentErrorAlarm			DisplayString,
					ommp401OtuTrailTraceIdentifierMismatchAlarm		DisplayString,
					ommp401OtuBackwardIncomingAlignmentErrorAlarm		DisplayString,
					ommp401OtuBackwardDefectIndicationAlarm		DisplayString,
					ommp401OduSignalFailAlarm				DisplayString,
					ommp401OduSignalDegradeAlarm				DisplayString,
					ommp401OduAlarmIndicationSignalAlarm			DisplayString,
					ommp401OduTrailTraceIdentifierMismatchAlarm		DisplayString,
					ommp401OduLockedDefectAlarm				DisplayString,
					ommp401OduOpenConnectionIndicationAlarm		DisplayString,
					ommp401OduBackwardDefectIndicationAlarm		DisplayString,
					ommp401OduTcm1BackwardDefectIndicationAlarm		DisplayString,
					ommp401OduTcm2BackwardDefectIndicationAlarm		DisplayString,
					ommp401OduTcm3BackwardDefectIndicationAlarm		DisplayString,
					ommp401OduTcm4BackwardDefectIndicationAlarm		DisplayString,
					ommp401OduTcm5BackwardDefectIndicationAlarm		DisplayString,
					ommp401OduTcm6BackwardDefectIndicationAlarm		DisplayString,
					ommp401OduTcm1BackwardIncomingAlignmentErrorAlarm		DisplayString,
					ommp401OduTcm2BackwardIncomingAlignmentErrorAlarm		DisplayString,
					ommp401OduTcm3BackwardIncomingAlignmentErrorAlarm		DisplayString,
					ommp401OduTcm4BackwardIncomingAlignmentErrorAlarm		DisplayString,
					ommp401OduTcm5BackwardIncomingAlignmentErrorAlarm		DisplayString,
					ommp401OduTcm6BackwardIncomingAlignmentErrorAlarm		DisplayString,
					ommp401OduTcm1LossOfTandemConnectionAlarm		DisplayString,
					ommp401OduTcm2LossOfTandemConnectionAlarm		DisplayString,
					ommp401OduTcm3LossOfTandemConnectionAlarm		DisplayString,
					ommp401OduTcm4LossOfTandemConnectionAlarm		DisplayString,
					ommp401OduTcm5LossOfTandemConnectionAlarm		DisplayString,
					ommp401OduTcm6LossOfTandemConnectionAlarm		DisplayString,
					ommp401OpuPayloadMismatchAlarm				DisplayString,
					ommp401EthernetLossOfSignalAlarm				DisplayString,
					ommp401EthernetIngressRemoteFaultAlarm			DisplayString,
					ommp401EthernetIngressPcsErrorBlocksDetectedAlarm	DisplayString,
					ommp401EthernetIngressPcsBipErrorsDetectedAlarm		DisplayString,
					ommp401EthernetIngressOpuClientServerFailIndicationAlarm	DisplayString,
					ommp401EthernetIngressLocalFaultAlarm			DisplayString,
					ommp401EthernetIngressLossOfAlignmentAlarm		DisplayString,
					ommp401EthernetIngressLossOfAlignmentMarkerLockAlarm	DisplayString,
					ommp401EthernetIngressLossOfBlockLockAlarm		DisplayString,
					ommp401EthernetEgressRemoteFaultAlarm			DisplayString,
					ommp401EthernetEgressPcsErrorBlocksDetectedAlarm		DisplayString,
					ommp401EthernetEgressPcsBipErrorsDetectedAlarm		DisplayString,
					ommp401EthernetEgressHighBerAlarm			DisplayString,
					ommp401EthernetEgressLocalFaultAlarm			DisplayString,
					ommp401EthernetEgressLossOfAlignmentAlarm		DisplayString,
					ommp401EthernetEgressLossOfAlignmentMarkerLockAlarm	DisplayString,
					ommp401EthernetEgressLossOfBlockLockAlarm		DisplayString,
					ommp401LineOtuLossOfSignalAlarm		DisplayString,
					ommp401LineOtuLossOfFrameAlarm		DisplayString,
					ommp401LineOtuOutOfFrameAlarm		DisplayString,
					ommp401LineOtuLossOfMultiFrameAlarm		DisplayString,
					ommp401LineOtuOutOfMultiFrameAlarm		DisplayString,
					ommp401LineOtuSignalDegradeAlarm		DisplayString,
					ommp401LineOtuAlarmIndicationSignalAlarm		DisplayString,
					ommp401LineOtuIncomingAlignmentErrorAlarm		DisplayString,
					ommp401LineOtuTrailTraceIdentifierMismatchAlarm		DisplayString,
					ommp401LineOtuBackwardIncomingAlignmentErrorAlarm		DisplayString,
					ommp401LineOtuBackwardDefectIndicationAlarm		DisplayString,
					ommp401LineOduSignalDegradeAlarm		DisplayString,
					ommp401LineOduAlarmIndicationSignalAlarm		DisplayString,
					ommp401LineOduTrailTraceIdentifierMismatchAlarm		DisplayString,
					ommp401LineOduLockedDefectAlarm		DisplayString,
					ommp401LineOduOpenConnectionIndicationAlarm		DisplayString,
					ommp401LineOduBackwardDefectIndicationAlarm		DisplayString,
					ommp401LineOduTcm1BackwardDefectIndicationAlarm		DisplayString,
					ommp401LineOduTcm2BackwardDefectIndicationAlarm		DisplayString,
					ommp401LineOduTcm3BackwardDefectIndicationAlarm		DisplayString,
					ommp401LineOduTcm4BackwardDefectIndicationAlarm		DisplayString,
					ommp401LineOduTcm5BackwardDefectIndicationAlarm		DisplayString,
					ommp401LineOduTcm6BackwardDefectIndicationAlarm		DisplayString,
					ommp401LineOduTcm1BackwardIncomingAlignmentErrorAlarm		DisplayString,
					ommp401LineOduTcm2BackwardIncomingAlignmentErrorAlarm		DisplayString,
					ommp401LineOduTcm3BackwardIncomingAlignmentErrorAlarm		DisplayString,
					ommp401LineOduTcm4BackwardIncomingAlignmentErrorAlarm		DisplayString,
					ommp401LineOduTcm5BackwardIncomingAlignmentErrorAlarm		DisplayString,
					ommp401LineOduTcm6BackwardIncomingAlignmentErrorAlarm		DisplayString,
					ommp401LineOduTcm1LossOfTandemConnectionAlarm		DisplayString,
					ommp401LineOduTcm2LossOfTandemConnectionAlarm		DisplayString,
					ommp401LineOduTcm3LossOfTandemConnectionAlarm		DisplayString,
					ommp401LineOduTcm4LossOfTandemConnectionAlarm		DisplayString,
					ommp401LineOduTcm5LossOfTandemConnectionAlarm		DisplayString,
					ommp401LineOduTcm6LossOfTandemConnectionAlarm		DisplayString,
					ommp401LineOpuPayloadMismatchAlarm		DisplayString,
					ommp401AlarmQueryTableRowStatus					RowStatus
		}

--*****************************************************************************
--				OPTICAL	ALARMS
--***************************************************************************** 

	ommp401Cfp2InputPowerFailureAlarm OBJECT-TYPE
              SYNTAX  DisplayString
              MAX-ACCESS  read-only
              STATUS  current
              DESCRIPTION
			"If optical input power at requested interface is less than
			-20dbm, this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 1 }

	ommp401Cfp2OutputPowerFailureAlarm OBJECT-TYPE
              SYNTAX  DisplayString
              MAX-ACCESS  read-only
              STATUS  current
              DESCRIPTION
			"If optical output power at requested interface is less than
			-10dbm, this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 2 }

	ommp401Cfp2HighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 3 }

	ommp401Cfp2LowTemperatureAlarm OBJECT-TYPE
              SYNTAX  DisplayString
              MAX-ACCESS  read-only
              STATUS  current
              DESCRIPTION
			"If optical temperature at requested interface is lower 
			than the Low Temperature Alarm Threshold, alarm will be 
			generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 4 }

	ommp401Cfp2HighTemperatureWarning OBJECT-TYPE
              SYNTAX  DisplayString
              MAX-ACCESS  read-only
              STATUS  current
              DESCRIPTION
			"If optical temperature at requested interface is greater
			than the High Temperature Warning Threshold, this alarm 
			will be generated.
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 5 }

	ommp401Cfp2LowTemperatureWarning OBJECT-TYPE
              SYNTAX  DisplayString
              MAX-ACCESS  read-only
              STATUS  current
              DESCRIPTION
			"If optical temperature at requested interface is lesser
			than the Low Temperature Warning Threshold, this alarm 
			will be generated.
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 6 }

	ommp401Cfp2InputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 7 }

	ommp401Cfp2InputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 8 }

	ommp401Cfp2InputHighPowerWarning OBJECT-TYPE
              SYNTAX  DisplayString
              MAX-ACCESS  read-only
              STATUS  current
              DESCRIPTION
			"If optical Input power at requested interface is 
			greater than the High Input Power Warning Threshold, 
			this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 9 }

	ommp401Cfp2InputLowPowerWarning OBJECT-TYPE
              SYNTAX  DisplayString
              MAX-ACCESS  read-only
              STATUS  current
              DESCRIPTION
			"If optical Input power at requested interface is lesser
			than the Low Input Power Warning Threshold, this alarm 
			will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 10 }

	ommp401Cfp2OutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 11 }

	ommp401Cfp2OutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp401InterfaceNumber:
			1 to 4 - CLIENT-1 to CLIENT-4
			5 - LINE-1
			-----------------------------
			Values :
			If Alarm is Present - Date and Time Stamp
				    eg:2017-5-18,9:47:20.0,+5:30
			If Alarm is Absent  - 0
			-----------------------------"
		::= { ommp401AlarmQueryEntry 12 }

	ommp401Cfp2OutputHighPowerWarning OBJECT-TYPE
              SYNTAX  DisplayString
              MAX-ACCESS  read-only
              STATUS  current
              DESCRIPTION
			"If optical Output power at requested interface is 
			greater than the High Output Power Warning Threshold, 
			this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 13 }

	ommp401Cfp2OutputLowPowerWarning OBJECT-TYPE
              SYNTAX  DisplayString
              MAX-ACCESS  read-only
              STATUS  current
              DESCRIPTION
			"If optical Output power at requested interface is 
			lesser than the Low Output Power Warning Threshold, 
			this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 14 }

	ommp401Cfp2HighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 15 }

	ommp401Cfp2LowSupplyVoltageAlarm OBJECT-TYPE
              SYNTAX  DisplayString
              MAX-ACCESS  read-only
              STATUS  current
              DESCRIPTION
			"If optical Supply Voltage at requested interface is 
			lesser than the Low Supply Voltage Alarm Threshold, 
			this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 16 }

	ommp401Cfp2HighSupplyVoltageWarning OBJECT-TYPE
              SYNTAX  DisplayString
              MAX-ACCESS  read-only
              STATUS  current
              DESCRIPTION
			"If optical Supply Voltage at requested interface is 
			higher than the High Supply Voltage Warning Threshold,
			this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 17 }

	ommp401Cfp2LowSupplyVoltageWarning OBJECT-TYPE
              SYNTAX  DisplayString
              MAX-ACCESS  read-only
              STATUS  current
              DESCRIPTION
			"If optical Supply Voltage at requested interface is 
			lesser than the Low Supply Voltage Warning Threshold, 
			this alarm will be generated
			-----------------------------
			ommp401InterfaceNumber:
			5 - LINE-1
			-----------------------------
			Values :
			If Alarm is Present - Date and Time Stamp
				    eg:2017-5-18,9:47:20.0,+5:30
			If Alarm is Absent  - 0
			-----------------------------"
		::= { ommp401AlarmQueryEntry 18 }

	ommp401Cfp2PresenceAbsenceNotification OBJECT-TYPE
              SYNTAX  DisplayString
              MAX-ACCESS  read-only
              STATUS  current
              DESCRIPTION
			"Whenever the CFP2 is jacked in or jacked out, this 
			notification is generated.
			-----------------------------
			ommp401InterfaceNumber:
			5 - LINE-1
			-----------------------------
			Values :
			If Alarm is Present(module absent) - Date and Time Stamp
				    eg:2017-5-18,9:47:20.0,+5:30
			If Alarm is Absent(module present) - 0
			-----------------------------"
		::= { ommp401AlarmQueryEntry 19 }

	ommp401Qsfp28InputPowerFailureAlarm OBJECT-TYPE
              SYNTAX  DisplayString
              MAX-ACCESS  read-only
              STATUS  current
              DESCRIPTION
			"If optical input power at requested interface is less than
			-20dbm, this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 20 }

	ommp401Qsfp28OutputPowerFailureAlarm OBJECT-TYPE
              SYNTAX  DisplayString
              MAX-ACCESS  read-only
              STATUS  current
              DESCRIPTION
			"If optical output power at requested interface is less than
			-10dbm, this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 21 }

	ommp401Qsfp28HighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 22 }

	ommp401Qsfp28LowTemperatureAlarm OBJECT-TYPE
              SYNTAX  DisplayString
              MAX-ACCESS  read-only
              STATUS  current
              DESCRIPTION
			"If optical temperature at requested interface is lesser 
			than the Low Temperature Alarm Threshold, alarm will be 
			generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 23 }

	ommp401Qsfp28HighTemperatureWarning OBJECT-TYPE
              SYNTAX  DisplayString
              MAX-ACCESS  read-only
              STATUS  current
              DESCRIPTION
			"If optical temperature at requested interface is greater
			than the High Temperature Warning Threshold, this alarm 
			will be generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 24 }

	ommp401Qsfp28LowTemperatureWarning OBJECT-TYPE
              SYNTAX  DisplayString
              MAX-ACCESS  read-only
              STATUS  current
              DESCRIPTION
			"If optical temperature at requested interface is lesser
			than the Low Temperature Warning Threshold, this alarm 
			will be generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 25 }

	ommp401Qsfp28HighBiasCurrentAlarm OBJECT-TYPE
              SYNTAX  DisplayString
              MAX-ACCESS  read-only
              STATUS  current
              DESCRIPTION
			"If optical transmit bias current at requested interface
			is greater than the High Bias Current Alarm Threshold, 
			this alarm will be generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 26 }

	ommp401Qsfp28LowBiasCurrentAlarm OBJECT-TYPE
              SYNTAX  DisplayString
              MAX-ACCESS  read-only
              STATUS  current
              DESCRIPTION
			"If optical transmit bias current at requested interface
			is lesser than the Low Bias Current Alarm Threshold, 
			this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 27 }

	ommp401Qsfp28HighBiasCurrentWarning OBJECT-TYPE
              SYNTAX  DisplayString
              MAX-ACCESS  read-only
              STATUS  current
              DESCRIPTION
			"If optical transmit bias current at requested interface
			is greater than the High Bias Current Warning Threshold,
			this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 28 }

	ommp401Qsfp28LowBiasCurrentWarning OBJECT-TYPE
              SYNTAX  DisplayString
              MAX-ACCESS  read-only
              STATUS  current
              DESCRIPTION
			"If optical transmit bias current at requested interface
			is lesser than the Low Bias Current Warning Threshold, 
			this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 29 }

	ommp401Qsfp28InputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 30 }

	ommp401Qsfp28InputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 31 }

	ommp401Qsfp28InputHighPowerWarning OBJECT-TYPE
              SYNTAX  DisplayString
              MAX-ACCESS  read-only
              STATUS  current
              DESCRIPTION
			"If optical Input power at requested interface is 
			greater than the High Input Power Warning Threshold, 
			this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 32 }

	ommp401Qsfp28InputLowPowerWarning OBJECT-TYPE
              SYNTAX  DisplayString
              MAX-ACCESS  read-only
              STATUS  current
              DESCRIPTION
			"If optical Input power at requested interface is lesser
			than the Low Input Power Warning Threshold, this alarm 
			will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 33 }

	ommp401Qsfp28OutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 34 }

	ommp401Qsfp28OutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 35 }

	ommp401Qsfp28OutputHighPowerWarning OBJECT-TYPE
              SYNTAX  DisplayString
              MAX-ACCESS  read-only
              STATUS  current
              DESCRIPTION
			"If optical Output power at requested interface is 
			greater than the High Output Power Warning Threshold, 
			this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 36 }

	ommp401Qsfp28OutputLowPowerWarning OBJECT-TYPE
              SYNTAX  DisplayString
              MAX-ACCESS  read-only
              STATUS  current
              DESCRIPTION
			"If optical Output power at requested interface is 
			lesser than the Low Output Power Warning Threshold, this
			alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 37 }

	ommp401Qsfp28HighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 38 }

	ommp401Qsfp28LowSupplyVoltageAlarm OBJECT-TYPE
              SYNTAX  DisplayString
              MAX-ACCESS  read-only
              STATUS  current
              DESCRIPTION
			"If optical Supply Voltage at requested interface is 
			lesser than the Low Supply Voltage Alarm Threshold, this
			alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 39 }

	ommp401Qsfp28HighSupplyVoltageWarning OBJECT-TYPE
              SYNTAX  DisplayString
              MAX-ACCESS  read-only
              STATUS  current
              DESCRIPTION
			"If optical Supply Voltage at requested interface is 
			greater than the High Supply Voltage Warning Threshold, 
			this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 40 }

	ommp401Qsfp28LowSupplyVoltageWarning OBJECT-TYPE
              SYNTAX  DisplayString
              MAX-ACCESS  read-only
              STATUS  current
              DESCRIPTION
			"If optical Supply Voltage at requested interface is 
			lesser than the Low Supply Voltage Warning Threshold, 
			this alarm will be generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 41 }

	ommp401Qsfp28PresenceAbsenceNotification OBJECT-TYPE
              SYNTAX  DisplayString
              MAX-ACCESS  read-only
              STATUS  current
              DESCRIPTION
			"Whenever the QSFP28 is jacked in or jacked out, this 
			notification is generated.
			-----------------------------
			ommp401InterfaceNumber:
			1 to 4 - CLIENT-1 to CLIENT-4
			-----------------------------
			Values :
			If Alarm is Present(module absent) - Date and Time Stamp
				    eg:2017-5-18,9:47:20.0,+5:30
			If Alarm is Absent(module present) - 0
			-----------------------------"
		::= { ommp401AlarmQueryEntry 42 }

	ommp401OtuLossOfSignalAlarm OBJECT-TYPE
              SYNTAX  DisplayString
              MAX-ACCESS  read-only
              STATUS  current
              DESCRIPTION
			"For port configured with OTU4/OTUC4 traffic,
			if there is no signal received then OTU-LOS Alarm
			is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 43 }

	ommp401OtuLossOfFrameAlarm OBJECT-TYPE
              SYNTAX  DisplayString
              MAX-ACCESS  read-only
              STATUS  current
              DESCRIPTION
			"For port configured with OTU4/OTUC4 traffic, if
			OTU4/OTUC4 frame received are in out-of-frame (OOF)
			state for 3 ms, then OTU-LOF Alarm is generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 44 }

	ommp401OtuOutOfFrameAlarm OBJECT-TYPE
              SYNTAX  DisplayString
              MAX-ACCESS  read-only
              STATUS  current
              DESCRIPTION
			"For port configured with OTU4/OTUC4 traffic, if 5
			consecutive OTU4/OTUC4 frames are received with
			invalid framing patterns then OOF Alarm is
			generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 45 }

	ommp401OtuLossOfMultiFrameAlarm OBJECT-TYPE
              SYNTAX  DisplayString
              MAX-ACCESS  read-only
              STATUS  current
              DESCRIPTION
			"For port configured with OTU4/OTUC4 traffic, if 
			OTU4/OTUC4 frame received are in Out-of-multiframe
			(OOM) state for 3 ms then LOM Alarm is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 46 }

	ommp401OtuOutOfMultiFrameAlarm OBJECT-TYPE
              SYNTAX  DisplayString
              MAX-ACCESS  read-only
              STATUS  current
              DESCRIPTION
			"For port configured with OTU4/OTUC4 traffic, if the
			received MFAS does not match with the expected multi
			frame number for five consecutive frames then
			OOM Alarm is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 47 }

	ommp401OtuSignalFailAlarm OBJECT-TYPE
              SYNTAX  DisplayString
              MAX-ACCESS  read-only
              STATUS  current
              DESCRIPTION
			"For port configured with OTU4/OTUC4 traffic, 
			OTU SF alarm is generated when BIP errors evaluated by 
			SM field of OTU4/OTUC4 frame exceeds the 
			'ommp401OtuSignalFailThreshold' threshold
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 48 }

	ommp401OtuSignalDegradeAlarm OBJECT-TYPE
              SYNTAX  DisplayString
              MAX-ACCESS  read-only
              STATUS  current
              DESCRIPTION
			"For port configured with OTU4/OTUC4 traffic, 
			OTU SD alarm is generated when BIP errors evaluated by 
			SM field of OTU4/OTUC4 frame exceeds the 
			'ommp401OtuSignalDegradeThreshold' threshold.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 49 }

	ommp401OtuAlarmIndicationSignalAlarm OBJECT-TYPE
              SYNTAX  DisplayString
              MAX-ACCESS  read-only
              STATUS  current
              DESCRIPTION
			"For port configured with OTU4/OTUC4 traffic,
			OTU-AIS is generated and transmitted in forward 
			direction, when LOS has been detected at far-end port.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 50 }

	ommp401OtuIncomingAlignmentErrorAlarm OBJECT-TYPE
              SYNTAX  DisplayString
              MAX-ACCESS  read-only
              STATUS  current
              DESCRIPTION
			"For port configured with OTU4/OTUC4 traffic, IAE alarms
			shall be declared if the IAE bit in the SM overhead
			field (byte 3, bit 6) is 1 for 5 consecutive frames. 
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 51 }

	ommp401OtuTrailTraceIdentifierMismatchAlarm OBJECT-TYPE
              SYNTAX  DisplayString
              MAX-ACCESS  read-only
              STATUS  current
              DESCRIPTION
			"For port configured with OTU4/OTUC4 traffic, when there
			is a mismatch between the incoming and the expected
			Sapi(TTI) at the SM section,
			OTU-Sapi alarm is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 52 }

	ommp401OtuBackwardIncomingAlignmentErrorAlarm OBJECT-TYPE
              SYNTAX  DisplayString
              MAX-ACCESS  read-only
              STATUS  current
              DESCRIPTION
			"For port configured with OTU4/OTUC4 traffic, 
			the presence of this alarm conveys that an incoming
			alignment error(IAE) condition is detected
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 53 }

	ommp401OtuBackwardDefectIndicationAlarm OBJECT-TYPE
              SYNTAX  DisplayString
              MAX-ACCESS  read-only
              STATUS  current
              DESCRIPTION
			"For port configured with OTU4/OTUC4 traffic,
			the presence of this alarm conveys that a
			a defect like LOS, LOF, LOM has been detected in the
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 54 }

	ommp401OduSignalFailAlarm OBJECT-TYPE
              SYNTAX  DisplayString
              MAX-ACCESS  read-only
              STATUS  current
              DESCRIPTION
			"For port configured with OTU4/OTUC4 traffic, ODU-SF
			alarm is generated when BIP errors evaluated by 
			PM field of OTU4 frame exceeds the 
			'ommp401OduSignalFailThreshold' threshold.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 55 }

	ommp401OduSignalDegradeAlarm OBJECT-TYPE
              SYNTAX  DisplayString
              MAX-ACCESS  read-only
              STATUS  current
              DESCRIPTION
			"For port configured with OTU4/OTUC4 traffic,ODU-SD
			alarm is generated when BIP errors evaluated by 
			PM field of OTU4 frame exceeds the 	
			'ommp401OduSignalDegradeThreshold' threshold.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 56 }

	ommp401OduAlarmIndicationSignalAlarm OBJECT-TYPE
              SYNTAX  DisplayString
              MAX-ACCESS  read-only
              STATUS  current
              DESCRIPTION
			"For port configured with OTU4/OTUC4 traffic, when the incoming
			OTU4 frame has all 1s in the entire ODUk signal,
			excluding the frame alignment overhead (FA OH),
			OTUk overhead (OTUk OH) and ODUk FTFL, this alarm is
			generated
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 57 }

	ommp401OduTrailTraceIdentifierMismatchAlarm OBJECT-TYPE
              SYNTAX  DisplayString
              MAX-ACCESS  read-only
              STATUS  current
              DESCRIPTION
			"For port configured with OTU4/OTUC4 traffic, when there
			is a mismatch between the incoming and the expected
			Sapi(TTI) at the PM section,
			ODU-Sapi alarm is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 58 }

	ommp401OduLockedDefectAlarm OBJECT-TYPE
              SYNTAX  DisplayString
              MAX-ACCESS  read-only
              STATUS  current
              DESCRIPTION
			"For port configured with OTU4/OTUC4 traffic, 
			the locked maintenance signal is generated on operator
			request in order to lock the signal from user access. It
			consists of a repeating 0b0101 0101 pattern in the
			entire ODUk signal, which excludes the Frame Alignment
			overhead and the OTUk overhead.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 59 }

	ommp401OduOpenConnectionIndicationAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire ODUk signal,
			which excludes the Frame Alignment overhead and the
			OTUk overhead.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 60 }

	ommp401OduBackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or ODU-AIS
			or ODU-OCI or ODU-LCK condition is detected
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 61 }

	ommp401OduTcm1BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM1-AIS
			or TCM1-OCI or TCM1-LCK condition is detected
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 68 }

	ommp401OduTcm2BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM2-AIS
			or TCM2-OCI or TCM2-LCK condition is detected
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 69 }

	ommp401OduTcm3BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM3-AIS
			or TCM3-OCI or TCM3-LCK condition is detected
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 70 }

	ommp401OduTcm4BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM4-AIS
			or TCM4-OCI or TCM4-LCK condition is detected
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 71 }

	ommp401OduTcm5BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM5-AIS
			or TCM5-OCI or TCM5-LCK condition is detected
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 72 }

	ommp401OduTcm6BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM6-AIS
			or TCM6-OCI or TCM6-LCK condition is detected
			by the far-end card.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 73 }

	ommp401OduTcm1BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM1k signal,
			which excludes the Frame Alignment overhead and the
			OTUk overhead.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 74 }

	ommp401OduTcm2BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM2k signal,
			which excludes the Frame Alignment overhead and the
			OTUk overhead.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 75 }

	ommp401OduTcm3BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM3k signal,
			which excludes the Frame Alignment overhead and the
			OTUk overhead.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 76 }

	ommp401OduTcm4BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM4k signal,
			which excludes the Frame Alignment overhead and the
			OTUk overhead.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 77 }

	ommp401OduTcm5BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM5k signal,
			which excludes the Frame Alignment overhead and the
			OTUk overhead.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 78 }

	ommp401OduTcm6BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM6k signal,
			which excludes the Frame Alignment overhead and the
			OTUk overhead.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 79 }

	ommp401OduTcm1LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.  
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 80 }

	ommp401OduTcm2LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.   
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 81 }

	ommp401OduTcm3LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 82 }

	ommp401OduTcm4LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 83 }

	ommp401OduTcm5LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000. 
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 84 }

	ommp401OduTcm6LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 85 }

	ommp401OpuPayloadMismatchAlarm OBJECT-TYPE
              SYNTAX  DisplayString
              MAX-ACCESS  read-only
              STATUS  current
              DESCRIPTION
			"For port configured with OTU4/OTUC4 traffic, 
			OPU-PLM Alarm is declared if the accepted payload type
			is not equal to the expected payload type.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 104 }

	ommp401EthernetLossOfSignalAlarm OBJECT-TYPE
              SYNTAX  DisplayString
              MAX-ACCESS  read-only
              STATUS  current
              DESCRIPTION
			"For port configured with 
			GE-GFP-F/FE-GFP-F/GE-GFP-T/FE-GFP-T traffic,
			if there is no signal received then LOS Alarm is 
			generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 105 }

	ommp401EthernetIngressRemoteFaultAlarm OBJECT-TYPE
              SYNTAX  DisplayString
              MAX-ACCESS  read-only
              STATUS  current
              DESCRIPTION
			"For port configured with Ethernet traffic,
			if fault is detected on the transmit data path then 
			Remote Fault Alarm is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 106 }

	ommp401EthernetIngressPcsErrorBlocksDetectedAlarm OBJECT-TYPE
              SYNTAX  DisplayString
              MAX-ACCESS  read-only
              STATUS  current
              DESCRIPTION
			"For port configured with Ethernet traffic,
			if fault is detected when at least one errored block 
			occurred while the PCS receiver is operating in normal mode
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 107 }

	ommp401EthernetIngressPcsBipErrorsDetectedAlarm OBJECT-TYPE
              SYNTAX  DisplayString
              MAX-ACCESS  read-only
              STATUS  current
              DESCRIPTION
			"For port configured with Ethernet traffic,
			if fault is detected which at least one bit error rate (BER) 
			occurred while the PCS receiver is operating in normal mode
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 108 }

	ommp401EthernetIngressOpuClientServerFailIndicationAlarm OBJECT-TYPE
              SYNTAX  DisplayString
              MAX-ACCESS  read-only
              STATUS  current
              DESCRIPTION
			"For port configured with Ethernet traffic,
			The 64B/66B receiver gets BER greater than 
			or equal to 10^-4
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 109 }

	ommp401EthernetIngressLocalFaultAlarm OBJECT-TYPE
              SYNTAX  DisplayString
              MAX-ACCESS  read-only
              STATUS  current
              DESCRIPTION
			"For port configured with Ethernet traffic,
			if fault is detected on the receive data path then Local
			Fault Alarm is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 110 }

	ommp401EthernetIngressLossOfAlignmentAlarm OBJECT-TYPE
              SYNTAX  DisplayString
              MAX-ACCESS  read-only
              STATUS  current
              DESCRIPTION
			"For port configured with Ethernet traffic,
			If no correct signal is given or the incoming signal clock 
			rate is not matching, then this alarm will be raised.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 111 }

	ommp401EthernetIngressLossOfAlignmentMarkerLockAlarm OBJECT-TYPE
              SYNTAX  DisplayString
              MAX-ACCESS  read-only
              STATUS  current
              DESCRIPTION
			"For port configured with Ethernet traffic, In lock mode
			If no correct signal is given or the incoming signal clock 
			rate is not matching, then this alarm will be raised.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 112 }

	ommp401EthernetIngressLossOfBlockLockAlarm OBJECT-TYPE
              SYNTAX  DisplayString
              MAX-ACCESS  read-only
              STATUS  current
              DESCRIPTION
			"For port configured with Ethernet traffic,
			The total Ethernet link between the devices would fail, 
			then this alarm will be raised
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 113 }

	ommp401EthernetEgressRemoteFaultAlarm OBJECT-TYPE
              SYNTAX  DisplayString
              MAX-ACCESS  read-only
              STATUS  current
              DESCRIPTION
			"For port configured with Ethernet traffic,
			if fault is detected on the transmit data path then 
			Remote Fault Alarm is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 114 }

	ommp401EthernetEgressPcsErrorBlocksDetectedAlarm OBJECT-TYPE
              SYNTAX  DisplayString
              MAX-ACCESS  read-only
              STATUS  current
              DESCRIPTION
			"For port configured with Ethernet traffic,
			if fault is detected when at least one errored block 
			occurred while the PCS receiver is operating in normal mode
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 115 }

	ommp401EthernetEgressPcsBipErrorsDetectedAlarm OBJECT-TYPE
              SYNTAX  DisplayString
              MAX-ACCESS  read-only
              STATUS  current
              DESCRIPTION
			"For port configured with Ethernet traffic,
			if fault is detected which at least one bit error rate (BER) 
			occurred while the PCS receiver is operating in normal mode
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 116 }

	ommp401EthernetEgressHighBerAlarm OBJECT-TYPE
              SYNTAX  DisplayString
              MAX-ACCESS  read-only
              STATUS  current
              DESCRIPTION
			"For port configured with Ethernet traffic,
			this alarm is generated when signal BER is
			greater than 1e−4. 
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 117 }

	ommp401EthernetEgressLocalFaultAlarm OBJECT-TYPE
              SYNTAX  DisplayString
              MAX-ACCESS  read-only
              STATUS  current
              DESCRIPTION
			"For port configured with Ethernet traffic,
			if fault is detected on the receive data path then Local
			Fault Alarm is generated.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 118 }

	ommp401EthernetEgressLossOfAlignmentAlarm OBJECT-TYPE
              SYNTAX  DisplayString
              MAX-ACCESS  read-only
              STATUS  current
              DESCRIPTION
			"For port configured with Ethernet traffic,
			If no correct signal is given or the incoming signal clock 
			rate is not matching, then this alarm will be raised.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 119 }

	ommp401EthernetEgressLossOfAlignmentMarkerLockAlarm OBJECT-TYPE
              SYNTAX  DisplayString
              MAX-ACCESS  read-only
              STATUS  current
              DESCRIPTION
			"For port configured with Ethernet traffic, In lock mode
			If no correct signal is given or the incoming signal clock 
			rate is not matching, then this alarm will be raised.
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 120 }

	ommp401EthernetEgressLossOfBlockLockAlarm OBJECT-TYPE
              SYNTAX  DisplayString
              MAX-ACCESS  read-only
              STATUS  current
              DESCRIPTION
			"For port configured with Ethernet traffic,
			The total Ethernet link between the devices would fail, 
			then this alarm will be raised
			-----------------------------
			ommp401InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 121 }
		
		ommp401LineOtuLossOfSignalAlarm OBJECT-TYPE
              SYNTAX  DisplayString
              MAX-ACCESS  read-only
              STATUS  current
              DESCRIPTION
			"For port configured with OTU4/OTUC4 traffic,
			if there is no signal received then OTU-LOS Alarm
			is generated.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 122 }

	ommp401LineOtuLossOfFrameAlarm OBJECT-TYPE
              SYNTAX  DisplayString
              MAX-ACCESS  read-only
              STATUS  current
              DESCRIPTION
			"For port configured with OTU4/OTUC4 traffic, if
			OTU4/OTUC4 frame received are in out-of-frame (OOF)
			state for 3 ms, then OTU-LOF Alarm is generated
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 123 }

	ommp401LineOtuOutOfFrameAlarm OBJECT-TYPE
              SYNTAX  DisplayString
              MAX-ACCESS  read-only
              STATUS  current
              DESCRIPTION
			"For port configured with OTU4/OTUC4 traffic, if 5
			consecutive OTU4/OTUC4 frames are received with
			invalid framing patterns then OOF Alarm is
			generated
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 124 }

	ommp401LineOtuLossOfMultiFrameAlarm OBJECT-TYPE
              SYNTAX  DisplayString
              MAX-ACCESS  read-only
              STATUS  current
              DESCRIPTION
			"For port configured with OTU4/OTUC4 traffic, if 
			OTU4/OTUC4 frame received are in Out-of-multiframe
			(OOM) state for 3 ms then LOM Alarm is generated.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 125 }

	ommp401LineOtuOutOfMultiFrameAlarm OBJECT-TYPE
              SYNTAX  DisplayString
              MAX-ACCESS  read-only
              STATUS  current
              DESCRIPTION
			"For port configured with OTU4/OTUC4 traffic, if the
			received MFAS does not match with the expected multi
			frame number for five consecutive frames then
			OOM Alarm is generated.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 126 }

	ommp401LineOtuSignalDegradeAlarm OBJECT-TYPE
              SYNTAX  DisplayString
              MAX-ACCESS  read-only
              STATUS  current
              DESCRIPTION
			"For port configured with OTU4/OTUC4 traffic, 
			OTU SD alarm is generated when BIP errors evaluated by 
			SM field of OTU4/OTUC4 frame exceeds the 
			'ommp401LineOtuSignalDegradeThreshold' threshold.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 128 }

	ommp401LineOtuAlarmIndicationSignalAlarm OBJECT-TYPE
              SYNTAX  DisplayString
              MAX-ACCESS  read-only
              STATUS  current
              DESCRIPTION
			"For port configured with OTU4/OTUC4 traffic,
			OTU-AIS is generated and transmitted in forward 
			direction, when LOS has been detected at far-end port.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 129 }

	ommp401LineOtuIncomingAlignmentErrorAlarm OBJECT-TYPE
              SYNTAX  DisplayString
              MAX-ACCESS  read-only
              STATUS  current
              DESCRIPTION
			"For port configured with OTU4/OTUC4 traffic, IAE alarms
			shall be declared if the IAE bit in the SM overhead
			field (byte 3, bit 6) is 1 for 5 consecutive frames. 
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 130 }

	ommp401LineOtuTrailTraceIdentifierMismatchAlarm OBJECT-TYPE
              SYNTAX  DisplayString
              MAX-ACCESS  read-only
              STATUS  current
              DESCRIPTION
			"For port configured with OTU4/OTUC4 traffic, when there
			is a mismatch between the incoming and the expected
			Sapi(TTI) at the SM section,
			OTU-Sapi alarm is generated.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 131 }

	ommp401LineOtuBackwardIncomingAlignmentErrorAlarm OBJECT-TYPE
              SYNTAX  DisplayString
              MAX-ACCESS  read-only
              STATUS  current
              DESCRIPTION
			"For port configured with OTU4/OTUC4 traffic, 
			the presence of this alarm conveys that an incoming
			alignment error(IAE) condition is detected
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 132 }

	ommp401LineOtuBackwardDefectIndicationAlarm OBJECT-TYPE
              SYNTAX  DisplayString
              MAX-ACCESS  read-only
              STATUS  current
              DESCRIPTION
			"For port configured with OTU4/OTUC4 traffic,
			the presence of this alarm conveys that a
			a defect like LOS, LOF, LOM has been detected in the
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 133 }

	ommp401LineOduSignalDegradeAlarm OBJECT-TYPE
              SYNTAX  DisplayString
              MAX-ACCESS  read-only
              STATUS  current
              DESCRIPTION
			"For port configured with OTU4/OTUC4 traffic,ODU-SD
			alarm is generated when BIP errors evaluated by 
			PM field of OTU4 frame exceeds the 	
			'ommp401LineOduSignalDegradeThreshold' threshold.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 135 }

	ommp401LineOduAlarmIndicationSignalAlarm OBJECT-TYPE
              SYNTAX  DisplayString
              MAX-ACCESS  read-only
              STATUS  current
              DESCRIPTION
			"For port configured with OTU4/OTUC4 traffic, when the incoming
			OTU4 frame has all 1s in the entire ODUk signal,
			excluding the frame alignment overhead (FA OH),
			OTUk overhead (OTUk OH) and ODUk FTFL, this alarm is
			generated
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 136 }

	ommp401LineOduTrailTraceIdentifierMismatchAlarm OBJECT-TYPE
              SYNTAX  DisplayString
              MAX-ACCESS  read-only
              STATUS  current
              DESCRIPTION
			"For port configured with OTU4/OTUC4 traffic, when there
			is a mismatch between the incoming and the expected
			Sapi(TTI) at the PM section,
			ODU-Sapi alarm is generated.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 137 }

	ommp401LineOduLockedDefectAlarm OBJECT-TYPE
              SYNTAX  DisplayString
              MAX-ACCESS  read-only
              STATUS  current
              DESCRIPTION
			"For port configured with OTU4/OTUC4 traffic, 
			the locked maintenance signal is generated on operator
			request in order to lock the signal from user access. It
			consists of a repeating 0b0101 0101 pattern in the
			entire ODUk signal, which excludes the Frame Alignment
			overhead and the OTUk overhead.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 138 }

	ommp401LineOduOpenConnectionIndicationAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire ODUk signal,
			which excludes the Frame Alignment overhead and the
			OTUk overhead.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 139 }

	ommp401LineOduBackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or ODU-AIS
			or ODU-OCI or ODU-LCK condition is detected
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 140 }

	ommp401LineOduTcm1BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM1-AIS
			or TCM1-OCI or TCM1-LCK condition is detected
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 141 }

	ommp401LineOduTcm2BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM2-AIS
			or TCM2-OCI or TCM2-LCK condition is detected
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 142 }

	ommp401LineOduTcm3BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM3-AIS
			or TCM3-OCI or TCM3-LCK condition is detected
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 143 }

	ommp401LineOduTcm4BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM4-AIS
			or TCM4-OCI or TCM4-LCK condition is detected
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 144 }

	ommp401LineOduTcm5BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM5-AIS
			or TCM5-OCI or TCM5-LCK condition is detected
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 145 }

	ommp401LineOduTcm6BackwardDefectIndicationAlarm OBJECT-TYPE
              SYNTAX  DisplayString
              MAX-ACCESS  read-only
              STATUS  current
              DESCRIPTION
			"For port configured with OTU4/OTUC4 traffic, 
			the presence of this alarm conveys that either of
			OTU-LOS or OTU-LOF or OTU-LOM or OTU-AIS or TCM6-AIS
			or TCM6-OCI or TCM6-LCK condition is detected
			by the far-end card.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 146 }

	ommp401LineOduTcm1BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM1k signal,
			which excludes the Frame Alignment overhead and the
			OTUk overhead.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 147 }

	ommp401LineOduTcm2BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM2k signal,
			which excludes the Frame Alignment overhead and the
			OTUk overhead.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 148 }

	ommp401LineOduTcm3BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM3k signal,
			which excludes the Frame Alignment overhead and the
			OTUk overhead.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 149 }

	ommp401LineOduTcm4BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM4k signal,
			which excludes the Frame Alignment overhead and the
			OTUk overhead.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 150 }

	ommp401LineOduTcm5BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM5k signal,
			which excludes the Frame Alignment overhead and the
			OTUk overhead.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 151 }

	ommp401LineOduTcm6BackwardIncomingAlignmentErrorAlarm OBJECT-TYPE
              SYNTAX  DisplayString
              MAX-ACCESS  read-only
              STATUS  current
              DESCRIPTION
			"For port configured with OTU4/OTUC4 traffic, 
			an open connection indication is sent downstream when
			no signal is detected from upstream. It consists of a
			repeating 0b0110 0110 pattern in the entire TCM6k signal,
			which excludes the Frame Alignment overhead and the
			OTUk overhead.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 152 }

	ommp401LineOduTcm1LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.  
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 153 }

	ommp401LineOduTcm2LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.   
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 154 }

	ommp401LineOduTcm3LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 155 }

	ommp401LineOduTcm4LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 156 }

	ommp401LineOduTcm5LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000. 
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 157 }

	ommp401LineOduTcm6LossOfTandemConnectionAlarm OBJECT-TYPE
              SYNTAX  DisplayString
              MAX-ACCESS  read-only
              STATUS  current
              DESCRIPTION
			"For port configured with OTU4/OTUC4 traffic, when there
			dLTC shall be declared if the accepted STAT information (AcSTAT) 
			is 000. dLTC shall be cleared if the accepted STAT information 
			is not equal to 000.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 158 }

	ommp401LineOpuPayloadMismatchAlarm OBJECT-TYPE
              SYNTAX  DisplayString
              MAX-ACCESS  read-only
              STATUS  current
              DESCRIPTION
			"For port configured with OTU4/OTUC4 traffic, 
			OPU-PLM Alarm is declared if the accepted payload type
			is not equal to the expected payload type.
			-----------------------------
			ommp401 InterfaceNumber:
			1 to 4 - CLIENT-1 to CLIENT-4
			-----------------------------
			Values :
			If Alarm is Present - Date and Time Stamp
				    eg:2017-5-18,9:47:20.0,+5:30
			If Alarm is Absent  - 0
			-----------------------------"
		::= { ommp401AlarmQueryEntry 159 }

	ommp401AlarmQueryTableRowStatus OBJECT-TYPE
              SYNTAX      RowStatus
              MAX-ACCESS  read-write
              STATUS      current
              DESCRIPTION
			"*****************************
			This is MIB realted property,
			NOT to be considered as a card property
			*****************************"
              ::= { ommp401AlarmQueryEntry 160 }	                                

--*****************************************************************************
--				    ALARM Notification Table
--*****************************************************************************
	ommp401Cfp2InputPowerFailureAlarmTrap NOTIFICATION-TYPE
		OBJECTS { ommp401Cfp2InputPowerFailureAlarm  }
		STATUS  current
		DESCRIPTION
                        "OMMP401 CFP2 Input Power Failure Alarm Trap"
        ::= { ommp401AlarmNotification 1 }

	ommp401Cfp2OutputPowerFailureAlarmTrap NOTIFICATION-TYPE
		OBJECTS { ommp401Cfp2OutputPowerFailureAlarm  }
		STATUS  current
		DESCRIPTION
                        "OMMP401 CFP2 Output Power Failure Alarm Trap" 
        ::= { ommp401AlarmNotification 2 }

	ommp401Cfp2HighTemperatureAlarmTrap NOTIFICATION-TYPE
		OBJECTS { ommp401Cfp2HighTemperatureAlarm  }
		STATUS  current
		DESCRIPTION
                        "OMMP401 CFP2 High Temperature Alarm Trap" 
        ::= { ommp401AlarmNotification 3 }

	ommp401Cfp2LowTemperatureAlarmTrap NOTIFICATION-TYPE
		OBJECTS { ommp401Cfp2LowTemperatureAlarm  }
		STATUS  current
		DESCRIPTION
                        "OMMP401 CFP2 Low Temperature Alarm Trap" 
        ::= { ommp401AlarmNotification 4 }

	ommp401Cfp2HighTemperatureWarningTrap NOTIFICATION-TYPE
		OBJECTS { ommp401Cfp2HighTemperatureWarning  }
		STATUS  current
		DESCRIPTION
                        "OMMP401 CFP2 High Temperature Warning Trap" 
        ::= { ommp401AlarmNotification 5 }

	ommp401Cfp2LowTemperatureWarningTrap NOTIFICATION-TYPE
		OBJECTS { ommp401Cfp2LowTemperatureWarning  }
		STATUS  current
		DESCRIPTION
                        "OMMP401 CFP2 Low Temperature Warning Trap" 
        ::= { ommp401AlarmNotification 6 }

	ommp401Cfp2InputHighPowerAlarmTrap NOTIFICATION-TYPE
		OBJECTS { ommp401Cfp2InputHighPowerAlarm  }
		STATUS  current
		DESCRIPTION
                        "OMMP401 CFP2 Input High Power Alarm Trap" 
        ::= { ommp401AlarmNotification 7 }

	ommp401Cfp2InputLowPowerAlarmTrap NOTIFICATION-TYPE
		OBJECTS { ommp401Cfp2InputLowPowerAlarm  }
		STATUS  current
		DESCRIPTION
                        "OMMP401 CFP2 Input Low Power Alarm Trap" 
        ::= { ommp401AlarmNotification 8 }

	ommp401Cfp2InputHighPowerWarningTrap NOTIFICATION-TYPE
		OBJECTS { ommp401Cfp2InputHighPowerWarning  }
		STATUS  current
		DESCRIPTION
                        "OMMP401 CFP2 Input High Power Warning Trap" 
        ::= { ommp401AlarmNotification 9 }

	ommp401Cfp2InputLowPowerWarningTrap NOTIFICATION-TYPE
		OBJECTS { ommp401Cfp2InputLowPowerWarning  }
		STATUS  current
		DESCRIPTION
                        "OMMP401 CFP2 Input Low Power Warning Trap" 
        ::= { ommp401AlarmNotification 10 }

	ommp401Cfp2OutputHighPowerAlarmTrap NOTIFICATION-TYPE
		OBJECTS { ommp401Cfp2OutputHighPowerAlarm  }
		STATUS  current
		DESCRIPTION
                        "OMMP401 CFP2 Output High Power Alarm Trap" 
        ::= { ommp401AlarmNotification 11 }

	ommp401Cfp2OutputLowPowerAlarmTrap NOTIFICATION-TYPE
		OBJECTS { ommp401Cfp2OutputLowPowerAlarm  }
		STATUS  current
		DESCRIPTION
                        "OMMP401 CFP2 Output Low Power Alarm Trap" 
        ::= { ommp401AlarmNotification 12 }

	ommp401Cfp2OutputHighPowerWarningTrap NOTIFICATION-TYPE
		OBJECTS { ommp401Cfp2OutputHighPowerWarning  }
		STATUS  current
		DESCRIPTION
                        "OMMP401 CFP2 Output High Power Warning Trap" 
        ::= { ommp401AlarmNotification 13 }

	ommp401Cfp2OutputLowPowerWarningTrap NOTIFICATION-TYPE
		OBJECTS { ommp401Cfp2OutputLowPowerWarning  }
		STATUS  current
		DESCRIPTION
                        "OMMP401 CFP2 Output Low Power Warning Trap" 
        ::= { ommp401AlarmNotification 14 }

	ommp401Cfp2HighSupplyVoltageAlarmTrap NOTIFICATION-TYPE
		OBJECTS { ommp401Cfp2HighSupplyVoltageAlarm  }
		STATUS  current
		DESCRIPTION
                        "OMMP401 CFP2 High Supply Voltage Alarm Trap" 
        ::= { ommp401AlarmNotification 15 }

	ommp401Cfp2LowSupplyVoltageAlarmTrap NOTIFICATION-TYPE
		OBJECTS { ommp401Cfp2LowSupplyVoltageAlarm  }
		STATUS  current
		DESCRIPTION
                        "OMMP401 CFP2 Low Supply Voltage Alarm Trap" 
        ::= { ommp401AlarmNotification 16 }

	ommp401Cfp2HighSupplyVoltageWarningTrap NOTIFICATION-TYPE
		OBJECTS { ommp401Cfp2HighSupplyVoltageWarning  }
		STATUS  current
		DESCRIPTION
                        "OMMP401 CFP2 High Supply Voltage Warning Trap" 
        ::= { ommp401AlarmNotification 17 }

	ommp401Cfp2LowSupplyVoltageWarningTrap NOTIFICATION-TYPE
		OBJECTS { ommp401Cfp2LowSupplyVoltageWarning  }
		STATUS  current
		DESCRIPTION
                        "OMMP401 CFP2 Low Supply Voltage Warning Trap" 
        ::= { ommp401AlarmNotification 18 }

	ommp401Cfp2PresenceAbsenceNotificationTrap NOTIFICATION-TYPE
		OBJECTS { ommp401Cfp2PresenceAbsenceNotification  }
		STATUS  current
		DESCRIPTION
                        "OMMP401 CFP2 Presence Absence Notification Trap" 
        ::= { ommp401AlarmNotification 19 }

	ommp401Qsfp28InputPowerFailureAlarmTrap NOTIFICATION-TYPE
		OBJECTS { ommp401Qsfp28InputPowerFailureAlarm  }
		STATUS  current
		DESCRIPTION
                        "OMMP401 QSFP28 Input Power Failure Alarm Trap" 
        ::= { ommp401AlarmNotification 20 }

	ommp401Qsfp28OutputPowerFailureAlarmTrap NOTIFICATION-TYPE
		OBJECTS { ommp401Qsfp28OutputPowerFailureAlarm  }
		STATUS  current
		DESCRIPTION
                        "OMMP401 QSFP28 Output Power Failure Alarm Trap" 
        ::= { ommp401AlarmNotification 21 }

	ommp401Qsfp28HighTemperatureAlarmTrap NOTIFICATION-TYPE
		OBJECTS { ommp401Qsfp28HighTemperatureAlarm  }
		STATUS  current
		DESCRIPTION
                        "OMMP401 QSFP28 High Temperature Alarm Trap" 
        ::= { ommp401AlarmNotification 22 }

	ommp401Qsfp28LowTemperatureAlarmTrap NOTIFICATION-TYPE
		OBJECTS { ommp401Qsfp28LowTemperatureAlarm  }
		STATUS  current
		DESCRIPTION
                        "OMMP401 QSFP28 Low Temperature Alarm Trap" 
        ::= { ommp401AlarmNotification 23 }

	ommp401Qsfp28HighTemperatureWarningTrap NOTIFICATION-TYPE
		OBJECTS { ommp401Qsfp28HighTemperatureWarning  }
		STATUS  current
		DESCRIPTION
                        "OMMP401 QSFP28 High Temperature Warning Trap" 
        ::= { ommp401AlarmNotification 24 }

	ommp401Qsfp28LowTemperatureWarningTrap NOTIFICATION-TYPE
		OBJECTS { ommp401Qsfp28LowTemperatureWarning  }
		STATUS  current
		DESCRIPTION
                        "OMMP401 QSFP28 Low Temperature Warning Trap" 
        ::= { ommp401AlarmNotification 25 }

	ommp401Qsfp28HighBiasCurrentAlarmTrap NOTIFICATION-TYPE
		OBJECTS { ommp401Qsfp28HighBiasCurrentAlarm  }
		STATUS  current
		DESCRIPTION
                        "OMMP401 QSFP28 High Bias Current Alarm Trap" 
        ::= { ommp401AlarmNotification 26 }

	ommp401Qsfp28LowBiasCurrentAlarmTrap NOTIFICATION-TYPE
		OBJECTS { ommp401Qsfp28LowBiasCurrentAlarm  }
		STATUS  current
		DESCRIPTION
                        "OMMP401 QSFP28 Low Bias Current Alarm Trap" 
        ::= { ommp401AlarmNotification 27 }

	ommp401Qsfp28HighBiasCurrentWarningTrap NOTIFICATION-TYPE
		OBJECTS { ommp401Qsfp28HighBiasCurrentWarning  }
		STATUS  current
		DESCRIPTION
                        "OMMP401 QSFP28 High Bias Current Warning Trap" 
        ::= { ommp401AlarmNotification 28 }

	ommp401Qsfp28LowBiasCurrentWarningTrap NOTIFICATION-TYPE
		OBJECTS { ommp401Qsfp28LowBiasCurrentWarning  }
		STATUS  current
		DESCRIPTION
                        "OMMP401 QSFP28 Low Bias Current Warning Trap" 
        ::= { ommp401AlarmNotification 29 }

	ommp401Qsfp28InputHighPowerAlarmTrap NOTIFICATION-TYPE
		OBJECTS { ommp401Qsfp28InputHighPowerAlarm  }
		STATUS  current
		DESCRIPTION
                        "OMMP401 QSFP28 Input High Power Alarm Trap" 
        ::= { ommp401AlarmNotification 30 }

	ommp401Qsfp28InputLowPowerAlarmTrap NOTIFICATION-TYPE
		OBJECTS { ommp401Qsfp28InputLowPowerAlarm  }
		STATUS  current
		DESCRIPTION
                        "OMMP401 QSFP28 Input Low Power Alarm Trap" 
        ::= { ommp401AlarmNotification 31 }

	ommp401Qsfp28InputHighPowerWarningTrap NOTIFICATION-TYPE
		OBJECTS { ommp401Qsfp28InputHighPowerWarning  }
		STATUS  current
		DESCRIPTION
                        "OMMP401 QSFP28 Input High Power Warning Trap" 
        ::= { ommp401AlarmNotification 32 }

	ommp401Qsfp28InputLowPowerWarningTrap NOTIFICATION-TYPE
		OBJECTS { ommp401Qsfp28InputLowPowerWarning  }
		STATUS  current
		DESCRIPTION
                        "OMMP401 QSFP28 Input Low Power Warning Trap" 
        ::= { ommp401AlarmNotification 33 }

	ommp401Qsfp28OutputHighPowerAlarmTrap NOTIFICATION-TYPE
		OBJECTS { ommp401Qsfp28OutputHighPowerAlarm  }
		STATUS  current
		DESCRIPTION
                        "OMMP401 QSFP28 Output High Power Alarm Trap" 
        ::= { ommp401AlarmNotification 34 }

	ommp401Qsfp28OutputLowPowerAlarmTrap NOTIFICATION-TYPE
		OBJECTS { ommp401Qsfp28OutputLowPowerAlarm  }
		STATUS  current
		DESCRIPTION
                        "OMMP401 QSFP28 Output Low Power Alarm Trap" 
        ::= { ommp401AlarmNotification 35 }

	ommp401Qsfp28OutputHighPowerWarningTrap NOTIFICATION-TYPE
		OBJECTS { ommp401Qsfp28OutputHighPowerWarning  }
		STATUS  current
		DESCRIPTION
                        "OMMP401 QSFP28 Output High Power Warning Trap" 
        ::= { ommp401AlarmNotification 36 }

	ommp401Qsfp28OutputLowPowerWarningTrap NOTIFICATION-TYPE
		OBJECTS { ommp401Qsfp28OutputLowPowerWarning  }
		STATUS  current
		DESCRIPTION
                        "OMMP401 QSFP28 Output Low Power Warning Trap" 
        ::= { ommp401AlarmNotification 37 }

	ommp401Qsfp28HighSupplyVoltageAlarmTrap NOTIFICATION-TYPE
		OBJECTS { ommp401Qsfp28HighSupplyVoltageAlarm  }
		STATUS  current
		DESCRIPTION
                        "OMMP401 QSFP28 High Supply Voltage Alarm Trap" 
        ::= { ommp401AlarmNotification 38 }

	ommp401Qsfp28LowSupplyVoltageAlarmTrap NOTIFICATION-TYPE
		OBJECTS { ommp401Qsfp28LowSupplyVoltageAlarm  }
		STATUS  current
		DESCRIPTION
                        "OMMP401 QSFP28 Low Supply Voltage Alarm Trap" 
        ::= { ommp401AlarmNotification 39 }

	ommp401Qsfp28HighSupplyVoltageWarningTrap NOTIFICATION-TYPE
		OBJECTS { ommp401Qsfp28HighSupplyVoltageWarning  }
		STATUS  current
		DESCRIPTION
                        "OMMP401 QSFP28 High Supply Voltage Warning Trap" 
        ::= { ommp401AlarmNotification 40 }

	ommp401Qsfp28LowSupplyVoltageWarningTrap NOTIFICATION-TYPE
		OBJECTS { ommp401Qsfp28LowSupplyVoltageWarning  }
		STATUS  current
		DESCRIPTION
                        "OMMP401 QSFP28 Low Supply Voltage Warning Trap" 
        ::= { ommp401AlarmNotification 41 }

	ommp401Qsfp28PresenceAbsenceNotificationTrap NOTIFICATION-TYPE
		OBJECTS { ommp401Qsfp28PresenceAbsenceNotification  }
		STATUS  current
		DESCRIPTION
                        "OMMP401 QSFP28 Presence Absence Notification Trap" 
        ::= { ommp401AlarmNotification 42 }

	ommp401OtuLossOfSignalAlarmTrap NOTIFICATION-TYPE
		OBJECTS { ommp401OtuLossOfSignalAlarm  }
		STATUS  current
		DESCRIPTION
                        "OMMP401 OTU Loss Of Signal Alarm Trap" 
        ::= { ommp401AlarmNotification 43 }

	ommp401OtuLossOfFrameAlarmTrap NOTIFICATION-TYPE
		OBJECTS { ommp401OtuLossOfFrameAlarm  }
		STATUS  current
		DESCRIPTION
                        "OMMP401 OTU Loss Of Frame Alarm Trap" 
        ::= { ommp401AlarmNotification 44 }

	ommp401OtuOutOfFrameAlarmTrap NOTIFICATION-TYPE
		OBJECTS { ommp401OtuOutOfFrameAlarm  }
		STATUS  current
		DESCRIPTION
                        "OMMP401 OTU Out Of Frame Alarm Trap" 
        ::= { ommp401AlarmNotification 45 }

	ommp401OtuLossOfMultiFrameAlarmTrap NOTIFICATION-TYPE
		OBJECTS { ommp401OtuLossOfMultiFrameAlarm  }
		STATUS  current
		DESCRIPTION
                        "OMMP401 OTU Loss Of Multi Frame Alarm Trap" 
        ::= { ommp401AlarmNotification 46 }

	ommp401OtuOutOfMultiFrameAlarmTrap NOTIFICATION-TYPE
		OBJECTS { ommp401OtuOutOfMultiFrameAlarm  }
		STATUS  current
		DESCRIPTION
                        "OMMP401 OTU Out Of Multi Frame Alarm Trap" 
        ::= { ommp401AlarmNotification 47 }

	ommp401OtuSignalFailAlarmTrap NOTIFICATION-TYPE
		OBJECTS { ommp401OtuSignalFailAlarm  }
		STATUS  current
		DESCRIPTION
                        "OMMP401 OTU Signal Fail Alarm Trap" 
        ::= { ommp401AlarmNotification 48 }

	ommp401OtuSignalDegradeAlarmTrap NOTIFICATION-TYPE
		OBJECTS { ommp401OtuSignalDegradeAlarm  }
		STATUS  current
		DESCRIPTION
                        "OMMP401 OTU Signal Degrade Alarm Trap" 
        ::= { ommp401AlarmNotification 49 }

	ommp401OtuAlarmIndicationSignalAlarmTrap NOTIFICATION-TYPE
		OBJECTS { ommp401OtuAlarmIndicationSignalAlarm  }
		STATUS  current
		DESCRIPTION
                        "OMMP401 OTU Alarm Indication Signal Alarm Trap" 
        ::= { ommp401AlarmNotification 50 }

	ommp401OtuIncomingAlignmentErrorAlarmTrap NOTIFICATION-TYPE
		OBJECTS { ommp401OtuIncomingAlignmentErrorAlarm  }
		STATUS  current
		DESCRIPTION
                        "OMMP401 OTU Incoming Alignment Error Alarm Trap" 
        ::= { ommp401AlarmNotification 51 }

	ommp401OtuTrailTraceIdentifierMismatchAlarmTrap NOTIFICATION-TYPE
		OBJECTS { ommp401OtuTrailTraceIdentifierMismatchAlarm  }
		STATUS  current
		DESCRIPTION
                        "OMMP401 OTU Sapi Alarm Trap" 
        ::= { ommp401AlarmNotification 52 }

	ommp401OtuBackwardIncomingAlignmentErrorAlarmTrap NOTIFICATION-TYPE
		OBJECTS { ommp401OtuBackwardIncomingAlignmentErrorAlarm  }
		STATUS  current
		DESCRIPTION
                        "OMMP401 OTU Backward Incoming Alignment Error Alarm Trap" 
        ::= { ommp401AlarmNotification 53 }

	ommp401OtuBackwardDefectIndicationAlarmTrap NOTIFICATION-TYPE
		OBJECTS { ommp401OtuBackwardDefectIndicationAlarm  }
		STATUS  current
		DESCRIPTION
                        "OMMP401 OTU Backward Defect Indication Alarm Trap" 
        ::= { ommp401AlarmNotification 54 }

	ommp401OduSignalFailAlarmTrap NOTIFICATION-TYPE
		OBJECTS { ommp401OduSignalFailAlarm  }
		STATUS  current
		DESCRIPTION
                        "OMMP401 ODU Signal Fail Alarm Trap" 
        ::= { ommp401AlarmNotification 55 }

	ommp401OduSignalDegradeAlarmTrap NOTIFICATION-TYPE
		OBJECTS { ommp401OduSignalDegradeAlarm  }
		STATUS  current
		DESCRIPTION
                        "OMMP401 ODU Signal Degrade Alarm Trap" 
        ::= { ommp401AlarmNotification 56 }

	ommp401OduAlarmIndicationSignalAlarmTrap NOTIFICATION-TYPE
		OBJECTS { ommp401OduAlarmIndicationSignalAlarm  }
		STATUS  current
		DESCRIPTION
                        "OMMP401 ODU Alarm Indication Signal Alarm Trap" 
        ::= { ommp401AlarmNotification 57 }

	ommp401OduTrailTraceIdentifierMismatchAlarmTrap NOTIFICATION-TYPE
		OBJECTS { ommp401OtuTrailTraceIdentifierMismatchAlarm  }
		STATUS  current
		DESCRIPTION
                        "OMMP401 ODU Sapi Alarm Trap" 
        ::= { ommp401AlarmNotification 58 }

	ommp401OduLockedDefectAlarmTrap NOTIFICATION-TYPE
		OBJECTS { ommp401OduLockedDefectAlarm  }
		STATUS  current
		DESCRIPTION
                        "OMMP401 ODU Locked Defect Alarm Trap" 
        ::= { ommp401AlarmNotification 59 }

	ommp401OduOpenConnectionIndicationAlarmTrap NOTIFICATION-TYPE
		OBJECTS { ommp401OduOpenConnectionIndicationAlarm  }
		STATUS  current
		DESCRIPTION
                        "OMMP401 ODU Open Connection Indication Alarm Trap" 
        ::= { ommp401AlarmNotification 60 }

	ommp401OduBackwardDefectIndicationAlarmTrap NOTIFICATION-TYPE
		OBJECTS { ommp401OduBackwardDefectIndicationAlarm  }
		STATUS  current
		DESCRIPTION
                        "OMMP401 ODU Backward Defect Indication Alarm Trap" 
        ::= { ommp401AlarmNotification 61 }

	ommp401OduTcm1BackwardDefectIndicationAlarmTrap NOTIFICATION-TYPE
		OBJECTS { ommp401OduTcm1BackwardDefectIndicationAlarm  }
		STATUS  current
		DESCRIPTION
                        "OMMP401 ODU-TCM1 Backward Defect Indication Alarm Trap" 
        ::= { ommp401AlarmNotification 68 }

	ommp401OduTcm2BackwardDefectIndicationAlarmTrap NOTIFICATION-TYPE
		OBJECTS { ommp401OduTcm2BackwardDefectIndicationAlarm  }
		STATUS  current
		DESCRIPTION
                        "OMMP401 ODU-TCM2 Backward Defect Indication Alarm Trap" 
        ::= { ommp401AlarmNotification 69 }

	ommp401OduTcm3BackwardDefectIndicationAlarmTrap NOTIFICATION-TYPE
		OBJECTS { ommp401OduTcm3BackwardDefectIndicationAlarm  }
		STATUS  current
		DESCRIPTION
                        "OMMP401 ODU-TCM3 Backward Defect Indication Alarm Trap" 
        ::= { ommp401AlarmNotification 70 }

	ommp401OduTcm4BackwardDefectIndicationAlarmTrap NOTIFICATION-TYPE
		OBJECTS { ommp401OduTcm4BackwardDefectIndicationAlarm  }
		STATUS  current
		DESCRIPTION
                        "OMMP401 ODU-TCM4 Backward Defect Indication Alarm Trap" 
        ::= { ommp401AlarmNotification 71 }

	ommp401OduTcm5BackwardDefectIndicationAlarmTrap NOTIFICATION-TYPE
		OBJECTS { ommp401OduTcm5BackwardDefectIndicationAlarm  }
		STATUS  current
		DESCRIPTION
                        "OMMP401 ODU-TCM5 Backward Defect Indication Alarm Trap" 
        ::= { ommp401AlarmNotification 72 }

	ommp401OduTcm6BackwardDefectIndicationAlarmTrap NOTIFICATION-TYPE
		OBJECTS { ommp401OduTcm6BackwardDefectIndicationAlarm  }
		STATUS  current
		DESCRIPTION
                        "OMMP401 ODU-TCM6 Backward Defect Indication Alarm Trap" 
        ::= { ommp401AlarmNotification 73 }

	ommp401OduTcm1BackwardIncomingAlignmentErrorAlarmTrap NOTIFICATION-TYPE
		OBJECTS { ommp401OduTcm1BackwardIncomingAlignmentErrorAlarm  }
		STATUS  current
		DESCRIPTION
                        "OMMP401 ODU-TCM1 Open Connection Indication Alarm Trap" 
        ::= { ommp401AlarmNotification 74 }

	ommp401OduTcm2BackwardIncomingAlignmentErrorAlarmTrap NOTIFICATION-TYPE
		OBJECTS { ommp401OduTcm2BackwardIncomingAlignmentErrorAlarm  }
		STATUS  current
		DESCRIPTION
                        "OMMP401 ODU-TCM2 Open Connection Indication Alarm Trap" 
        ::= { ommp401AlarmNotification 75 }

	ommp401OduTcm3BackwardIncomingAlignmentErrorAlarmTrap NOTIFICATION-TYPE
		OBJECTS { ommp401OduTcm3BackwardIncomingAlignmentErrorAlarm  }
		STATUS  current
		DESCRIPTION
                        "OMMP401 ODU-TCM3 Open Connection Indication Alarm Trap" 
        ::= { ommp401AlarmNotification 76 }

	ommp401OduTcm4BackwardIncomingAlignmentErrorAlarmTrap NOTIFICATION-TYPE
		OBJECTS { ommp401OduTcm4BackwardIncomingAlignmentErrorAlarm  }
		STATUS  current
		DESCRIPTION
                        "OMMP401 ODU-TCM4 Open Connection Indication Alarm Trap" 
        ::= { ommp401AlarmNotification 77 }

	ommp401OduTcm5BackwardIncomingAlignmentErrorAlarmTrap NOTIFICATION-TYPE
		OBJECTS { ommp401OduTcm5BackwardIncomingAlignmentErrorAlarm  }
		STATUS  current
		DESCRIPTION
                        "OMMP401 ODU-TCM5 Open Connection Indication Alarm Trap" 
        ::= { ommp401AlarmNotification 78 }

	ommp401OduTcm6BackwardIncomingAlignmentErrorAlarmTrap NOTIFICATION-TYPE
		OBJECTS { ommp401OduTcm6BackwardIncomingAlignmentErrorAlarm  }
		STATUS  current
		DESCRIPTION
                        "OMMP401 ODU-TCM6 Open Connection Indication Alarm Trap" 
        ::= { ommp401AlarmNotification 79}

	ommp401OduTcm1LossOfTandemConnectionAlarmTrap NOTIFICATION-TYPE
		OBJECTS { ommp401OduTcm1LossOfTandemConnectionAlarm  }
		STATUS  current
		DESCRIPTION
                        "OMMP401 ODU-TCM1 Loss Of Tandem Connection Alarm Trap" 
        ::= { ommp401AlarmNotification 80 }

	ommp401OduTcm2LossOfTandemConnectionAlarmTrap NOTIFICATION-TYPE
		OBJECTS { ommp401OduTcm2LossOfTandemConnectionAlarm  }
		STATUS  current
		DESCRIPTION
                        "OMMP401 ODU-TCM2 Loss Of Tandem Connection Alarm Trap" 
        ::= { ommp401AlarmNotification 81 }

	ommp401OduTcm3LossOfTandemConnectionAlarmTrap NOTIFICATION-TYPE
		OBJECTS { ommp401OduTcm3LossOfTandemConnectionAlarm  }
		STATUS  current
		DESCRIPTION
                        "OMMP401 ODU-TCM3 Loss Of Tandem Connection Alarm Trap" 
        ::= { ommp401AlarmNotification 82 }

	ommp401OduTcm4LossOfTandemConnectionAlarmTrap NOTIFICATION-TYPE
		OBJECTS { ommp401OduTcm4LossOfTandemConnectionAlarm  }
		STATUS  current
		DESCRIPTION
                        "OMMP401 ODU-TCM4 Loss Of Tandem Connection Alarm Trap" 
        ::= { ommp401AlarmNotification 83 }

	ommp401OduTcm5LossOfTandemConnectionAlarmTrap NOTIFICATION-TYPE
		OBJECTS { ommp401OduTcm5LossOfTandemConnectionAlarm  }
		STATUS  current
		DESCRIPTION
                        "OMMP401 ODU-TCM5 Loss Of Tandem Connection Alarm Trap" 
        ::= { ommp401AlarmNotification 84 }

	ommp401OduTcm6LossOfTandemConnectionAlarmTrap NOTIFICATION-TYPE
		OBJECTS { ommp401OduTcm6LossOfTandemConnectionAlarm  }
		STATUS  current
		DESCRIPTION
                        "OMMP401 ODU-TCM6 Loss Of Tandem Connection Alarm Trap" 
        ::= { ommp401AlarmNotification 85 }

	ommp401OpuPayloadMismatchAlarmTrap NOTIFICATION-TYPE
		OBJECTS { ommp401OpuPayloadMismatchAlarm  }
		STATUS  current
		DESCRIPTION
                        "OMMP401 OPU Payload Mismatch Alarm Trap" 
        ::= { ommp401AlarmNotification 104 }

	ommp401EthernetLossOfSignalAlarmTrap NOTIFICATION-TYPE
		OBJECTS { ommp401EthernetLossOfSignalAlarm  }
		STATUS  current
		DESCRIPTION
                        "OMMP401 Ethernet Loss Of Signal Alarm Trap" 
        ::= { ommp401AlarmNotification 105 }

	ommp401EthernetIngressRemoteFaultAlarmTrap NOTIFICATION-TYPE
		OBJECTS { ommp401EthernetIngressRemoteFaultAlarm  }
		STATUS  current
		DESCRIPTION
                        "OMMP401 Ethernet Ingress Remote Fault Alarm Trap" 
        ::= { ommp401AlarmNotification 106 }

	ommp401EthernetIngressPcsErrorBlocksDetectedAlarmTrap NOTIFICATION-TYPE
		OBJECTS { ommp401EthernetIngressPcsErrorBlocksDetectedAlarm  }
		STATUS  current
		DESCRIPTION
                        "OMMP401 Ethernet Ingress Pcs Error Blocks Detected Alarm Trap" 
        ::= { ommp401AlarmNotification 107 }

	ommp401EthernetIngressPcsBipErrorsDetectedAlarmTrap NOTIFICATION-TYPE
		OBJECTS { ommp401EthernetIngressPcsBipErrorsDetectedAlarm  }
		STATUS  current
		DESCRIPTION
                        "OMMP401 Ethernet Ingress Pcs Bip Errors Detected Alarm Trap" 
        ::= { ommp401AlarmNotification 108 }

	ommp401EthernetIngressOpuClientServerFailIndicationAlarmTrap NOTIFICATION-TYPE
		OBJECTS { ommp401EthernetIngressOpuClientServerFailIndicationAlarm  }
		STATUS  current
		DESCRIPTION
                        "OMMP401 Ethernet Ingress Opu Client Server Fail Indication Alarm Trap" 
        ::= { ommp401AlarmNotification 109 }

	ommp401EthernetIngressLocalFaultAlarmTrap NOTIFICATION-TYPE
		OBJECTS { ommp401EthernetIngressLocalFaultAlarm  }
		STATUS  current
		DESCRIPTION
                        "OMMP401 Ethernet Ingress Local Fault Alarm Trap" 
        ::= { ommp401AlarmNotification 110 }

	ommp401EthernetIngressLossOfAlignmentAlarmTrap NOTIFICATION-TYPE
		OBJECTS { ommp401EthernetIngressLossOfAlignmentAlarm  }
		STATUS  current
		DESCRIPTION
                        "OMMP401 Ethernet Ingress Loss Of Alignment Alarm Trap" 
        ::= { ommp401AlarmNotification 111 }

	ommp401EthernetIngressLossOfAlignmentMarkerLockAlarmTrap NOTIFICATION-TYPE
		OBJECTS { ommp401EthernetIngressLossOfAlignmentMarkerLockAlarm  }
		STATUS  current
		DESCRIPTION
                        "OMMP401 Ethernet Ingress Loss Of Alignment Marker lock Alarm Trap" 
        ::= { ommp401AlarmNotification 112 }

	ommp401EthernetIngressLossOfBlockLockAlarmTrap NOTIFICATION-TYPE
		OBJECTS { ommp401EthernetIngressLossOfBlockLockAlarm  }
		STATUS  current
		DESCRIPTION
                        "OMMP401 Ethernet Ingress Loss Of Block Lock Alarm Trap" 
        ::= { ommp401AlarmNotification 113 }

	ommp401EthernetEgressRemoteFaultAlarmTrap NOTIFICATION-TYPE
		OBJECTS { ommp401EthernetEgressRemoteFaultAlarm  }
		STATUS  current
		DESCRIPTION
                        "OMMP401 Ethernet Egress Remote Fault Alarm Trap" 
        ::= { ommp401AlarmNotification 114 }

	ommp401EthernetEgressPcsErrorBlocksDetectedAlarmTrap NOTIFICATION-TYPE
		OBJECTS { ommp401EthernetEgressPcsErrorBlocksDetectedAlarm  }
		STATUS  current
		DESCRIPTION
                        "OMMP401 Ethernet Egress Pcs Error Blocks Detected Alarm Trap" 
        ::= { ommp401AlarmNotification 115 }

	ommp401EthernetEgressPcsBipErrorsDetectedAlarmTrap NOTIFICATION-TYPE
		OBJECTS { ommp401EthernetEgressPcsBipErrorsDetectedAlarm  }
		STATUS  current
		DESCRIPTION
                        "OMMP401 Ethernet Egress Pcs Bip Errors Detected Alarm Trap" 
        ::= { ommp401AlarmNotification 116 }

	ommp401EthernetEgressHighBerAlarmTrap NOTIFICATION-TYPE
		OBJECTS { ommp401EthernetEgressHighBerAlarm  }
		STATUS  current
		DESCRIPTION
                        "OMMP401 Ethernet Egress High BER Alarm Trap" 
        ::= { ommp401AlarmNotification 117 }

	ommp401EthernetEgressLocalFaultAlarmTrap NOTIFICATION-TYPE
		OBJECTS { ommp401EthernetEgressLocalFaultAlarm  }
		STATUS  current
		DESCRIPTION
                        "OMMP401 Ethernet Egress Local Fault Alarm Trap" 
        ::= { ommp401AlarmNotification 118 }

	ommp401EthernetEgressLossOfAlignmentAlarmTrap NOTIFICATION-TYPE
		OBJECTS { ommp401EthernetEgressLossOfAlignmentAlarm  }
		STATUS  current
		DESCRIPTION
                        "OMMP401 Ethernet Egress Loss Of Alignment Alarm Trap" 
        ::= { ommp401AlarmNotification 119 }

	ommp401EthernetEgressLossOfAlignmentMarkerLockAlarmTrap NOTIFICATION-TYPE
		OBJECTS { ommp401EthernetEgressLossOfAlignmentMarkerLockAlarm  }
		STATUS  current
		DESCRIPTION
                        "OMMP401 Ethernet Egress Loss Of Alignment Marker lock Alarm Trap" 
        ::= { ommp401AlarmNotification 120 }

	ommp401EthernetEgressLossOfBlockLockAlarmTrap NOTIFICATION-TYPE
		OBJECTS { ommp401EthernetEgressLossOfBlockLockAlarm  }
		STATUS  current
		DESCRIPTION
                        "OMMP401 Ethernet Egress Loss Of Block Lock Alarm Trap" 
        ::= { ommp401AlarmNotification 121 }
        
        	ommp401LineOtuLossOfSignalAlarmTrap NOTIFICATION-TYPE
		OBJECTS { ommp401LineOtuLossOfSignalAlarm  }
		STATUS  current
		DESCRIPTION
                        "OMMP401 OTU Loss Of Signal Alarm Trap" 
        ::= { ommp401AlarmNotification 122 }

	ommp401LineOtuLossOfFrameAlarmTrap NOTIFICATION-TYPE
		OBJECTS { ommp401LineOtuLossOfFrameAlarm  }
		STATUS  current
		DESCRIPTION
                        "OMMP401 OTU Loss Of Frame Alarm Trap" 
        ::= { ommp401AlarmNotification 123 }

	ommp401LineOtuOutOfFrameAlarmTrap NOTIFICATION-TYPE
		OBJECTS { ommp401LineOtuOutOfFrameAlarm  }
		STATUS  current
		DESCRIPTION
                        "OMMP401 OTU Out Of Frame Alarm Trap" 
        ::= { ommp401AlarmNotification 124 }

	ommp401LineOtuLossOfMultiFrameAlarmTrap NOTIFICATION-TYPE
		OBJECTS { ommp401LineOtuLossOfMultiFrameAlarm  }
		STATUS  current
		DESCRIPTION
                        "OMMP401 OTU Loss Of Multi Frame Alarm Trap" 
        ::= { ommp401AlarmNotification 125 }

	ommp401LineOtuOutOfMultiFrameAlarmTrap NOTIFICATION-TYPE
		OBJECTS { ommp401LineOtuOutOfMultiFrameAlarm  }
		STATUS  current
		DESCRIPTION
                        "OMMP401 OTU Out Of Multi Frame Alarm Trap" 
        ::= { ommp401AlarmNotification 126 }

	ommp401LineOtuSignalDegradeAlarmTrap NOTIFICATION-TYPE
		OBJECTS { ommp401LineOtuSignalDegradeAlarm  }
		STATUS  current
		DESCRIPTION
                        "OMMP401 OTU Signal Degrade Alarm Trap" 
        ::= { ommp401AlarmNotification 128 }

	ommp401LineOtuAlarmIndicationSignalAlarmTrap NOTIFICATION-TYPE
		OBJECTS { ommp401LineOtuAlarmIndicationSignalAlarm  }
		STATUS  current
		DESCRIPTION
                        "OMMP401 OTU Alarm Indication Signal Alarm Trap" 
        ::= { ommp401AlarmNotification 130 }

	ommp401LineOtuIncomingAlignmentErrorAlarmTrap NOTIFICATION-TYPE
		OBJECTS { ommp401LineOtuIncomingAlignmentErrorAlarm  }
		STATUS  current
		DESCRIPTION
                        "OMMP401 OTU Incoming Alignment Error Alarm Trap" 
        ::= { ommp401AlarmNotification 131 }

	ommp401LineOtuTrailTraceIdentifierMismatchAlarmTrap NOTIFICATION-TYPE
		OBJECTS { ommp401LineOtuTrailTraceIdentifierMismatchAlarm  }
		STATUS  current
		DESCRIPTION
                        "OMMP401 OTU Sapi Alarm Trap" 
        ::= { ommp401AlarmNotification 132 }

	ommp401LineOtuBackwardIncomingAlignmentErrorAlarmTrap NOTIFICATION-TYPE
		OBJECTS { ommp401LineOtuBackwardIncomingAlignmentErrorAlarm  }
		STATUS  current
		DESCRIPTION
                        "OMMP401 OTU Backward Incoming Alignment Error Alarm Trap" 
        ::= { ommp401AlarmNotification 133 }

	ommp401LineOtuBackwardDefectIndicationAlarmTrap NOTIFICATION-TYPE
		OBJECTS { ommp401LineOtuBackwardDefectIndicationAlarm  }
		STATUS  current
		DESCRIPTION
                        "OMMP401 OTU Backward Defect Indication Alarm Trap" 
        ::= { ommp401AlarmNotification 134 }

	ommp401LineOduSignalDegradeAlarmTrap NOTIFICATION-TYPE
		OBJECTS { ommp401LineOduSignalDegradeAlarm  }
		STATUS  current
		DESCRIPTION
                        "OMMP401 ODU Signal Degrade Alarm Trap" 
        ::= { ommp401AlarmNotification 136 }

	ommp401LineOduAlarmIndicationSignalAlarmTrap NOTIFICATION-TYPE
		OBJECTS { ommp401LineOduAlarmIndicationSignalAlarm  }
		STATUS  current
		DESCRIPTION
                        "OMMP401 ODU Alarm Indication Signal Alarm Trap" 
        ::= { ommp401AlarmNotification 137 }

	ommp401LineOduTrailTraceIdentifierMismatchAlarmTrap NOTIFICATION-TYPE
		OBJECTS { ommp401LineOtuTrailTraceIdentifierMismatchAlarm  }
		STATUS  current
		DESCRIPTION
                        "OMMP401 ODU Sapi Alarm Trap" 
        ::= { ommp401AlarmNotification 138 }

	ommp401LineOduLockedDefectAlarmTrap NOTIFICATION-TYPE
		OBJECTS { ommp401LineOduLockedDefectAlarm  }
		STATUS  current
		DESCRIPTION
                        "OMMP401 ODU Locked Defect Alarm Trap" 
        ::= { ommp401AlarmNotification 139 }

	ommp401LineOduOpenConnectionIndicationAlarmTrap NOTIFICATION-TYPE
		OBJECTS { ommp401LineOduOpenConnectionIndicationAlarm  }
		STATUS  current
		DESCRIPTION
                        "OMMP401 ODU Open Connection Indication Alarm Trap" 
        ::= { ommp401AlarmNotification 140 }

	ommp401LineOduBackwardDefectIndicationAlarmTrap NOTIFICATION-TYPE
		OBJECTS { ommp401LineOduBackwardDefectIndicationAlarm  }
		STATUS  current
		DESCRIPTION
                        "OMMP401 ODU Backward Defect Indication Alarm Trap" 
        ::= { ommp401AlarmNotification 141 }

	ommp401LineOduTcm1BackwardDefectIndicationAlarmTrap NOTIFICATION-TYPE
		OBJECTS { ommp401LineOduTcm1BackwardDefectIndicationAlarm  }
		STATUS  current
		DESCRIPTION
                        "OMMP401 ODU-TCM1 Backward Defect Indication Alarm Trap" 
        ::= { ommp401AlarmNotification 142 }

	ommp401LineOduTcm2BackwardDefectIndicationAlarmTrap NOTIFICATION-TYPE
		OBJECTS { ommp401LineOduTcm2BackwardDefectIndicationAlarm  }
		STATUS  current
		DESCRIPTION
                        "OMMP401 ODU-TCM2 Backward Defect Indication Alarm Trap" 
        ::= { ommp401AlarmNotification 143 }

	ommp401LineOduTcm3BackwardDefectIndicationAlarmTrap NOTIFICATION-TYPE
		OBJECTS { ommp401LineOduTcm3BackwardDefectIndicationAlarm  }
		STATUS  current
		DESCRIPTION
                        "OMMP401 ODU-TCM3 Backward Defect Indication Alarm Trap" 
        ::= { ommp401AlarmNotification 144 }

	ommp401LineOduTcm4BackwardDefectIndicationAlarmTrap NOTIFICATION-TYPE
		OBJECTS { ommp401LineOduTcm4BackwardDefectIndicationAlarm  }
		STATUS  current
		DESCRIPTION
                        "OMMP401 ODU-TCM4 Backward Defect Indication Alarm Trap" 
        ::= { ommp401AlarmNotification 145 }

	ommp401LineOduTcm5BackwardDefectIndicationAlarmTrap NOTIFICATION-TYPE
		OBJECTS { ommp401LineOduTcm5BackwardDefectIndicationAlarm  }
		STATUS  current
		DESCRIPTION
                        "OMMP401 ODU-TCM5 Backward Defect Indication Alarm Trap" 
        ::= { ommp401AlarmNotification 146 }

	ommp401LineOduTcm6BackwardDefectIndicationAlarmTrap NOTIFICATION-TYPE
		OBJECTS { ommp401LineOduTcm6BackwardDefectIndicationAlarm  }
		STATUS  current
		DESCRIPTION
                        "OMMP401 ODU-TCM6 Backward Defect Indication Alarm Trap" 
        ::= { ommp401AlarmNotification 147 }

	ommp401LineOduTcm1BackwardIncomingAlignmentErrorAlarmTrap NOTIFICATION-TYPE
		OBJECTS { ommp401LineOduTcm1BackwardIncomingAlignmentErrorAlarm  }
		STATUS  current
		DESCRIPTION
                        "OMMP401 ODU-TCM1 Open Connection Indication Alarm Trap" 
        ::= { ommp401AlarmNotification 148 }

	ommp401LineOduTcm2BackwardIncomingAlignmentErrorAlarmTrap NOTIFICATION-TYPE
		OBJECTS { ommp401LineOduTcm2BackwardIncomingAlignmentErrorAlarm  }
		STATUS  current
		DESCRIPTION
                        "OMMP401 ODU-TCM2 Open Connection Indication Alarm Trap" 
        ::= { ommp401AlarmNotification 149 }

	ommp401LineOduTcm3BackwardIncomingAlignmentErrorAlarmTrap NOTIFICATION-TYPE
		OBJECTS { ommp401LineOduTcm3BackwardIncomingAlignmentErrorAlarm  }
		STATUS  current
		DESCRIPTION
                        "OMMP401 ODU-TCM3 Open Connection Indication Alarm Trap" 
        ::= { ommp401AlarmNotification 150 }

	ommp401LineOduTcm4BackwardIncomingAlignmentErrorAlarmTrap NOTIFICATION-TYPE
		OBJECTS { ommp401LineOduTcm4BackwardIncomingAlignmentErrorAlarm  }
		STATUS  current
		DESCRIPTION
                        "OMMP401 ODU-TCM4 Open Connection Indication Alarm Trap" 
        ::= { ommp401AlarmNotification 151 }

	ommp401LineOduTcm5BackwardIncomingAlignmentErrorAlarmTrap NOTIFICATION-TYPE
		OBJECTS { ommp401LineOduTcm5BackwardIncomingAlignmentErrorAlarm  }
		STATUS  current
		DESCRIPTION
                        "OMMP401 ODU-TCM5 Open Connection Indication Alarm Trap" 
        ::= { ommp401AlarmNotification 152 }

	ommp401LineOduTcm6BackwardIncomingAlignmentErrorAlarmTrap NOTIFICATION-TYPE
		OBJECTS { ommp401LineOduTcm6BackwardIncomingAlignmentErrorAlarm  }
		STATUS  current
		DESCRIPTION
                        "OMMP401 ODU-TCM6 Open Connection Indication Alarm Trap" 
        ::= { ommp401AlarmNotification 153}

	ommp401LineOduTcm1LossOfTandemConnectionAlarmTrap NOTIFICATION-TYPE
		OBJECTS { ommp401LineOduTcm1LossOfTandemConnectionAlarm  }
		STATUS  current
		DESCRIPTION
                        "OMMP401 ODU-TCM1 Loss Of Tandem Connection Alarm Trap" 
        ::= { ommp401AlarmNotification 154 }

	ommp401LineOduTcm2LossOfTandemConnectionAlarmTrap NOTIFICATION-TYPE
		OBJECTS { ommp401LineOduTcm2LossOfTandemConnectionAlarm  }
		STATUS  current
		DESCRIPTION
                        "OMMP401 ODU-TCM2 Loss Of Tandem Connection Alarm Trap" 
        ::= { ommp401AlarmNotification 155 }

	ommp401LineOduTcm3LossOfTandemConnectionAlarmTrap NOTIFICATION-TYPE
		OBJECTS { ommp401LineOduTcm3LossOfTandemConnectionAlarm  }
		STATUS  current
		DESCRIPTION
                        "OMMP401 ODU-TCM3 Loss Of Tandem Connection Alarm Trap" 
        ::= { ommp401AlarmNotification 156 }

	ommp401LineOduTcm4LossOfTandemConnectionAlarmTrap NOTIFICATION-TYPE
		OBJECTS { ommp401LineOduTcm4LossOfTandemConnectionAlarm  }
		STATUS  current
		DESCRIPTION
                        "OMMP401 ODU-TCM4 Loss Of Tandem Connection Alarm Trap" 
        ::= { ommp401AlarmNotification 157 }

	ommp401LineOduTcm5LossOfTandemConnectionAlarmTrap NOTIFICATION-TYPE
		OBJECTS { ommp401LineOduTcm5LossOfTandemConnectionAlarm  }
		STATUS  current
		DESCRIPTION
                        "OMMP401 ODU-TCM5 Loss Of Tandem Connection Alarm Trap" 
        ::= { ommp401AlarmNotification 158 }

	ommp401LineOduTcm6LossOfTandemConnectionAlarmTrap NOTIFICATION-TYPE
		OBJECTS { ommp401LineOduTcm6LossOfTandemConnectionAlarm  }
		STATUS  current
		DESCRIPTION
                        "OMMP401 ODU-TCM6 Loss Of Tandem Connection Alarm Trap" 
        ::= { ommp401AlarmNotification 159 }

	ommp401LineOpuPayloadMismatchAlarmTrap NOTIFICATION-TYPE
		OBJECTS { ommp401LineOpuPayloadMismatchAlarm  }
		STATUS  current
		DESCRIPTION
                        "OMMP401 OPU Payload Mismatch Alarm Trap" 
        ::= { ommp401AlarmNotification 160 }

--*****************************************************************************
--				    PERFORMANCE
--*****************************************************************************        

	ommp401PerformanceTable OBJECT-TYPE
	      SYNTAX  SEQUENCE OF Ommp401PerformanceEntry
              MAX-ACCESS  not-accessible
              STATUS  current
              DESCRIPTION
                      "Gives Optical and Signal performance status of the OMMP401 card"
		::= { ommp401Performance 1 }	

	ommp401PerformanceEntry   OBJECT-TYPE
              SYNTAX  Ommp401PerformanceEntry 
              MAX-ACCESS  not-accessible
              STATUS  current
              DESCRIPTION 
              	""
		INDEX   { node, rack , subRack , slot , ommp401InterfaceNumber}
		::= { ommp401PerformanceTable 1 }
	
	Ommp401PerformanceEntry ::= 
		SEQUENCE {
				ommp401Cfp2InputPower							DisplayString,
				ommp401Cfp2OutputPower						DisplayString,
				ommp401Cfp2SupplyVoltage						DisplayString,
				ommp401Cfp2Temperature						DisplayString,
				ommp401Qsfp28InputPower							DisplayString,
				ommp401Qsfp28OutputPower						DisplayString,
				ommp401Qsfp28BiasCurrent						DisplayString,
				ommp401Qsfp28SupplyVoltage						DisplayString,
				ommp401Qsfp28Temperature						DisplayString,
				ommp401OtnFecUncorrectedWords					DisplayString,
				ommp401OtnFecCorrectedBits					DisplayString,
				ommp401OtnFecZerosCorrectedBits					DisplayString,
				ommp401OtnFecOnesCorrectedBits					DisplayString,
				ommp401OtuBitInterleavedParityErrors					DisplayString,
				ommp401OtuIncomingAlignmentErrorSeconds					DisplayString,
				ommp401OtuBackwardErrorIndicationErrorCount					DisplayString,
				ommp401OtuBackwardIncomingAlignmentErrorSeconds					DisplayString,
				ommp401OtuErrorFreeSeconds					DisplayString,
				ommp401OtuErrorSeconds					DisplayString,
				ommp401OtuBackgroundBlockErrors					DisplayString,
				ommp401OtuSevereErrorSeconds					DisplayString,
				ommp401OtuUnavailableSeconds					DisplayString,
				ommp401OtuErrorSecondsErrorRatio					DisplayString,
				ommp401OtuErrorFreePeriod					DisplayString,
				ommp401OtuErroredPeriod					DisplayString,
				ommp401OtuConsecutiveSevereErrorSecond					DisplayString,
				ommp401OtuNonConsecutiveSevereErrorSecond					DisplayString,
				ommp401OtuPathAvailabilityStatus					DisplayString,
				ommp401OtuBackgroundBlockErrorRatio					DisplayString,
				ommp401OtuSevereErrorSecondsErrorRatio					DisplayString,
				ommp401OtuFarEndErrorFreeSeconds					DisplayString,
				ommp401OtuFarEndBackgroundBlockErrors					DisplayString,
				ommp401OtuFarEndSevereErrorSeconds					DisplayString,
				ommp401OtuFarEndUnavailableSeconds					DisplayString,
				ommp401OtuFarEndErrorSecondsErrorRatio					DisplayString,
				ommp401OtuFarEndErrorSeconds					DisplayString,
				ommp401OtuFarEndBackgroundBlockErrorRatio					DisplayString,
				ommp401OtuFarEndSevereErrorSecondsErrorRatio					DisplayString,
				ommp401OtuErrorRatio					DisplayString,
				ommp401OtuFarEndErrorFreePeriod					DisplayString,
				ommp401OtuFarEndErroredPeriod					DisplayString,
				ommp401OtuFarEndConsecutiveSevereErrorSecond					DisplayString,
				ommp401OtuFarEndNonConsecutiveSevereErrorSecond					DisplayString,
				ommp401OtuFarEndPathAvailabilityStatus					DisplayString,
				ommp401OtuFramesReceived					DisplayString,
				ommp401OtuBitErrorRate					DisplayString,
				ommp401OduBitInterleavedParityErrors					DisplayString,
				ommp401OduTcm1BitInterleavedParityErrors					DisplayString,
				ommp401OduTcm2BitInterleavedParityErrors					DisplayString,
				ommp401OduTcm3BitInterleavedParityErrors					DisplayString,
				ommp401OduTcm4BitInterleavedParityErrors					DisplayString,
				ommp401OduTcm5BitInterleavedParityErrors					DisplayString,
				ommp401OduTcm6BitInterleavedParityErrors					DisplayString,
				ommp401OduTcm1IncomingAlignmentErrorSeconds					DisplayString,
				ommp401OduBackwardErrorIndicationErrorCount					DisplayString,
				ommp401OduTcm1BackwardErrorIndicationErrorCount					DisplayString,
				ommp401OduTcm2BackwardErrorIndicationErrorCount					DisplayString,
				ommp401OduTcm3BackwardErrorIndicationErrorCount					DisplayString,
				ommp401OduTcm4BackwardErrorIndicationErrorCount					DisplayString,
				ommp401OduTcm5BackwardErrorIndicationErrorCount					DisplayString,
				ommp401OduTcm6BackwardErrorIndicationErrorCount					DisplayString,
				ommp401OduTcm1BackwardIncomingAlignmentErrorSeconds					DisplayString,
				ommp401OduDelayMeasurement					DisplayString,
				ommp401OduErrorFreeSeconds					DisplayString,
				ommp401OduErrorSeconds					DisplayString,
				ommp401OduBackgroundBlockErrors					DisplayString,
				ommp401OduSevereErrorSeconds					DisplayString,
				ommp401OduUnavailableSeconds					DisplayString,
				ommp401OduErrorFreePeriod					DisplayString,
				ommp401OduErroredPeriod					DisplayString,
				ommp401OduConsecutiveSevereErrorSecond					DisplayString,
				ommp401OduNonConsecutiveSevereErrorSecond					DisplayString,
				ommp401OduPathAvailabilityStatus					DisplayString,
				ommp401OduFarEndErrorFreePeriod					DisplayString,
				ommp401OduFarEndErroredPeriod					DisplayString,
				ommp401OduFarEndConsecutiveSevereErrorSecond					DisplayString,
				ommp401OduFarEndNonConsecutiveSevereErrorSecond					DisplayString,
				ommp401OduFarEndPathAvailabilityStatus					DisplayString,
				ommp401OduFramesReceived					DisplayString,
				ommp401OduErrorSecondsErrorRatio					DisplayString,
				ommp401OduBackgroundBlockErrorRatio					DisplayString,
				ommp401OduSevereErrorSecondsErrorRatio					DisplayString,
				ommp401OduFarEndErrorFreeSeconds					DisplayString,
				ommp401OduFarEndErrorSeconds					DisplayString,
				ommp401OduFarEndBackgroundBlockErrors					DisplayString,
				ommp401OduFarEndSevereErrorSeconds					DisplayString,
				ommp401OduFarEndUnavailableSeconds					DisplayString,
				ommp401OduFarEndErrorSecondsErrorRatio					DisplayString,
				ommp401OduFarEndBackgroundBlockErrorRatio					DisplayString,
				ommp401OduFarEndSevereErrorSecondsErrorRatio					DisplayString,
				ommp401OtnMeasurementPeriod					DisplayString,
				ommp401OduTcm1ErrorFreeSeconds					DisplayString,
				ommp401OduTcm1ErrorSeconds					DisplayString,
				ommp401OduTcm1BackgroundBlockErrors					DisplayString,
				ommp401OduTcm1SevereErrorSeconds					DisplayString,
				ommp401OduTcm1UnavailableSeconds					DisplayString,
				ommp401OduTcm1ErrorFreePeriod					DisplayString,
				ommp401OduTcm1ErroredPeriod					DisplayString,
				ommp401OduTcm1ConsecutiveSevereErrorSecond					DisplayString,
				ommp401OduTcm1NonConsecutiveSevereErrorSecond					DisplayString,
				ommp401OduTcm1PathAvailabilityStatus					DisplayString,
				ommp401OduTcm1BackgroundBlockErrorRatio					DisplayString,
				ommp401OduTcm1SevereErrorSecondsErrorRatio					DisplayString,
				ommp401OduTcm1FarEndErrorFreeSeconds					DisplayString,
				ommp401OduTcm1FarEndErrorSeconds					DisplayString,
				ommp401OduTcm1FarEndBackgroundBlockErrors					DisplayString,
				ommp401OduTcm1FarEndSevereErrorSeconds					DisplayString,
				ommp401OduTcm1FarEndUnavailableSeconds					DisplayString,
				ommp401OduTcm1FarEndErrorFreePeriod					DisplayString,
				ommp401OduTcm1FarEndErroredPeriod					DisplayString,
				ommp401OduTcm1FarEndConsecutiveSevereErrorSecond					DisplayString,
				ommp401OduTcm1FarEndNonConsecutiveSevereErrorSecond					DisplayString,
				ommp401OduTcm1FarEndPathAvailabilityStatus					DisplayString,
				ommp401OduTcm1FarEndBackgroundBlockErrorRatio					DisplayString,
				ommp401OduTcm1FarEndSevereErrorSecondsErrorRatio					DisplayString,
				ommp401OduTcm2ErrorFreeSeconds					DisplayString,
				ommp401OduTcm2ErrorSeconds					DisplayString,
				ommp401OduTcm2BackgroundBlockErrors					DisplayString,
				ommp401OduTcm2SevereErrorSeconds					DisplayString,
				ommp401OduTcm2UnavailableSeconds					DisplayString,
				ommp401OduTcm2ErrorFreePeriod					DisplayString,
				ommp401OduTcm2ErroredPeriod					DisplayString,
				ommp401OduTcm2ConsecutiveSevereErrorSecond					DisplayString,
				ommp401OduTcm2NonConsecutiveSevereErrorSecond					DisplayString,
				ommp401OduTcm2PathAvailabilityStatus					DisplayString,
				ommp401OduTcm2BackgroundBlockErrorRatio					DisplayString,
				ommp401OduTcm2SevereErrorSecondsErrorRatio					DisplayString,
				ommp401OduTcm2FarEndErrorFreeSeconds					DisplayString,
				ommp401OduTcm2FarEndErrorSeconds					DisplayString,
				ommp401OduTcm2FarEndBackgroundBlockErrors					DisplayString,
				ommp401OduTcm2FarEndSevereErrorSeconds					DisplayString,
				ommp401OduTcm2FarEndUnavailableSeconds					DisplayString,
				ommp401OduTcm2FarEndErrorFreePeriod					DisplayString,
				ommp401OduTcm2FarEndErroredPeriod					DisplayString,
				ommp401OduTcm2FarEndConsecutiveSevereErrorSecond					DisplayString,
				ommp401OduTcm2FarEndNonConsecutiveSevereErrorSecond					DisplayString,
				ommp401OduTcm2FarEndPathAvailabilityStatus					DisplayString,
				ommp401OduTcm2FarEndBackgroundBlockErrorRatio					DisplayString,
				ommp401OduTcm2FarEndSevereErrorSecondsErrorRatio					DisplayString,
				ommp401OduTcm3ErrorFreeSeconds					DisplayString,
				ommp401OduTcm3ErrorSeconds					DisplayString,
				ommp401OduTcm3BackgroundBlockErrors					DisplayString,
				ommp401OduTcm3SevereErrorSeconds					DisplayString,
				ommp401OduTcm3UnavailableSeconds					DisplayString,
				ommp401OduTcm3ErrorFreePeriod					DisplayString,
				ommp401OduTcm3ErroredPeriod					DisplayString,
				ommp401OduTcm3ConsecutiveSevereErrorSecond					DisplayString,
				ommp401OduTcm3NonConsecutiveSevereErrorSecond					DisplayString,
				ommp401OduTcm3PathAvailabilityStatus					DisplayString,
				ommp401OduTcm3BackgroundBlockErrorRatio					DisplayString,
				ommp401OduTcm3SevereErrorSecondsErrorRatio					DisplayString,
				ommp401OduTcm3FarEndErrorFreeSeconds					DisplayString,
				ommp401OduTcm3FarEndErrorSeconds					DisplayString,
				ommp401OduTcm3FarEndBackgroundBlockErrors					DisplayString,
				ommp401OduTcm3FarEndSevereErrorSeconds					DisplayString,
				ommp401OduTcm3FarEndUnavailableSeconds					DisplayString,
				ommp401OduTcm3FarEndErrorFreePeriod					DisplayString,
				ommp401OduTcm3FarEndErroredPeriod					DisplayString,
				ommp401OduTcm3FarEndConsecutiveSevereErrorSecond					DisplayString,
				ommp401OduTcm3FarEndNonConsecutiveSevereErrorSecond					DisplayString,
				ommp401OduTcm3FarEndPathAvailabilityStatus					DisplayString,
				ommp401OduTcm3FarEndBackgroundBlockErrorRatio					DisplayString,
				ommp401OduTcm3FarEndSevereErrorSecondsErrorRatio					DisplayString,
				ommp401OduTcm4ErrorFreeSeconds					DisplayString,
				ommp401OduTcm4ErrorSeconds					DisplayString,
				ommp401OduTcm4BackgroundBlockErrors					DisplayString,
				ommp401OduTcm4SevereErrorSeconds					DisplayString,
				ommp401OduTcm4UnavailableSeconds					DisplayString,
				ommp401OduTcm4ErrorFreePeriod					DisplayString,
				ommp401OduTcm4ErroredPeriod					DisplayString,
				ommp401OduTcm4ConsecutiveSevereErrorSecond					DisplayString,
				ommp401OduTcm4NonConsecutiveSevereErrorSecond					DisplayString,
				ommp401OduTcm4PathAvailabilityStatus					DisplayString,
				ommp401OduTcm4BackgroundBlockErrorRatio					DisplayString,
				ommp401OduTcm4SevereErrorSecondsErrorRatio					DisplayString,
				ommp401OduTcm4FarEndErrorFreeSeconds					DisplayString,
				ommp401OduTcm4FarEndErrorSeconds					DisplayString,
				ommp401OduTcm4FarEndBackgroundBlockErrors					DisplayString,
				ommp401OduTcm4FarEndSevereErrorSeconds					DisplayString,
				ommp401OduTcm4FarEndUnavailableSeconds					DisplayString,
				ommp401OduTcm4FarEndErrorFreePeriod					DisplayString,
				ommp401OduTcm4FarEndErroredPeriod					DisplayString,
				ommp401OduTcm4FarEndConsecutiveSevereErrorSecond					DisplayString,
				ommp401OduTcm4FarEndNonConsecutiveSevereErrorSecond					DisplayString,
				ommp401OduTcm4FarEndPathAvailabilityStatus					DisplayString,
				ommp401OduTcm4FarEndBackgroundBlockErrorRatio					DisplayString,
				ommp401OduTcm4FarEndSevereErrorSecondsErrorRatio					DisplayString,
				ommp401OduTcm5ErrorFreeSeconds					DisplayString,
				ommp401OduTcm5ErrorSeconds					DisplayString,
				ommp401OduTcm5BackgroundBlockErrors					DisplayString,
				ommp401OduTcm5SevereErrorSeconds					DisplayString,
				ommp401OduTcm5UnavailableSeconds					DisplayString,
				ommp401OduTcm5ErrorFreePeriod					DisplayString,
				ommp401OduTcm5ErroredPeriod					DisplayString,
				ommp401OduTcm5ConsecutiveSevereErrorSecond					DisplayString,
				ommp401OduTcm5NonConsecutiveSevereErrorSecond					DisplayString,
				ommp401OduTcm5PathAvailabilityStatus					DisplayString,
				ommp401OduTcm5BackgroundBlockErrorRatio					DisplayString,
				ommp401OduTcm5SevereErrorSecondsErrorRatio					DisplayString,
				ommp401OduTcm5FarEndErrorFreeSeconds					DisplayString,
				ommp401OduTcm5FarEndErrorSeconds					DisplayString,
				ommp401OduTcm5FarEndBackgroundBlockErrors					DisplayString,
				ommp401OduTcm5FarEndSevereErrorSeconds					DisplayString,
				ommp401OduTcm5FarEndUnavailableSeconds					DisplayString,
				ommp401OduTcm5FarEndErrorFreePeriod					DisplayString,
				ommp401OduTcm5FarEndErroredPeriod					DisplayString,
				ommp401OduTcm5FarEndConsecutiveSevereErrorSecond					DisplayString,
				ommp401OduTcm5FarEndNonConsecutiveSevereErrorSecond					DisplayString,
				ommp401OduTcm5FarEndPathAvailabilityStatus					DisplayString,
				ommp401OduTcm5FarEndBackgroundBlockErrorRatio					DisplayString,
				ommp401OduTcm5FarEndSevereErrorSecondsErrorRatio					DisplayString,
				ommp401OduTcm6ErrorFreeSeconds					DisplayString,
				ommp401OduTcm6ErrorSeconds					DisplayString,
				ommp401OduTcm6BackgroundBlockErrors					DisplayString,
				ommp401OduTcm6SevereErrorSeconds					DisplayString,
				ommp401OduTcm6UnavailableSeconds					DisplayString,
				ommp401OduTcm6ErrorFreePeriod					DisplayString,
				ommp401OduTcm6ErroredPeriod					DisplayString,
				ommp401OduTcm6ConsecutiveSevereErrorSecond					DisplayString,
				ommp401OduTcm6NonConsecutiveSevereErrorSecond					DisplayString,
				ommp401OduTcm6PathAvailabilityStatus					DisplayString,
				ommp401OduTcm6BackgroundBlockErrorRatio					DisplayString,
				ommp401OduTcm6SevereErrorSecondsErrorRatio					DisplayString,
				ommp401OduTcm6FarEndErrorFreeSeconds					DisplayString,
				ommp401OduTcm6FarEndErrorSeconds					DisplayString,
				ommp401OduTcm6FarEndBackgroundBlockErrors					DisplayString,
				ommp401OduTcm6FarEndSevereErrorSeconds					DisplayString,
				ommp401OduTcm6FarEndUnavailableSeconds					DisplayString,
				ommp401OduTcm6FarEndErrorFreePeriod					DisplayString,
				ommp401OduTcm6FarEndErroredPeriod					DisplayString,
				ommp401OduTcm6FarEndConsecutiveSevereErrorSecond					DisplayString,
				ommp401OduTcm6FarEndNonConsecutiveSevereErrorSecond					DisplayString,
				ommp401OduTcm6FarEndPathAvailabilityStatus					DisplayString,
				ommp401OduTcm6FarEndBackgroundBlockErrorRatio					DisplayString,
				ommp401OduTcm6FarEndSevereErrorSecondsErrorRatio					DisplayString,
				ommp401EthernetMacTerminatedFramesTransmitted					DisplayString,
				ommp401EthernetMacTerminatedFramesReceived					DisplayString,
				ommp401EthernetMacTerminatedPauseFramesTransmitted					DisplayString,
				ommp401EthernetMacTerminatedPauseFramesReceived					DisplayString,
				ommp401EthernetMacTerminatedUnicastFramesTransmitted					DisplayString,
				ommp401EthernetMacTerminatedUnicastFramesReceived					DisplayString,
				ommp401EthernetMacTerminatedMulticastFramesTransmitted					DisplayString,
				ommp401EthernetMacTerminatedMulticastFramesReceived					DisplayString,
				ommp401EthernetMacTerminatedBroadcastFramesTransmitted					DisplayString,
				ommp401EthernetMacTerminatedBroadcastFramesReceived					DisplayString,
				ommp401EthernetMacTerminatedUnderSizeFramesTransmitted					DisplayString,
				ommp401EthernetMacTerminatedUnderSizeFramesReceived					DisplayString,
				ommp401EthernetMacTerminatedOverSizeFramesTransmitted					DisplayString,
				ommp401EthernetMacTerminatedOverSizeFramesReceived					DisplayString,
				ommp401EthernetMacTerminatedFragmentFramesTransmitted					DisplayString,
				ommp401EthernetMacTerminatedFragmentFramesReceived					DisplayString,
				ommp401EthernetMacTerminatedFrameCheckSequenceErrorsTransmitted					DisplayString,
				ommp401EthernetMacTerminatedFrameCheckSequenceErrorsReceived					DisplayString,
				ommp401EthernetMacTerminatedBytesTransmitted					DisplayString,
				ommp401EthernetMacTerminatedBytesReceived					DisplayString,
				ommp401EthernetMacTerminatedJabberFramesTransmitted					DisplayString,
				ommp401EthernetMacTerminatedJabberFramesReceived					DisplayString,
				ommp401EthernetMacTerminated64BytesFramesTransmitted					DisplayString,
				ommp401EthernetMacTerminated64BytesFramesReceived					DisplayString,
				ommp401EthernetMacTerminated65to127BytesFramesTransmitted					DisplayString,
				ommp401EthernetMacTerminated65to127BytesFramesReceived					DisplayString,
				ommp401EthernetMacTerminated128to255BytesFramesTransmitted					DisplayString,
				ommp401EthernetMacTerminated128to255BytesFramesReceived					DisplayString,
				ommp401EthernetMacTerminated256to511BytesFramesTransmitted					DisplayString,
				ommp401EthernetMacTerminated256to511BytesFramesReceived					DisplayString,
				ommp401EthernetMacTerminated512to1023BytesFramesTransmitted					DisplayString,
				ommp401EthernetMacTerminated512to1023BytesFramesReceived					DisplayString,
				ommp401EthernetMacTerminated1024to1518BytesFramesTransmitted					DisplayString,
				ommp401EthernetMacTerminated1024to1518BytesFramesReceived					DisplayString,
				ommp401EthernetMacTerminated1519toMaxBytesFramesTransmitted					DisplayString,
				ommp401EthernetMacTerminated1519toMaxBytesFramesReceived					DisplayString,
				ommp401EthernetMacTerminatedJumboFramesTransmitted					DisplayString,
				ommp401EthernetMacTerminatedJumboFramesReceived					DisplayString,
				ommp401LineOtnFecUncorrectedWords					DisplayString,
				ommp401LineOtnFecCorrectedBits					DisplayString,
				ommp401LineOtnFecZerosCorrectedBits					DisplayString,
				ommp401LineOtnFecOnesCorrectedBits					DisplayString,
				ommp401LineOtuBitInterleavedParityErrors					DisplayString,
				ommp401LineOtuIncomingAlignmentErrorSeconds					DisplayString,
				ommp401LineOtuBackwardErrorIndicationErrorCount					DisplayString,
				ommp401LineOtuBackwardIncomingAlignmentErrorSeconds					DisplayString,
				ommp401LineOtuErrorFreeSeconds					DisplayString,
				ommp401LineOtuErrorSeconds					DisplayString,
				ommp401LineOtuBackgroundBlockErrors					DisplayString,
				ommp401LineOtuSevereErrorSeconds					DisplayString,
				ommp401LineOtuUnavailableSeconds					DisplayString,
				ommp401LineOtuErrorSecondsErrorRatio					DisplayString,
				ommp401LineOtuErrorFreePeriod					DisplayString,
				ommp401LineOtuErroredPeriod					DisplayString,
				ommp401LineOtuConsecutiveSevereErrorSecond					DisplayString,
				ommp401LineOtuNonConsecutiveSevereErrorSecond					DisplayString,
				ommp401LineOtuPathAvailabilityStatus					DisplayString,
				ommp401LineOtuBackgroundBlockErrorRatio					DisplayString,
				ommp401LineOtuSevereErrorSecondsErrorRatio					DisplayString,
				ommp401LineOtuFarEndErrorFreeSeconds					DisplayString,
				ommp401LineOtuFarEndBackgroundBlockErrors					DisplayString,
				ommp401LineOtuFarEndSevereErrorSeconds					DisplayString,
				ommp401LineOtuFarEndUnavailableSeconds					DisplayString,
				ommp401LineOtuFarEndErrorSecondsErrorRatio					DisplayString,
				ommp401LineOtuFarEndErrorSeconds					DisplayString,
				ommp401LineOtuFarEndBackgroundBlockErrorRatio					DisplayString,
				ommp401LineOtuFarEndSevereErrorSecondsErrorRatio					DisplayString,
				ommp401LineOtuErrorRatio					DisplayString,
				ommp401LineOtuFarEndErrorFreePeriod					DisplayString,
				ommp401LineOtuFarEndErroredPeriod					DisplayString,
				ommp401LineOtuFarEndConsecutiveSevereErrorSecond					DisplayString,
				ommp401LineOtuFarEndNonConsecutiveSevereErrorSecond					DisplayString,
				ommp401LineOtuFarEndPathAvailabilityStatus					DisplayString,
				ommp401LineOtuFramesReceived					DisplayString,
				ommp401LineOtuBitErrorRate					DisplayString,
				ommp401LineOduBitInterleavedParityErrors					DisplayString,
				ommp401LineOduTcm1BitInterleavedParityErrors					DisplayString,
				ommp401LineOduTcm2BitInterleavedParityErrors					DisplayString,
				ommp401LineOduTcm3BitInterleavedParityErrors					DisplayString,
				ommp401LineOduTcm4BitInterleavedParityErrors					DisplayString,
				ommp401LineOduTcm5BitInterleavedParityErrors					DisplayString,
				ommp401LineOduTcm6BitInterleavedParityErrors					DisplayString,
				ommp401LineOduTcm1IncomingAlignmentErrorSeconds					DisplayString,
				ommp401LineOduBackwardErrorIndicationErrorCount					DisplayString,
				ommp401LineOduTcm1BackwardErrorIndicationErrorCount					DisplayString,
				ommp401LineOduTcm2BackwardErrorIndicationErrorCount					DisplayString,
				ommp401LineOduTcm3BackwardErrorIndicationErrorCount					DisplayString,
				ommp401LineOduTcm4BackwardErrorIndicationErrorCount					DisplayString,
				ommp401LineOduTcm5BackwardErrorIndicationErrorCount					DisplayString,
				ommp401LineOduTcm6BackwardErrorIndicationErrorCount					DisplayString,
				ommp401LineOduTcm1BackwardIncomingAlignmentErrorSeconds					DisplayString,
				ommp401LineOduDelayMeasurement					DisplayString,
				ommp401LineOduErrorFreeSeconds					DisplayString,
				ommp401LineOduErrorSeconds					DisplayString,
				ommp401LineOduBackgroundBlockErrors					DisplayString,
				ommp401LineOduSevereErrorSeconds					DisplayString,
				ommp401LineOduUnavailableSeconds					DisplayString,
				ommp401LineOduErrorFreePeriod					DisplayString,
				ommp401LineOduErroredPeriod					DisplayString,
				ommp401LineOduConsecutiveSevereErrorSecond					DisplayString,
				ommp401LineOduNonConsecutiveSevereErrorSecond					DisplayString,
				ommp401LineOduPathAvailabilityStatus					DisplayString,
				ommp401LineOduFarEndErrorFreePeriod					DisplayString,
				ommp401LineOduFarEndErroredPeriod					DisplayString,
				ommp401LineOduFarEndConsecutiveSevereErrorSecond					DisplayString,
				ommp401LineOduFarEndNonConsecutiveSevereErrorSecond					DisplayString,
				ommp401LineOduFarEndPathAvailabilityStatus					DisplayString,
				ommp401LineOduFramesReceived					DisplayString,
				ommp401LineOduErrorSecondsErrorRatio					DisplayString,
				ommp401LineOduBackgroundBlockErrorRatio					DisplayString,
				ommp401LineOduSevereErrorSecondsErrorRatio					DisplayString,
				ommp401LineOduFarEndErrorFreeSeconds					DisplayString,
				ommp401LineOduFarEndErrorSeconds					DisplayString,
				ommp401LineOduFarEndBackgroundBlockErrors					DisplayString,
				ommp401LineOduFarEndSevereErrorSeconds					DisplayString,
				ommp401LineOduFarEndUnavailableSeconds					DisplayString,
				ommp401LineOduFarEndErrorSecondsErrorRatio					DisplayString,
				ommp401LineOduFarEndBackgroundBlockErrorRatio					DisplayString,
				ommp401LineOduFarEndSevereErrorSecondsErrorRatio					DisplayString,
				ommp401LineOtnMeasurementPeriod					DisplayString,
				ommp401LineOduTcm1ErrorFreeSeconds					DisplayString,
				ommp401LineOduTcm1ErrorSeconds					DisplayString,
				ommp401LineOduTcm1BackgroundBlockErrors					DisplayString,
				ommp401LineOduTcm1SevereErrorSeconds					DisplayString,
				ommp401LineOduTcm1UnavailableSeconds					DisplayString,
				ommp401LineOduTcm1ErrorFreePeriod					DisplayString,
				ommp401LineOduTcm1ErroredPeriod					DisplayString,
				ommp401LineOduTcm1ConsecutiveSevereErrorSecond					DisplayString,
				ommp401LineOduTcm1NonConsecutiveSevereErrorSecond					DisplayString,
				ommp401LineOduTcm1PathAvailabilityStatus					DisplayString,
				ommp401LineOduTcm1BackgroundBlockErrorRatio					DisplayString,
				ommp401LineOduTcm1SevereErrorSecondsErrorRatio					DisplayString,
				ommp401LineOduTcm1FarEndErrorFreeSeconds					DisplayString,
				ommp401LineOduTcm1FarEndErrorSeconds					DisplayString,
				ommp401LineOduTcm1FarEndBackgroundBlockErrors					DisplayString,
				ommp401LineOduTcm1FarEndSevereErrorSeconds					DisplayString,
				ommp401LineOduTcm1FarEndUnavailableSeconds					DisplayString,
				ommp401LineOduTcm1FarEndErrorFreePeriod					DisplayString,
				ommp401LineOduTcm1FarEndErroredPeriod					DisplayString,
				ommp401LineOduTcm1FarEndConsecutiveSevereErrorSecond					DisplayString,
				ommp401LineOduTcm1FarEndNonConsecutiveSevereErrorSecond					DisplayString,
				ommp401LineOduTcm1FarEndPathAvailabilityStatus					DisplayString,
				ommp401LineOduTcm1FarEndBackgroundBlockErrorRatio					DisplayString,
				ommp401LineOduTcm1FarEndSevereErrorSecondsErrorRatio					DisplayString,
				ommp401LineOduTcm2ErrorFreeSeconds					DisplayString,
				ommp401LineOduTcm2ErrorSeconds					DisplayString,
				ommp401LineOduTcm2BackgroundBlockErrors					DisplayString,
				ommp401LineOduTcm2SevereErrorSeconds					DisplayString,
				ommp401LineOduTcm2UnavailableSeconds					DisplayString,
				ommp401LineOduTcm2ErrorFreePeriod					DisplayString,
				ommp401LineOduTcm2ErroredPeriod					DisplayString,
				ommp401LineOduTcm2ConsecutiveSevereErrorSecond					DisplayString,
				ommp401LineOduTcm2NonConsecutiveSevereErrorSecond					DisplayString,
				ommp401LineOduTcm2PathAvailabilityStatus					DisplayString,
				ommp401LineOduTcm2BackgroundBlockErrorRatio					DisplayString,
				ommp401LineOduTcm2SevereErrorSecondsErrorRatio					DisplayString,
				ommp401LineOduTcm2FarEndErrorFreeSeconds					DisplayString,
				ommp401LineOduTcm2FarEndErrorSeconds					DisplayString,
				ommp401LineOduTcm2FarEndBackgroundBlockErrors					DisplayString,
				ommp401LineOduTcm2FarEndSevereErrorSeconds					DisplayString,
				ommp401LineOduTcm2FarEndUnavailableSeconds					DisplayString,
				ommp401LineOduTcm2FarEndErrorFreePeriod					DisplayString,
				ommp401LineOduTcm2FarEndErroredPeriod					DisplayString,
				ommp401LineOduTcm2FarEndConsecutiveSevereErrorSecond					DisplayString,
				ommp401LineOduTcm2FarEndNonConsecutiveSevereErrorSecond					DisplayString,
				ommp401LineOduTcm2FarEndPathAvailabilityStatus					DisplayString,
				ommp401LineOduTcm2FarEndBackgroundBlockErrorRatio					DisplayString,
				ommp401LineOduTcm2FarEndSevereErrorSecondsErrorRatio					DisplayString,
				ommp401LineOduTcm3ErrorFreeSeconds					DisplayString,
				ommp401LineOduTcm3ErrorSeconds					DisplayString,
				ommp401LineOduTcm3BackgroundBlockErrors					DisplayString,
				ommp401LineOduTcm3SevereErrorSeconds					DisplayString,
				ommp401LineOduTcm3UnavailableSeconds					DisplayString,
				ommp401LineOduTcm3ErrorFreePeriod					DisplayString,
				ommp401LineOduTcm3ErroredPeriod					DisplayString,
				ommp401LineOduTcm3ConsecutiveSevereErrorSecond					DisplayString,
				ommp401LineOduTcm3NonConsecutiveSevereErrorSecond					DisplayString,
				ommp401LineOduTcm3PathAvailabilityStatus					DisplayString,
				ommp401LineOduTcm3BackgroundBlockErrorRatio					DisplayString,
				ommp401LineOduTcm3SevereErrorSecondsErrorRatio					DisplayString,
				ommp401LineOduTcm3FarEndErrorFreeSeconds					DisplayString,
				ommp401LineOduTcm3FarEndErrorSeconds					DisplayString,
				ommp401LineOduTcm3FarEndBackgroundBlockErrors					DisplayString,
				ommp401LineOduTcm3FarEndSevereErrorSeconds					DisplayString,
				ommp401LineOduTcm3FarEndUnavailableSeconds					DisplayString,
				ommp401LineOduTcm3FarEndErrorFreePeriod					DisplayString,
				ommp401LineOduTcm3FarEndErroredPeriod					DisplayString,
				ommp401LineOduTcm3FarEndConsecutiveSevereErrorSecond					DisplayString,
				ommp401LineOduTcm3FarEndNonConsecutiveSevereErrorSecond					DisplayString,
				ommp401LineOduTcm3FarEndPathAvailabilityStatus					DisplayString,
				ommp401LineOduTcm3FarEndBackgroundBlockErrorRatio					DisplayString,
				ommp401LineOduTcm3FarEndSevereErrorSecondsErrorRatio					DisplayString,
				ommp401LineOduTcm4ErrorFreeSeconds					DisplayString,
				ommp401LineOduTcm4ErrorSeconds					DisplayString,
				ommp401LineOduTcm4BackgroundBlockErrors					DisplayString,
				ommp401LineOduTcm4SevereErrorSeconds					DisplayString,
				ommp401LineOduTcm4UnavailableSeconds					DisplayString,
				ommp401LineOduTcm4ErrorFreePeriod					DisplayString,
				ommp401LineOduTcm4ErroredPeriod					DisplayString,
				ommp401LineOduTcm4ConsecutiveSevereErrorSecond					DisplayString,
				ommp401LineOduTcm4NonConsecutiveSevereErrorSecond					DisplayString,
				ommp401LineOduTcm4PathAvailabilityStatus					DisplayString,
				ommp401LineOduTcm4BackgroundBlockErrorRatio					DisplayString,
				ommp401LineOduTcm4SevereErrorSecondsErrorRatio					DisplayString,
				ommp401LineOduTcm4FarEndErrorFreeSeconds					DisplayString,
				ommp401LineOduTcm4FarEndErrorSeconds					DisplayString,
				ommp401LineOduTcm4FarEndBackgroundBlockErrors					DisplayString,
				ommp401LineOduTcm4FarEndSevereErrorSeconds					DisplayString,
				ommp401LineOduTcm4FarEndUnavailableSeconds					DisplayString,
				ommp401LineOduTcm4FarEndErrorFreePeriod					DisplayString,
				ommp401LineOduTcm4FarEndErroredPeriod					DisplayString,
				ommp401LineOduTcm4FarEndConsecutiveSevereErrorSecond					DisplayString,
				ommp401LineOduTcm4FarEndNonConsecutiveSevereErrorSecond					DisplayString,
				ommp401LineOduTcm4FarEndPathAvailabilityStatus					DisplayString,
				ommp401LineOduTcm4FarEndBackgroundBlockErrorRatio					DisplayString,
				ommp401LineOduTcm4FarEndSevereErrorSecondsErrorRatio					DisplayString,
				ommp401LineOduTcm5ErrorFreeSeconds					DisplayString,
				ommp401LineOduTcm5ErrorSeconds					DisplayString,
				ommp401LineOduTcm5BackgroundBlockErrors					DisplayString,
				ommp401LineOduTcm5SevereErrorSeconds					DisplayString,
				ommp401LineOduTcm5UnavailableSeconds					DisplayString,
				ommp401LineOduTcm5ErrorFreePeriod					DisplayString,
				ommp401LineOduTcm5ErroredPeriod					DisplayString,
				ommp401LineOduTcm5ConsecutiveSevereErrorSecond					DisplayString,
				ommp401LineOduTcm5NonConsecutiveSevereErrorSecond					DisplayString,
				ommp401LineOduTcm5PathAvailabilityStatus					DisplayString,
				ommp401LineOduTcm5BackgroundBlockErrorRatio					DisplayString,
				ommp401LineOduTcm5SevereErrorSecondsErrorRatio					DisplayString,
				ommp401LineOduTcm5FarEndErrorFreeSeconds					DisplayString,
				ommp401LineOduTcm5FarEndErrorSeconds					DisplayString,
				ommp401LineOduTcm5FarEndBackgroundBlockErrors					DisplayString,
				ommp401LineOduTcm5FarEndSevereErrorSeconds					DisplayString,
				ommp401LineOduTcm5FarEndUnavailableSeconds					DisplayString,
				ommp401LineOduTcm5FarEndErrorFreePeriod					DisplayString,
				ommp401LineOduTcm5FarEndErroredPeriod					DisplayString,
				ommp401LineOduTcm5FarEndConsecutiveSevereErrorSecond					DisplayString,
				ommp401LineOduTcm5FarEndNonConsecutiveSevereErrorSecond					DisplayString,
				ommp401LineOduTcm5FarEndPathAvailabilityStatus					DisplayString,
				ommp401LineOduTcm5FarEndBackgroundBlockErrorRatio					DisplayString,
				ommp401LineOduTcm5FarEndSevereErrorSecondsErrorRatio					DisplayString,
				ommp401LineOduTcm6ErrorFreeSeconds					DisplayString,
				ommp401LineOduTcm6ErrorSeconds					DisplayString,
				ommp401LineOduTcm6BackgroundBlockErrors					DisplayString,
				ommp401LineOduTcm6SevereErrorSeconds					DisplayString,
				ommp401LineOduTcm6UnavailableSeconds					DisplayString,
				ommp401LineOduTcm6ErrorFreePeriod					DisplayString,
				ommp401LineOduTcm6ErroredPeriod					DisplayString,
				ommp401LineOduTcm6ConsecutiveSevereErrorSecond					DisplayString,
				ommp401LineOduTcm6NonConsecutiveSevereErrorSecond					DisplayString,
				ommp401LineOduTcm6PathAvailabilityStatus					DisplayString,
				ommp401LineOduTcm6BackgroundBlockErrorRatio					DisplayString,
				ommp401LineOduTcm6SevereErrorSecondsErrorRatio					DisplayString,
				ommp401LineOduTcm6FarEndErrorFreeSeconds					DisplayString,
				ommp401LineOduTcm6FarEndErrorSeconds					DisplayString,
				ommp401LineOduTcm6FarEndBackgroundBlockErrors					DisplayString,
				ommp401LineOduTcm6FarEndSevereErrorSeconds					DisplayString,
				ommp401LineOduTcm6FarEndUnavailableSeconds					DisplayString,
				ommp401LineOduTcm6FarEndErrorFreePeriod					DisplayString,
				ommp401LineOduTcm6FarEndErroredPeriod					DisplayString,
				ommp401LineOduTcm6FarEndConsecutiveSevereErrorSecond					DisplayString,
				ommp401LineOduTcm6FarEndNonConsecutiveSevereErrorSecond					DisplayString,
				ommp401LineOduTcm6FarEndPathAvailabilityStatus					DisplayString,
				ommp401LineOduTcm6FarEndBackgroundBlockErrorRatio					DisplayString,
				ommp401LineOduTcm6FarEndSevereErrorSecondsErrorRatio					DisplayString,
				ommp401PerformanceTableRowStatus					RowStatus
			}	           

	ommp401Cfp2InputPower OBJECT-TYPE
		SYNTAX  DisplayString
		MAX-ACCESS  read-only
		STATUS  current
		DESCRIPTION
			"Gives the current Input power(dbm) received at the port
			-----------------------------
			ommp401InterfaceNumber:
			5 - LINE-1
			-----------------------------
			Values:
			eg: -9.0
			-----------------------------"
	::= { ommp401PerformanceEntry 1 }

	ommp401Cfp2OutputPower OBJECT-TYPE
		SYNTAX  DisplayString
		MAX-ACCESS  read-only
		STATUS  current
		DESCRIPTION
			"Gives the current Output power(dbm) transmitted at the port
			-----------------------------
			ommp401InterfaceNumber:
			5 - LINE-1
			-----------------------------
			Values:
			eg: -0.6
			-----------------------------"
	::= { ommp401PerformanceEntry 2 }

	ommp401Cfp2SupplyVoltage OBJECT-TYPE
		SYNTAX  DisplayString
		MAX-ACCESS  read-only
		STATUS  current
		DESCRIPTION
			"Gives the Supply Voltage of the port
			-----------------------------
			ommp401InterfaceNumber:
			5 - LINE-1
			-----------------------------
			Values:
			eg: 3.3
			-----------------------------"
	::= { ommp401PerformanceEntry 3 }

	ommp401Cfp2Temperature OBJECT-TYPE
		SYNTAX  DisplayString
		MAX-ACCESS  read-only
		STATUS  current
		DESCRIPTION
			"Gives the temperature(degree celcius) of the transmitter
			at  the port
			-----------------------------
			ommp401InterfaceNumber:
			5 - LINE-1
			-----------------------------
			Values:
			eg: 33.35
			-----------------------------"
	::= { ommp401PerformanceEntry 4 }

	ommp401Qsfp28InputPower OBJECT-TYPE
		SYNTAX  DisplayString
		MAX-ACCESS  read-only
		STATUS  current
		DESCRIPTION
			"Gives the current Input power(dbm) received at the port
			-----------------------------
			ommp401InterfaceNumber:
			1 to 4 - CLIENT-1 to CLIENT-4
			-----------------------------
			Values:
			eg: -9.0
			-----------------------------"
	::= { ommp401PerformanceEntry 5 }

	ommp401Qsfp28OutputPower OBJECT-TYPE
		SYNTAX  DisplayString
		MAX-ACCESS  read-only
		STATUS  current
		DESCRIPTION
			"Gives the current Output power(dbm) transmitted at the port
			-----------------------------
			ommp401InterfaceNumber:
			1 to 4 - CLIENT-1 to CLIENT-4
			-----------------------------
			Values:
			eg: -6.0
			-----------------------------"
	::= { ommp401PerformanceEntry 6 }

	ommp401Qsfp28BiasCurrent OBJECT-TYPE
		SYNTAX  DisplayString
		MAX-ACCESS  read-only
		STATUS  current
		DESCRIPTION
			"Gives the bias current(mA) thats transmitted at the port
			-----------------------------
			ommp401InterfaceNumber:
			1 to 4 - CLIENT-1 to CLIENT-4
			-----------------------------
			Values:
			eg: 55
			-----------------------------"
	::= { ommp401PerformanceEntry 7 }

	ommp401Qsfp28SupplyVoltage OBJECT-TYPE
		SYNTAX  DisplayString
		MAX-ACCESS  read-only
		STATUS  current
		DESCRIPTION
			"Gives the Supply Voltage of the port
			-----------------------------
			ommp401InterfaceNumber:
			1 to 4 - CLIENT-1 to CLIENT-4
			-----------------------------
			Values:
			eg: 3.3
			-----------------------------"
	::= { ommp401PerformanceEntry 8 }

	ommp401Qsfp28Temperature OBJECT-TYPE
		SYNTAX  DisplayString
		MAX-ACCESS  read-only
		STATUS  current
		DESCRIPTION
			"Gives the temperature(degree celcius) of the transmitter
			at the port
			-----------------------------
			ommp401InterfaceNumber:
			1 to 4 - CLIENT-1 to CLIENT-4
			-----------------------------
			Values:
			eg: 33.35
			-----------------------------"
	::= { ommp401PerformanceEntry 9 }

	ommp401OtnFecUncorrectedWords OBJECT-TYPE
		SYNTAX  DisplayString
		MAX-ACCESS  read-only
		STATUS  current
		DESCRIPTION
			"For port configured with OTU4/OTUC4 traffic,
			OTU Uncorrected Word Error Counter counts the number of
			FEC errored code words that could not be corrected.
			-----------------------------
			ommp401InterfaceNumber:
			1 to 4 - CLIENT-1 to CLIENT-4
			-----------------------------
			Values:
			eg: 1234
			-----------------------------"
	::= { ommp401PerformanceEntry 10 }

	ommp401OtnFecCorrectedBits OBJECT-TYPE
		SYNTAX  DisplayString
		MAX-ACCESS  read-only
		STATUS  current
		DESCRIPTION
			"For port configured with OTU4/OTUC4 traffic,
			OTU Corrected Bit Error Counter counts the number of
			FEC error bits that could be corrected(sum of ones
			corrected and zeros corrected bits).
			-----------------------------
			ommp401InterfaceNumber:
			1 to 4 - CLIENT-1 to CLIENT-4
			-----------------------------
			Values:
			eg: 1234
			-----------------------------"
	::= { ommp401PerformanceEntry 11 }

	ommp401OtnFecZerosCorrectedBits OBJECT-TYPE
		SYNTAX  DisplayString
		MAX-ACCESS  read-only
		STATUS  current
		DESCRIPTION
			"For port configured with OTU4/OTUC4 traffic,
			OTU Zero Corrected Bits Error Counter counts the number
			of FEC error bits that could be corrected from
			one to zero value(Expected 0 but received as 1).
			-----------------------------
			ommp401InterfaceNumber:
			1 to 4 - CLIENT-1 to CLIENT-4
			-----------------------------
			Values:
			eg: 1234
			-----------------------------"
	::= { ommp401PerformanceEntry 12 }

	ommp401OtnFecOnesCorrectedBits OBJECT-TYPE
		SYNTAX  DisplayString
		MAX-ACCESS  read-only
		STATUS  current
		DESCRIPTION
			"For port configured with OTU4/OTUC4 traffic,
			OTU Ones Corrected Byte Error Counter counts the number
			of FEC error bytes that could be corrected from
			zero to one value(Expected 1 but received as 0).
			-----------------------------
			ommp401InterfaceNumber:
			1 to 4 - CLIENT-1 to CLIENT-4
			-----------------------------
			Values:
			eg: 1234
			-----------------------------"
	::= { ommp401PerformanceEntry 13 }

	ommp401OtuBitInterleavedParityErrors OBJECT-TYPE
		SYNTAX  DisplayString
		MAX-ACCESS  read-only
		STATUS  current
		DESCRIPTION
			"For port configured with OTU4/OTUC4 traffic,
			OTU-BIP Counter counts the Parity errors evaluated by
			SM field of an OTU4 frame.
			-----------------------------
			ommp401InterfaceNumber:
			1 to 4 - CLIENT-1 to CLIENT-4
			-----------------------------
			Values:
			eg: 1234
			-----------------------------"
	::= { ommp401PerformanceEntry 14 }

	ommp401OtuIncomingAlignmentErrorSeconds OBJECT-TYPE
		SYNTAX  DisplayString
		MAX-ACCESS  read-only
		STATUS  current
		DESCRIPTION
			"For port configured with OTU4/OTUC4 traffic,
			OTU Incoming Alignment Error Second increases,
			when OTU IAE Alarm is detected in that particular second
			of the incoming OTU signal
			-----------------------------
			ommp401InterfaceNumber:
			1 to 4 - CLIENT-1 to CLIENT-4
			-----------------------------
			Values:
			eg: 1234
			-----------------------------"
	::= { ommp401PerformanceEntry 15 }

	ommp401OtuBackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code.
			-----------------------------
			ommp401InterfaceNumber:
			1 to 4 - CLIENT-1 to CLIENT-4
			-----------------------------
			Values:
			eg: 1234
			-----------------------------"
	::= { ommp401PerformanceEntry 16 }

	ommp401OtuBackwardIncomingAlignmentErrorSeconds OBJECT-TYPE
		SYNTAX  DisplayString
		MAX-ACCESS  read-only
		STATUS  current
		DESCRIPTION
			"For port configured with OTU4/OTUC4 traffic,
			OTU-BIAE Counter increases when SM-BIAE Alarm is 
			detected in that particular second
			of the incoming OTU signal
			-----------------------------
			ommp401InterfaceNumber:
			1 to 4 - CLIENT-1 to CLIENT-4
			-----------------------------
			Values:
			eg: 1234
			-----------------------------"
	::= { ommp401PerformanceEntry 17 }

	ommp401OtuErrorFreeSeconds OBJECT-TYPE
		SYNTAX  DisplayString
		MAX-ACCESS  read-only
		STATUS  current
		DESCRIPTION
			"For port configured with OTU4/OTUC4 traffic,
			OTU Error Free Seconds increases when no BIP errors
			or defects are detected
			-----------------------------
			ommp401InterfaceNumber:
			1 to 4 - CLIENT-1 to CLIENT-4
			-----------------------------
			Values:
			eg: 1234
			-----------------------------"
	::= { ommp401PerformanceEntry 18 }

	ommp401OtuErrorSeconds OBJECT-TYPE
		SYNTAX  DisplayString
		MAX-ACCESS  read-only
		STATUS  current
		DESCRIPTION
			"For port configured with OTU4/OTUC4 traffic,
			OTU Error Seconds increases when any defects like 
			OTU-AIS, SM-TIM etc are detected at the
			section monitoring level
			-----------------------------
			ommp401InterfaceNumber:
			1 to 4 - CLIENT-1 to CLIENT-4
			-----------------------------
			Values:
			eg: 1234
			-----------------------------"
	::= { ommp401PerformanceEntry 19 }

	ommp401OtuBackgroundBlockErrors OBJECT-TYPE
		SYNTAX  DisplayString
		MAX-ACCESS  read-only
		STATUS  current
		DESCRIPTION
			"For port configured with OTU4/OTUC4 traffic,
			OTU Background Block Errors increases on defects 
			detected and when BIP errors are less than 15% errored
			blocks received 
			-----------------------------
			ommp401InterfaceNumber:
			1 to 4 - CLIENT-1 to CLIENT-4
			-----------------------------
			Values:
			eg: 1234
			-----------------------------"
	::= { ommp401PerformanceEntry 20 }

	ommp401OtuSevereErrorSeconds OBJECT-TYPE
		SYNTAX  DisplayString
		MAX-ACCESS  read-only
		STATUS  current
		DESCRIPTION
			"For port configured with OTU4/OTUC4 traffic,
			OTU Severe Error Seconds increases on defects
			detected and when BIP errors are greater than or
			equal to 15% errored blocks received 
			-----------------------------
			ommp401InterfaceNumber:
			1 to 4 - CLIENT-1 to CLIENT-4
			-----------------------------
			Values:
			eg: 1234
			-----------------------------"
	::= { ommp401PerformanceEntry 21 }

	ommp401OtuUnavailableSeconds OBJECT-TYPE
		SYNTAX  DisplayString
		MAX-ACCESS  read-only
		STATUS  current
		DESCRIPTION
			"For port configured with OTU4/OTUC4 traffic,
			OTU Unavailable Seconds increases,
			when 10 consecutive OTU Severe Error seconds
			are detected
			-----------------------------
			ommp401InterfaceNumber:
			1 to 4 - CLIENT-1 to CLIENT-4
			-----------------------------
			Values:
			eg: 1234
			-----------------------------"
	::= { ommp401PerformanceEntry 22 }

	ommp401OtuErrorSecondsErrorRatio OBJECT-TYPE
		SYNTAX  DisplayString
		MAX-ACCESS  read-only
		STATUS  current
		DESCRIPTION
			"For port configured with OTU4/OTUC4 traffic,
			OTU Error Seconds increases when any defects like 
			OTU-AIS, SM-TIM etc are detected at the section monitoring level,
			The ratio of Error seconds in available time to total seconds
			in available time during a fixed measurement interval
			-----------------------------
			ommp401InterfaceNumber:
			1 to 4 - CLIENT-1 to CLIENT-4
			-----------------------------
			Values:
			eg: 1234
			-----------------------------"
	::= { ommp401PerformanceEntry 23 }

	ommp401OtuErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 24 }

	ommp401OtuErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 25 }

	ommp401OtuConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 26 }

	ommp401OtuNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 27 }

	ommp401OtuPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 28 }

	ommp401OtuBackgroundBlockErrorRatio OBJECT-TYPE
		SYNTAX  DisplayString
		MAX-ACCESS  read-only
		STATUS  current
		DESCRIPTION
			"For port configured with OTU4/OTUC4 traffic,
			gives OTU Background Block Error Seconds Error Ratio.
			The ratio of BBE in available time to total seconds
			in available time during a fixed measurement interval.
			-----------------------------
			ommp401InterfaceNumber:
			1 to 4 - CLIENT-1 to CLIENT-4
			-----------------------------
			Values:
			eg: 1e-3
			-----------------------------"
	::= { ommp401PerformanceEntry 29 }

	ommp401OtuSevereErrorSecondsErrorRatio OBJECT-TYPE
		SYNTAX  DisplayString
		MAX-ACCESS  read-only
		STATUS  current
		DESCRIPTION
			"For port configured with OTU4/OTUC4 traffic,
			gives OTU Severe Error Seconds Error Ratio.
			The ratio of SES in available time to total seconds
			in available time during a fixed measurement interval.
			-----------------------------
			ommp401InterfaceNumber:
			1 to 4 - CLIENT-1 to CLIENT-4
			-----------------------------
			Values:
			eg: 1e-3
			-----------------------------"
	::= { ommp401PerformanceEntry 30 }

	ommp401OtuFarEndErrorFreeSeconds OBJECT-TYPE
		SYNTAX  DisplayString
		MAX-ACCESS  read-only
		STATUS  current
		DESCRIPTION
			"For port configured with OTU4/OTUC4 traffic,
			OTU Far end Error Free Seconds, increases when no
			backward errors or defects like BDI or BEI
			are detected in the incoming OTU signal.
			-----------------------------
			ommp401InterfaceNumber:
			1 to 4 - CLIENT-1 to CLIENT-4
			-----------------------------
			Values:
			eg: 1234
			-----------------------------"
	::= { ommp401PerformanceEntry 31 }

	ommp401OtuFarEndBackgroundBlockErrors OBJECT-TYPE
		SYNTAX  DisplayString
		MAX-ACCESS  read-only
		STATUS  current
		DESCRIPTION
			"For port configured with OTU4/OTUC4 traffic,
			OTU Far End Background Block Errors increases when BEI
			errors are less than 15% Errored Blocks in incoming
			OTU signal.
			-----------------------------
			ommp401InterfaceNumber:
			1 to 4 - CLIENT-1 to CLIENT-4
			-----------------------------
			Values:
			eg: 1234
			-----------------------------"
	::= { ommp401PerformanceEntry 32 }

	ommp401OtuFarEndSevereErrorSeconds OBJECT-TYPE
		SYNTAX  DisplayString
		MAX-ACCESS  read-only
		STATUS  current
		DESCRIPTION
			"For port configured with OTU4/OTUC4 traffic,
			OTU Far End Severe Error Seconds increases on defects
			like BDI are detected and when BEI errors are greater
			than or equal to 15% Errored Blocks in incoming OTU 
			signal.
			-----------------------------
			ommp401InterfaceNumber:
			1 to 4 - CLIENT-1 to CLIENT-4
			-----------------------------
			Values:
			eg: 1234
			-----------------------------"
	::= { ommp401PerformanceEntry 33 }

	ommp401OtuFarEndUnavailableSeconds OBJECT-TYPE
		SYNTAX  DisplayString
		MAX-ACCESS  read-only
		STATUS  current
		DESCRIPTION
			"For port configured with OTU4/OTUC4 traffic,
			OTU Far End Unavailable Seconds increases, 
			after 9 consecutive OTU Far End Severe Error
			seconds are detected
			-----------------------------
			ommp401InterfaceNumber:
			1 to 4 - CLIENT-1 to CLIENT-4
			-----------------------------
			Values:
			eg: 1234
			-----------------------------"
	::= { ommp401PerformanceEntry 34 }

	ommp401OtuFarEndErrorSecondsErrorRatio OBJECT-TYPE
		SYNTAX  DisplayString
		MAX-ACCESS  read-only
		STATUS  current
		DESCRIPTION
			"For port configured with OTU4/OTUC4 traffic,
			gives Otu Far End Error seconds Error Ratio.
			The ratio of Far End ES in available time to total
			seconds in available time during a fixed measurement
			interval.
			-----------------------------
			ommp401InterfaceNumber:
			1 to 4 - CLIENT-1 to CLIENT-4
			-----------------------------
			Values:
			eg: 1e-3
			-----------------------------"
	::= { ommp401PerformanceEntry 35 }

	ommp401OtuFarEndErrorSeconds OBJECT-TYPE
		SYNTAX  DisplayString
		MAX-ACCESS  read-only
		STATUS  current
		DESCRIPTION
			"For port configured with OTU4/OTUC4 traffic,
			OTU Far End Error Seconds increases on
			detection of defects like BDI in incoming
			OTU signal.
			-----------------------------
			ommp401InterfaceNumber:
			1 to 4 - CLIENT-1 to CLIENT-4
			-----------------------------
			Values:
			eg: 1234
			-----------------------------"
	::= { ommp401PerformanceEntry 36 }

	ommp401OtuFarEndBackgroundBlockErrorRatio OBJECT-TYPE
		SYNTAX  DisplayString
		MAX-ACCESS  read-only
		STATUS  current
		DESCRIPTION
			"For port configured with OTU4/OTUC4 traffic,
			gives Otu Far End Background Block Error Ratio.
			The ratio of Far End BBE in available time to total
			seconds in available time during a fixed measurement
			interval.
			-----------------------------
			ommp401InterfaceNumber:
			1 to 4 - CLIENT-1 to CLIENT-4
			-----------------------------
			Values:
			eg: 1e-3
			-----------------------------"
	::= { ommp401PerformanceEntry 37 }

	ommp401OtuFarEndSevereErrorSecondsErrorRatio OBJECT-TYPE
		SYNTAX  DisplayString
		MAX-ACCESS  read-only
		STATUS  current
		DESCRIPTION
			"For port configured with OTU4/OTUC4 traffic,
			gives Otu Far End Severe Error Seconds Error Ratio.
			The ratio of Far End SES in available time to total seconds
			in available time during a fixed measurement interval.
			-----------------------------
			ommp401InterfaceNumber:
			1 to 4 - CLIENT-1 to CLIENT-4
			-----------------------------
			Values:
			eg: 1e-3
			-----------------------------"
	::= { ommp401PerformanceEntry 38 }

	ommp401OtuErrorRatio   OBJECT-TYPE
              SYNTAX  DisplayString
              MAX-ACCESS  read-only
              STATUS  current
              DESCRIPTION
			"For port configured with OTU4/OTUC4 traffic,
			gives the OTU Error Ratio for requested port. The ratio  
			of number of error bits to the number of bits received in
			a particular second
			-----------------------------
			ommp401InterfaceNumber:
			1 to 4 - CLIENT-1 to CLIENT-4
			-----------------------------	
			Value:
			eg: 4.0
			-----------------------------"
	::= { ommp401PerformanceEntry 39 } 

	ommp401OtuFarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 40 }

	ommp401OtuFarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 41 }

	ommp401OtuFarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 42 }

	ommp401OtuFarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 43 }

	ommp401OtuFarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 44 }

	ommp401OtuFramesReceived  OBJECT-TYPE
              SYNTAX  DisplayString
              MAX-ACCESS  read-only
              STATUS  current
              DESCRIPTION
			"For port configured with OTU4/OTUC4 traffic, gives the 
			gives the number of OTU frames transmitted.
			-----------------------------
			ommp401InterfaceNumber:
			1 to 4 - CLIENT-1 to CLIENT-4
			-----------------------------	
			Value:
			eg: 4.0
			-----------------------------"
	::= { ommp401PerformanceEntry 45 }

	ommp401OtuBitErrorRate  OBJECT-TYPE
              SYNTAX  DisplayString
              MAX-ACCESS  read-only
              STATUS  current
              DESCRIPTION
			"For port configured with OTU4/OTUC4 traffic, gives the 
			Bit Error Rate. Bit error rate is the Error ratio 
			multiplied by the OTU4 standard signal 
			data-rate( 10.709225316 Gbps )
			-----------------------------
			ommp401InterfaceNumber:
			1 to 4 - CLIENT-1 to CLIENT-4
			-----------------------------	
			Value:
			eg: 4.0
			-----------------------------"
	::= { ommp401PerformanceEntry 46 }

	ommp401OduBitInterleavedParityErrors OBJECT-TYPE
		SYNTAX  DisplayString
		MAX-ACCESS  read-only
		STATUS  current
		DESCRIPTION
			"For port configured with OTU4/OTUC4 traffic,
			ODU-BIP Counter counts the Parity errors evaluated by
			PM field of an OTU4 frame
			-----------------------------
			ommp401InterfaceNumber:
			1 to 4 - CLIENT-1 to CLIENT-4
			-----------------------------
			Values:
			eg: 1234
			-----------------------------"
	::= { ommp401PerformanceEntry 47 }

	ommp401OduTcm1BitInterleavedParityErrors OBJECT-TYPE
		SYNTAX  DisplayString
		MAX-ACCESS  read-only
		STATUS  current
		DESCRIPTION
			"For port configured with OTU4/OTUC4 traffic,
			TCM1-BIP Counter counts the Parity errors evaluated by
			TCM1 field in ODU frame
			-----------------------------
			ommp401InterfaceNumber:
			1 to 4 - CLIENT-1 to CLIENT-4
			-----------------------------
			Values:
			eg: 1234
			-----------------------------"
	::= { ommp401PerformanceEntry 48 }

	ommp401OduTcm2BitInterleavedParityErrors OBJECT-TYPE
		SYNTAX  DisplayString
		MAX-ACCESS  read-only
		STATUS  current
		DESCRIPTION
			"For port configured with OTU4/OTUC4 traffic,
			TCM2-BIP Counter counts the Parity errors evaluated by
			TCM2 field in ODU frame
			-----------------------------
			ommp401InterfaceNumber:
			1 to 4 - CLIENT-1 to CLIENT-4
			-----------------------------
			Values:
			eg: 1234
			-----------------------------"
	::= { ommp401PerformanceEntry 49 }

	ommp401OduTcm3BitInterleavedParityErrors OBJECT-TYPE
		SYNTAX  DisplayString
		MAX-ACCESS  read-only
		STATUS  current
		DESCRIPTION
			"For port configured with OTU4/OTUC4 traffic,
			TCM3-BIP Counter counts the Parity errors evaluated by
			TCM3 field in ODU frame
			-----------------------------
			ommp401InterfaceNumber:
			1 to 4 - CLIENT-1 to CLIENT-4
			-----------------------------
			Values:
			eg: 1234
			-----------------------------"
	::= { ommp401PerformanceEntry 50 }

	ommp401OduTcm4BitInterleavedParityErrors OBJECT-TYPE
		SYNTAX  DisplayString
		MAX-ACCESS  read-only
		STATUS  current
		DESCRIPTION
			"For port configured with OTU4/OTUC4 traffic,
			TCM4-BIP Counter counts the Parity errors evaluated by
			TCM4 field in ODU frame
			-----------------------------
			ommp401InterfaceNumber:
			1 to 4 - CLIENT-1 to CLIENT-4
			-----------------------------
			Values:
			eg: 1234
			-----------------------------"
	::= { ommp401PerformanceEntry 51 }

	ommp401OduTcm5BitInterleavedParityErrors OBJECT-TYPE
		SYNTAX  DisplayString
		MAX-ACCESS  read-only
		STATUS  current
		DESCRIPTION
			"For port configured with OTU4/OTUC4 traffic,
			TCM5-BIP Counter counts the Parity errors evaluated by
			TCM5 field in ODU frame
			-----------------------------
			ommp401InterfaceNumber:
			1 to 4 - CLIENT-1 to CLIENT-4
			-----------------------------
			Values:
			eg: 1234
			-----------------------------"
	::= { ommp401PerformanceEntry 52 }

	ommp401OduTcm6BitInterleavedParityErrors OBJECT-TYPE
		SYNTAX  DisplayString
		MAX-ACCESS  read-only
		STATUS  current
		DESCRIPTION
			"For port configured with OTU4/OTUC4 traffic,
			TCM6-BIP Counter counts the Parity errors evaluated by
			TCM6 field in ODU frame
			-----------------------------
			ommp401InterfaceNumber:
			1 to 4 - CLIENT-1 to CLIENT-4
			-----------------------------
			Values:
			eg: 1234
			-----------------------------"
	::= { ommp401PerformanceEntry 53 }

	ommp401OduTcm1IncomingAlignmentErrorSeconds OBJECT-TYPE
		SYNTAX  DisplayString
		MAX-ACCESS  read-only
		STATUS  current
		DESCRIPTION
			"For port configured with OTU4/OTUC4 traffic,
			ODU Incoming Alignment Error Count increases,
			when ODU-TCM1-IAE is detected in that particular second
			of the incoming OTU signal
			-----------------------------
			ommp401InterfaceNumber:
			1 to 4 - CLIENT-1 to CLIENT-4
			-----------------------------
			Values:
			eg: 1234
			-----------------------------"
	::= { ommp401PerformanceEntry 54 }

	ommp401OduBackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code.
			-----------------------------
			ommp401InterfaceNumber:
			1 to 4 - CLIENT-1 to CLIENT-4
			-----------------------------
			Values:
			eg: 1234
			-----------------------------"
	::= { ommp401PerformanceEntry 55 }

	ommp401OduTcm1BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM1 level.
			-----------------------------
			ommp401InterfaceNumber:
			1 to 4 - CLIENT-1 to CLIENT-4
			-----------------------------
			Values:
			eg: 1234
			-----------------------------"
	::= { ommp401PerformanceEntry 56 }

	ommp401OduTcm2BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM2 level.
			-----------------------------
			ommp401InterfaceNumber:
			1 to 4 - CLIENT-1 to CLIENT-4
			-----------------------------
			Values:
			eg: 1234
			-----------------------------"
	::= { ommp401PerformanceEntry 57 }

	ommp401OduTcm3BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM3 level.
			-----------------------------
			ommp401InterfaceNumber:
			1 to 4 - CLIENT-1 to CLIENT-4
			-----------------------------
			Values:
			eg: 1234
			-----------------------------"
	::= { ommp401PerformanceEntry 58 }

	ommp401OduTcm4BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM4 level.
			-----------------------------
			ommp401InterfaceNumber:
			1 to 4 - CLIENT-1 to CLIENT-4
			-----------------------------
			Values:
			eg: 1234
			-----------------------------"
	::= { ommp401PerformanceEntry 59 }

	ommp401OduTcm5BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM5 level.
			-----------------------------
			ommp401InterfaceNumber:
			1 to 4 - CLIENT-1 to CLIENT-4
			-----------------------------
			Values:
			eg: 1234
			-----------------------------"
	::= { ommp401PerformanceEntry 60 }

	ommp401OduTcm6BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM6 level.
			-----------------------------
			ommp401InterfaceNumber:
			1 to 4 - CLIENT-1 to CLIENT-4
			-----------------------------
			Values:
			eg: 1234
			-----------------------------"
	::= { ommp401PerformanceEntry 61 }

	ommp401OduTcm1BackwardIncomingAlignmentErrorSeconds OBJECT-TYPE
		SYNTAX  DisplayString
		MAX-ACCESS  read-only
		STATUS  current
		DESCRIPTION
			"For port configured with OTU4/OTUC4 traffic,
			ODU Backward Incoming Alignment Error Count increases,
			when ODU-TCM1-BIAE is detected in that particular second
			of the incoming OTU signal
			-----------------------------
			ommp401InterfaceNumber:
			1 to 4 - CLIENT-1 to CLIENT-4
			-----------------------------
			Values:
			eg: 1234
			-----------------------------"
	::= { ommp401PerformanceEntry 62 }

	ommp401OduDelayMeasurement OBJECT-TYPE
		SYNTAX  DisplayString
		MAX-ACCESS  read-only
		STATUS  current
		DESCRIPTION
			"For port configured with OTU4/OTUC4 traffic,
			gives delay measurement of ODU frame
			-----------------------------
			ommp401InterfaceNumber:
			1 to 4 - CLIENT-1 to CLIENT-4
			-----------------------------
			Values:
			eg: Reserved for further study
			-----------------------------"
	::= { ommp401PerformanceEntry 63 }

	ommp401OduErrorFreeSeconds OBJECT-TYPE
		SYNTAX  DisplayString
		MAX-ACCESS  read-only
		STATUS  current
		DESCRIPTION
			"For port configured with OTU4/OTUC4 traffic,
			ODU Error Free Seconds increases,
			when no BIP errors or defects are detected at the
			path monitoring level
			-----------------------------
			ommp401InterfaceNumber:
			1 to 4 - CLIENT-1 to CLIENT-4
			-----------------------------
			Values:
			eg: 1234
			-----------------------------"
	::= { ommp401PerformanceEntry 64 }

	ommp401OduErrorSeconds OBJECT-TYPE
		SYNTAX  DisplayString
		MAX-ACCESS  read-only
		STATUS  current
		DESCRIPTION
			"For port configured with OTU4/OTUC4 traffic,
			ODU Error Seconds increases on defects detected at the
			path monitoring level
			-----------------------------
			ommp401InterfaceNumber:
			1 to 4 - CLIENT-1 to CLIENT-4
			-----------------------------
			Values:
			eg: 1234
			-----------------------------"
	::= { ommp401PerformanceEntry 65 }

	ommp401OduBackgroundBlockErrors OBJECT-TYPE
		SYNTAX  DisplayString
		MAX-ACCESS  read-only
		STATUS  current
		DESCRIPTION
			"For port configured with OTU4/OTUC4 traffic,
			ODU Background Block Errors increases on defects 
			detected and when BIP errors are less than 15% 
			Errored Blocks in incoming OTU signal.
			-----------------------------
			ommp401InterfaceNumber:
			1 to 4 - CLIENT-1 to CLIENT-4
			-----------------------------
			Values:
			eg: 1234
			-----------------------------"
	::= { ommp401PerformanceEntry 66 }

	ommp401OduSevereErrorSeconds OBJECT-TYPE
		SYNTAX  DisplayString
		MAX-ACCESS  read-only
		STATUS  current
		DESCRIPTION
			"For port configured with OTU4/OTUC4 traffic,
			ODU Severe Error Seconds increases on defects detected
			and when BIP errors are more than 15% Errored Blocks
			in incoming OTU signal.
			-----------------------------
			ommp401InterfaceNumber:
			1 to 4 - CLIENT-1 to CLIENT-4
			-----------------------------
			Values:
			eg: 1234
			-----------------------------"
	::= { ommp401PerformanceEntry 67 }

	ommp401OduUnavailableSeconds OBJECT-TYPE
		SYNTAX  DisplayString
		MAX-ACCESS  read-only
		STATUS  current
		DESCRIPTION
			"For port configured with OTU4/OTUC4 traffic,
			ODU Unavailable Seconds increases, when 10 consecutive
			Severe ODU Error seconds are detected
			-----------------------------
			ommp401InterfaceNumber:
			1 to 4 - CLIENT-1 to CLIENT-4
			-----------------------------
			Values:
			eg: 1234
			-----------------------------"
	::= { ommp401PerformanceEntry 68 }

	ommp401OduErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 69 }

	ommp401OduErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 70 }

	ommp401OduConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 71 }

	ommp401OduNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 72 }

	ommp401OduPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 73 }

	ommp401OduFarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 74 }

	ommp401OduFarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 75 }

	ommp401OduFarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 76 }

	ommp401OduFarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 77 }

	ommp401OduFarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 78 }

	ommp401OduFramesReceived OBJECT-TYPE
		SYNTAX  DisplayString
		MAX-ACCESS  read-only
		STATUS  current
		DESCRIPTION
			"For port configured with OTU4/OTUC4 traffic,
			The number of frames received in ODU layer
			-----------------------------
			ommp401InterfaceNumber:
			1 to 4 - CLIENT-1 to CLIENT-4
			-----------------------------
			Values:
			eg: 1234
			-----------------------------"
	::= { ommp401PerformanceEntry 79 }

	ommp401OduErrorSecondsErrorRatio OBJECT-TYPE
		SYNTAX  DisplayString
		MAX-ACCESS  read-only
		STATUS  current
		DESCRIPTION
			"For port configured with OTU4/OTUC4 traffic,
			OTU Error Seconds increases when any defects like 
			OTU-AIS, SM-TIM etc are detected at the section monitoring level,
			The ratio of Error seconds in available time to total seconds
			in available time during a fixed measurement interval
			-----------------------------
			ommp401InterfaceNumber:
			1 to 4 - CLIENT-1 to CLIENT-4
			-----------------------------
			Values:
			eg: 1234
			-----------------------------"
	::= { ommp401PerformanceEntry 80 }

	ommp401OduBackgroundBlockErrorRatio OBJECT-TYPE
		SYNTAX  DisplayString
		MAX-ACCESS  read-only
		STATUS  current
		DESCRIPTION
			"For port configured with OTU4/OTUC4 traffic,
			gives ODU Background Block Error Ratio i.e.
			the ratio of BBE in available time to total seconds
			in available time during a fixed measurement interval.
			-----------------------------
			ommp401InterfaceNumber:
			1 to 4 - CLIENT-1 to CLIENT-4
			-----------------------------
			Values:
			eg: 1e-3
			-----------------------------"
	::= { ommp401PerformanceEntry 81 }

	ommp401OduSevereErrorSecondsErrorRatio OBJECT-TYPE
		SYNTAX  DisplayString
		MAX-ACCESS  read-only
		STATUS  current
		DESCRIPTION
			"For port configured with OTU4/OTUC4 traffic,
			gives ODU Severe Error Seconds Error Ratio i.e.
			the ratio of SES in available time to total seconds
			in available time during a fixed measurement interval.
			-----------------------------
			ommp401InterfaceNumber:
			1 to 4 - CLIENT-1 to CLIENT-4
			-----------------------------
			Values:
			eg: 1e-3
			-----------------------------"
	::= { ommp401PerformanceEntry 82 }

	ommp401OduFarEndErrorFreeSeconds OBJECT-TYPE
		SYNTAX  DisplayString
		MAX-ACCESS  read-only
		STATUS  current
		DESCRIPTION
			"For port configured with OTU4/OTUC4 traffic,
			ODU Far end Error Free Seconds, increases when no
			far end errors or defects are detected
			-----------------------------
			ommp401InterfaceNumber:
			1 to 4 - CLIENT-1 to CLIENT-4
			-----------------------------
			Values:
			eg: 1234
			-----------------------------"
	::= { ommp401PerformanceEntry 83 }

	ommp401OduFarEndErrorSeconds OBJECT-TYPE
		SYNTAX  DisplayString
		MAX-ACCESS  read-only
		STATUS  current
		DESCRIPTION
			"For port configured with OTU4/OTUC4 traffic,
			ODU Far End Error Seconds increases on detection of
			defects like BDI and BEI at path monitoring level
			-----------------------------
			ommp401InterfaceNumber:
			1 to 4 - CLIENT-1 to CLIENT-4
			-----------------------------
			Values:
			eg: 1234
			-----------------------------"
	::= { ommp401PerformanceEntry 84 }

	ommp401OduFarEndBackgroundBlockErrors OBJECT-TYPE
		SYNTAX  DisplayString
		MAX-ACCESS  read-only
		STATUS  current
		DESCRIPTION
			"For port configured with OTU4/OTUC4 traffic,
			ODU Far End Background Block Errors increases when
			BEI errors are less than 15% Errored Blocks in
			incoming OTU signal.
			-----------------------------
			ommp401InterfaceNumber:
			1 to 4 - CLIENT-1 to CLIENT-4
			-----------------------------
			Values:
			eg: 1234
			-----------------------------"
	::= { ommp401PerformanceEntry 85 }

	ommp401OduFarEndSevereErrorSeconds OBJECT-TYPE
		SYNTAX  DisplayString
		MAX-ACCESS  read-only
		STATUS  current
		DESCRIPTION
			"For port configured with OTU4/OTUC4 traffic,
			ODU Far End Severe Error Seconds increases on defects
			like BDI are detected and when BEI errors are more than
			15% Errored Blocks in incoming OTU signal.
			-----------------------------
			ommp401InterfaceNumber:
			1 to 4 - CLIENT-1 to CLIENT-4
			-----------------------------
			Values:
			eg: 1234
			-----------------------------"
	::= { ommp401PerformanceEntry 86 }

	ommp401OduFarEndUnavailableSeconds OBJECT-TYPE
		SYNTAX  DisplayString
		MAX-ACCESS  read-only
		STATUS  current
		DESCRIPTION
			"For port configured with OTU4/OTUC4 traffic,
			ODU Far End Unavailable Seconds increases, when 10
			consecutive OTU Far End Error seconds are detected
			-----------------------------
			ommp401InterfaceNumber:
			1 to 4 - CLIENT-1 to CLIENT-4
			-----------------------------
			Values:
			eg: 1234
			-----------------------------"
	::= { ommp401PerformanceEntry 87 }

	ommp401OduFarEndErrorSecondsErrorRatio OBJECT-TYPE
		SYNTAX  DisplayString
		MAX-ACCESS  read-only
		STATUS  current
		DESCRIPTION
			"For port configured with OTU4/OTUC4 traffic,
			OTU Error Seconds increases when any defects like 
			OTU-AIS, SM-TIM etc are detected at the section monitoring level,
			The ratio of Error seconds in available time to total seconds
			in available time during a fixed measurement interval
			-----------------------------
			ommp401InterfaceNumber:
			1 to 4 - CLIENT-1 to CLIENT-4
			-----------------------------
			Values:
			eg: 1234
			-----------------------------"
	::= { ommp401PerformanceEntry 88 }

	ommp401OduFarEndBackgroundBlockErrorRatio OBJECT-TYPE
		SYNTAX  DisplayString
		MAX-ACCESS  read-only
		STATUS  current
		DESCRIPTION
			"For port configured with OTU4/OTUC4 traffic,
			gives ODU Far End Background Block Error Ratio i.e.
			the ratio of Far End BBE in available time to total
			seconds	in available time during a fixed measurement
			interval.
			-----------------------------
			ommp401InterfaceNumber:
			1 to 4 - CLIENT-1 to CLIENT-4
			-----------------------------
			Values:
			eg: 1e-3
			-----------------------------"
	::= { ommp401PerformanceEntry 89 }

	ommp401OduFarEndSevereErrorSecondsErrorRatio OBJECT-TYPE
		SYNTAX  DisplayString
		MAX-ACCESS  read-only
		STATUS  current
		DESCRIPTION
			"For port configured with OTU4/OTUC4 traffic,
			gives ODU Far End Severe Error Seconds Error Ratio i.e.
			The ratio of Far End SES in available time to total
			seconds in available time during a fixed measurement
			interval.
			-----------------------------
			ommp401InterfaceNumber:
			1 to 4 - CLIENT-1 to CLIENT-4
			-----------------------------
			Values:
			eg: 1e-3
			-----------------------------"
	::= { ommp401PerformanceEntry 90 }

	ommp401OtnMeasurementPeriod OBJECT-TYPE
		SYNTAX  DisplayString
		MAX-ACCESS  read-only
		STATUS  current
		DESCRIPTION
			"For port configured with OTU4/OTUC4 traffic,
			gives measurement period of OTN frame
			-----------------------------
			ommp401InterfaceNumber:
			1 to 4 - CLIENT-1 to CLIENT-4
			-----------------------------
			Values:
			eg: Reserved for further study
			-----------------------------"
	::= { ommp401PerformanceEntry 91 }

	ommp401OduTcm1ErrorFreeSeconds OBJECT-TYPE
		SYNTAX  DisplayString
		MAX-ACCESS  read-only
		STATUS  current
		DESCRIPTION
			"For port configured with OTU4/OTUC4 traffic,
			TCM1 Error Free Seconds increases,
			when no BIP errors or defects are detected at the
			path monitoring level
			-----------------------------
			ommp401InterfaceNumber:
			1 to 4 - CLIENT-1 to CLIENT-4
			-----------------------------
			Values:
			eg: 1234
			-----------------------------"
	::= { ommp401PerformanceEntry 92 }

	ommp401OduTcm1ErrorSeconds OBJECT-TYPE
		SYNTAX  DisplayString
		MAX-ACCESS  read-only
		STATUS  current
		DESCRIPTION
			"For port configured with OTU4/OTUC4 traffic,
			TCM1 Error Seconds increases on defects detected at the
			path monitoring level
			-----------------------------
			ommp401InterfaceNumber:
			1 to 4 - CLIENT-1 to CLIENT-4
			-----------------------------
			Values:
			eg: 1234
			-----------------------------"
	::= { ommp401PerformanceEntry 93 }

	ommp401OduTcm1BackgroundBlockErrors OBJECT-TYPE
		SYNTAX  DisplayString
		MAX-ACCESS  read-only
		STATUS  current
		DESCRIPTION
			"For port configured with OTU4/OTUC4 traffic,
			TCM1 Background Block Errors increases on defects 
			detected and when BIP errors are less than 15% 
			Errored Blocks in incoming OTU signal.
			-----------------------------
			ommp401InterfaceNumber:
			1 to 4 - CLIENT-1 to CLIENT-4
			-----------------------------
			Values:
			eg: 1234
			-----------------------------"
	::= { ommp401PerformanceEntry 94 }

	ommp401OduTcm1SevereErrorSeconds OBJECT-TYPE
		SYNTAX  DisplayString
		MAX-ACCESS  read-only
		STATUS  current
		DESCRIPTION
			"For port configured with OTU4/OTUC4 traffic,
			TCM1 Severe Error Seconds increases on defects detected
			and when BIP errors are more than 15% Errored Blocks
			in incoming OTU signal.
			-----------------------------
			ommp401InterfaceNumber:
			1 to 4 - CLIENT-1 to CLIENT-4
			-----------------------------
			Values:
			eg: 1234
			-----------------------------"
	::= { ommp401PerformanceEntry 95 }

	ommp401OduTcm1UnavailableSeconds OBJECT-TYPE
		SYNTAX  DisplayString
		MAX-ACCESS  read-only
		STATUS  current
		DESCRIPTION
			"For port configured with OTU4/OTUC4 traffic,
			TCM1 Unavailable Seconds increases, when 10 consecutive
			Severe TCM1 Error seconds are detected
			-----------------------------
			ommp401InterfaceNumber:
			1 to 4 - CLIENT-1 to CLIENT-4
			-----------------------------
			Values:
			eg: 1234
			-----------------------------"
	::= { ommp401PerformanceEntry 96 }

	ommp401OduTcm1ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 97 }

	ommp401OduTcm1ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 98 }

	ommp401OduTcm1ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 99 }

	ommp401OduTcm1NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 100 }

	ommp401OduTcm1PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 101 }

	ommp401OduTcm1BackgroundBlockErrorRatio OBJECT-TYPE
		SYNTAX  DisplayString
		MAX-ACCESS  read-only
		STATUS  current
		DESCRIPTION
			"For port configured with OTU4/OTUC4 traffic,
			gives TCM1 Background Block Error Ratio i.e.
			the ratio of BBE in available time to total seconds
			in available time during a fixed measurement interval.
			-----------------------------
			ommp401InterfaceNumber:
			1 to 4 - CLIENT-1 to CLIENT-4
			-----------------------------
			Values:
			eg: 1e-3
			-----------------------------"
	::= { ommp401PerformanceEntry 102 }

	ommp401OduTcm1SevereErrorSecondsErrorRatio OBJECT-TYPE
		SYNTAX  DisplayString
		MAX-ACCESS  read-only
		STATUS  current
		DESCRIPTION
			"For port configured with OTU4/OTUC4 traffic,
			gives TCM1 Severe Error Seconds Error Ratio i.e.
			the ratio of SES in available time to total seconds
			in available time during a fixed measurement interval.
			-----------------------------
			ommp401InterfaceNumber:
			1 to 4 - CLIENT-1 to CLIENT-4
			-----------------------------
			Values:
			eg: 1e-3
			-----------------------------"
	::= { ommp401PerformanceEntry 103 }

	ommp401OduTcm1FarEndErrorFreeSeconds OBJECT-TYPE
		SYNTAX  DisplayString
		MAX-ACCESS  read-only
		STATUS  current
		DESCRIPTION
			"For port configured with OTU4/OTUC4 traffic,
			TCM1 Far end Error Free Seconds, increases when no
			far end errors or defects are detected
			-----------------------------
			ommp401InterfaceNumber:
			1 to 4 - CLIENT-1 to CLIENT-4
			-----------------------------
			Values:
			eg: 1234
			-----------------------------"
	::= { ommp401PerformanceEntry 104 }

	ommp401OduTcm1FarEndErrorSeconds OBJECT-TYPE
		SYNTAX  DisplayString
		MAX-ACCESS  read-only
		STATUS  current
		DESCRIPTION
			"For port configured with OTU4/OTUC4 traffic,
			TCM1 Far End Error Seconds increases on detection of
			defects like BDI and BEI at path monitoring level
			-----------------------------
			ommp401InterfaceNumber:
			1 to 4 - CLIENT-1 to CLIENT-4
			-----------------------------
			Values:
			eg: 1234
			-----------------------------"
	::= { ommp401PerformanceEntry 105 }

	ommp401OduTcm1FarEndBackgroundBlockErrors OBJECT-TYPE
		SYNTAX  DisplayString
		MAX-ACCESS  read-only
		STATUS  current
		DESCRIPTION
			"For port configured with OTU4/OTUC4 traffic,
			TCM1 Far End Background Block Errors increases when
			BEI errors are less than 15% Errored Blocks in
			incoming OTU signal.
			-----------------------------
			ommp401InterfaceNumber:
			1 to 4 - CLIENT-1 to CLIENT-4
			-----------------------------
			Values:
			eg: 1234
			-----------------------------"
	::= { ommp401PerformanceEntry 106 }

	ommp401OduTcm1FarEndSevereErrorSeconds OBJECT-TYPE
		SYNTAX  DisplayString
		MAX-ACCESS  read-only
		STATUS  current
		DESCRIPTION
			"For port configured with OTU4/OTUC4 traffic,
			TCM1 Far End Severe Error Seconds increases on defects
			like BDI are detected and when BEI errors are more than
			15% Errored Blocks in incoming OTU signal.
			-----------------------------
			ommp401InterfaceNumber:
			1 to 4 - CLIENT-1 to CLIENT-4
			-----------------------------
			Values:
			eg: 1234
			-----------------------------"
	::= { ommp401PerformanceEntry 107 }

	ommp401OduTcm1FarEndUnavailableSeconds OBJECT-TYPE
		SYNTAX  DisplayString
		MAX-ACCESS  read-only
		STATUS  current
		DESCRIPTION
			"For port configured with OTU4/OTUC4 traffic,
			TCM1 Far End Unavailable Seconds increases, when 10
			consecutive OTU Far End Error seconds are detected
			-----------------------------
			ommp401InterfaceNumber:
			1 to 4 - CLIENT-1 to CLIENT-4
			-----------------------------
			Values:
			eg: 1234
			-----------------------------"
	::= { ommp401PerformanceEntry 108 }

	ommp401OduTcm1FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 109 }

	ommp401OduTcm1FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 110 }

	ommp401OduTcm1FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 111 }

	ommp401OduTcm1FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 112 }

	ommp401OduTcm1FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 113 }

	ommp401OduTcm1FarEndBackgroundBlockErrorRatio OBJECT-TYPE
		SYNTAX  DisplayString
		MAX-ACCESS  read-only
		STATUS  current
		DESCRIPTION
			"For port configured with OTU4/OTUC4 traffic,
			gives TCM1 Far End Background Block Error Ratio i.e.
			the ratio of Far End BBE in available time to total
			seconds	in available time during a fixed measurement
			interval.
			-----------------------------
			ommp401InterfaceNumber:
			1 to 4 - CLIENT-1 to CLIENT-4
			-----------------------------
			Values:
			eg: 1e-3
			-----------------------------"
	::= { ommp401PerformanceEntry 114 }

	ommp401OduTcm1FarEndSevereErrorSecondsErrorRatio OBJECT-TYPE
		SYNTAX  DisplayString
		MAX-ACCESS  read-only
		STATUS  current
		DESCRIPTION
			"For port configured with OTU4/OTUC4 traffic,
			gives TCM1 Far End Severe Error Seconds Error Ratio i.e.
			The ratio of Far End SES in available time to total
			seconds in available time during a fixed measurement
			interval.
			-----------------------------
			ommp401InterfaceNumber:
			1 to 4 - CLIENT-1 to CLIENT-4
			-----------------------------
			Values:
			eg: 1e-3
			-----------------------------"
	::= { ommp401PerformanceEntry 115 } 

	ommp401OduTcm2ErrorFreeSeconds OBJECT-TYPE
		SYNTAX  DisplayString
		MAX-ACCESS  read-only
		STATUS  current
		DESCRIPTION
			"For port configured with OTU4/OTUC4 traffic,
			TCM2 Error Free Seconds increases,
			when no BIP errors or defects are detected at the
			path monitoring level
			-----------------------------
			ommp401InterfaceNumber:
			1 to 4 - CLIENT-1 to CLIENT-4
			-----------------------------
			Values:
			eg: 1234
			-----------------------------"
	::= { ommp401PerformanceEntry 116 }

	ommp401OduTcm2ErrorSeconds OBJECT-TYPE
		SYNTAX  DisplayString
		MAX-ACCESS  read-only
		STATUS  current
		DESCRIPTION
			"For port configured with OTU4/OTUC4 traffic,
			TCM2 Error Seconds increases on defects detected at the
			path monitoring level
			-----------------------------
			ommp401InterfaceNumber:
			1 to 4 - CLIENT-1 to CLIENT-4
			-----------------------------
			Values:
			eg: 1234
			-----------------------------"
	::= { ommp401PerformanceEntry 117 }

	ommp401OduTcm2BackgroundBlockErrors OBJECT-TYPE
		SYNTAX  DisplayString
		MAX-ACCESS  read-only
		STATUS  current
		DESCRIPTION
			"For port configured with OTU4/OTUC4 traffic,
			TCM2 Background Block Errors increases on defects 
			detected and when BIP errors are less than 15% 
			Errored Blocks in incoming OTU signal.
			-----------------------------
			ommp401InterfaceNumber:
			1 to 4 - CLIENT-1 to CLIENT-4
			-----------------------------
			Values:
			eg: 1234
			-----------------------------"
	::= { ommp401PerformanceEntry 118 }

	ommp401OduTcm2SevereErrorSeconds OBJECT-TYPE
		SYNTAX  DisplayString
		MAX-ACCESS  read-only
		STATUS  current
		DESCRIPTION
			"For port configured with OTU4/OTUC4 traffic,
			TCM2 Severe Error Seconds increases on defects detected
			and when BIP errors are more than 15% Errored Blocks
			in incoming OTU signal.
			-----------------------------
			ommp401InterfaceNumber:
			1 to 4 - CLIENT-1 to CLIENT-4
			-----------------------------
			Values:
			eg: 1234
			-----------------------------"
	::= { ommp401PerformanceEntry 119 }

	ommp401OduTcm2UnavailableSeconds OBJECT-TYPE
		SYNTAX  DisplayString
		MAX-ACCESS  read-only
		STATUS  current
		DESCRIPTION
			"For port configured with OTU4/OTUC4 traffic,
			TCM2 Unavailable Seconds increases, when 10 consecutive
			Severe TCM2 Error seconds are detected
			-----------------------------
			ommp401InterfaceNumber:
			1 to 4 - CLIENT-1 to CLIENT-4
			-----------------------------
			Values:
			eg: 1234
			-----------------------------"
	::= { ommp401PerformanceEntry 120 }

	ommp401OduTcm2ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 121 }

	ommp401OduTcm2ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 122 }

	ommp401OduTcm2ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 123 }

	ommp401OduTcm2NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 124 }

	ommp401OduTcm2PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 125 }

	ommp401OduTcm2BackgroundBlockErrorRatio OBJECT-TYPE
		SYNTAX  DisplayString
		MAX-ACCESS  read-only
		STATUS  current
		DESCRIPTION
			"For port configured with OTU4/OTUC4 traffic,
			gives TCM2 Background Block Error Ratio i.e.
			the ratio of BBE in available time to total seconds
			in available time during a fixed measurement interval.
			-----------------------------
			ommp401InterfaceNumber:
			1 to 4 - CLIENT-1 to CLIENT-4
			-----------------------------
			Values:
			eg: 1e-3
			-----------------------------"
	::= { ommp401PerformanceEntry 126 }

	ommp401OduTcm2SevereErrorSecondsErrorRatio OBJECT-TYPE
		SYNTAX  DisplayString
		MAX-ACCESS  read-only
		STATUS  current
		DESCRIPTION
			"For port configured with OTU4/OTUC4 traffic,
			gives TCM2 Severe Error Seconds Error Ratio i.e.
			the ratio of SES in available time to total seconds
			in available time during a fixed measurement interval.
			-----------------------------
			ommp401InterfaceNumber:
			1 to 4 - CLIENT-1 to CLIENT-4
			-----------------------------
			Values:
			eg: 1e-3
			-----------------------------"
	::= { ommp401PerformanceEntry 127 }

	ommp401OduTcm2FarEndErrorFreeSeconds OBJECT-TYPE
		SYNTAX  DisplayString
		MAX-ACCESS  read-only
		STATUS  current
		DESCRIPTION
			"For port configured with OTU4/OTUC4 traffic,
			TCM2 Far end Error Free Seconds, increases when no
			far end errors or defects are detected
			-----------------------------
			ommp401InterfaceNumber:
			1 to 4 - CLIENT-1 to CLIENT-4
			-----------------------------
			Values:
			eg: 1234
			-----------------------------"
	::= { ommp401PerformanceEntry 128 }

	ommp401OduTcm2FarEndErrorSeconds OBJECT-TYPE
		SYNTAX  DisplayString
		MAX-ACCESS  read-only
		STATUS  current
		DESCRIPTION
			"For port configured with OTU4/OTUC4 traffic,
			TCM2 Far End Error Seconds increases on detection of
			defects like BDI and BEI at path monitoring level
			-----------------------------
			ommp401InterfaceNumber:
			1 to 4 - CLIENT-1 to CLIENT-4
			-----------------------------
			Values:
			eg: 1234
			-----------------------------"
	::= { ommp401PerformanceEntry 129 }

	ommp401OduTcm2FarEndBackgroundBlockErrors OBJECT-TYPE
		SYNTAX  DisplayString
		MAX-ACCESS  read-only
		STATUS  current
		DESCRIPTION
			"For port configured with OTU4/OTUC4 traffic,
			TCM2 Far End Background Block Errors increases when
			BEI errors are less than 15% Errored Blocks in
			incoming OTU signal.
			-----------------------------
			ommp401InterfaceNumber:
			1 to 4 - CLIENT-1 to CLIENT-4
			-----------------------------
			Values:
			eg: 1234
			-----------------------------"
	::= { ommp401PerformanceEntry 130 }

	ommp401OduTcm2FarEndSevereErrorSeconds OBJECT-TYPE
		SYNTAX  DisplayString
		MAX-ACCESS  read-only
		STATUS  current
		DESCRIPTION
			"For port configured with OTU4/OTUC4 traffic,
			TCM2 Far End Severe Error Seconds increases on defects
			like BDI are detected and when BEI errors are more than
			15% Errored Blocks in incoming OTU signal.
			-----------------------------
			ommp401InterfaceNumber:
			1 to 4 - CLIENT-1 to CLIENT-4
			-----------------------------
			Values:
			eg: 1234
			-----------------------------"
	::= { ommp401PerformanceEntry 131 }

	ommp401OduTcm2FarEndUnavailableSeconds OBJECT-TYPE
		SYNTAX  DisplayString
		MAX-ACCESS  read-only
		STATUS  current
		DESCRIPTION
			"For port configured with OTU4/OTUC4 traffic,
			TCM2 Far End Unavailable Seconds increases, when 10
			consecutive OTU Far End Error seconds are detected
			-----------------------------
			ommp401InterfaceNumber:
			1 to 4 - CLIENT-1 to CLIENT-4
			-----------------------------
			Values:
			eg: 1234
			-----------------------------"
	::= { ommp401PerformanceEntry 132 }

	ommp401OduTcm2FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 133 }

	ommp401OduTcm2FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 134 }

	ommp401OduTcm2FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 135 }

	ommp401OduTcm2FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 136 }

	ommp401OduTcm2FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 137 }

	ommp401OduTcm2FarEndBackgroundBlockErrorRatio OBJECT-TYPE
		SYNTAX  DisplayString
		MAX-ACCESS  read-only
		STATUS  current
		DESCRIPTION
			"For port configured with OTU4/OTUC4 traffic,
			gives TCM2 Far End Background Block Error Ratio i.e.
			the ratio of Far End BBE in available time to total
			seconds	in available time during a fixed measurement
			interval.
			-----------------------------
			ommp401InterfaceNumber:
			1 to 4 - CLIENT-1 to CLIENT-4
			-----------------------------
			Values:
			eg: 1e-3
			-----------------------------"
	::= { ommp401PerformanceEntry 138 }

	ommp401OduTcm2FarEndSevereErrorSecondsErrorRatio OBJECT-TYPE
		SYNTAX  DisplayString
		MAX-ACCESS  read-only
		STATUS  current
		DESCRIPTION
			"For port configured with OTU4/OTUC4 traffic,
			gives TCM2 Far End Severe Error Seconds Error Ratio i.e.
			The ratio of Far End SES in available time to total
			seconds in available time during a fixed measurement
			interval.
			-----------------------------
			ommp401InterfaceNumber:
			1 to 4 - CLIENT-1 to CLIENT-4
			-----------------------------
			Values:
			eg: 1e-3
			-----------------------------"
	::= { ommp401PerformanceEntry 139 }

	ommp401OduTcm3ErrorFreeSeconds OBJECT-TYPE
		SYNTAX  DisplayString
		MAX-ACCESS  read-only
		STATUS  current
		DESCRIPTION
			"For port configured with OTU4/OTUC4 traffic,
			TCM3 Error Free Seconds increases,
			when no BIP errors or defects are detected at the
			path monitoring level
			-----------------------------
			ommp401InterfaceNumber:
			1 to 4 - CLIENT-1 to CLIENT-4
			-----------------------------
			Values:
			eg: 1234
			-----------------------------"
	::= { ommp401PerformanceEntry 140 }

	ommp401OduTcm3ErrorSeconds OBJECT-TYPE
		SYNTAX  DisplayString
		MAX-ACCESS  read-only
		STATUS  current
		DESCRIPTION
			"For port configured with OTU4/OTUC4 traffic,
			TCM3 Error Seconds increases on defects detected at the
			path monitoring level
			-----------------------------
			ommp401InterfaceNumber:
			1 to 4 - CLIENT-1 to CLIENT-4
			-----------------------------
			Values:
			eg: 1234
			-----------------------------"
	::= { ommp401PerformanceEntry 141 }

	ommp401OduTcm3BackgroundBlockErrors OBJECT-TYPE
		SYNTAX  DisplayString
		MAX-ACCESS  read-only
		STATUS  current
		DESCRIPTION
			"For port configured with OTU4/OTUC4 traffic,
			TCM3 Background Block Errors increases on defects 
			detected and when BIP errors are less than 15% 
			Errored Blocks in incoming OTU signal.
			-----------------------------
			ommp401InterfaceNumber:
			1 to 4 - CLIENT-1 to CLIENT-4
			-----------------------------
			Values:
			eg: 1234
			-----------------------------"
	::= { ommp401PerformanceEntry 142 }

	ommp401OduTcm3SevereErrorSeconds OBJECT-TYPE
		SYNTAX  DisplayString
		MAX-ACCESS  read-only
		STATUS  current
		DESCRIPTION
			"For port configured with OTU4/OTUC4 traffic,
			TCM3 Severe Error Seconds increases on defects detected
			and when BIP errors are more than 15% Errored Blocks
			in incoming OTU signal.
			-----------------------------
			ommp401InterfaceNumber:
			1 to 4 - CLIENT-1 to CLIENT-4
			-----------------------------
			Values:
			eg: 1234
			-----------------------------"
	::= { ommp401PerformanceEntry 143 }

	ommp401OduTcm3UnavailableSeconds OBJECT-TYPE
		SYNTAX  DisplayString
		MAX-ACCESS  read-only
		STATUS  current
		DESCRIPTION
			"For port configured with OTU4/OTUC4 traffic,
			TCM3 Unavailable Seconds increases, when 10 consecutive
			Severe TCM3 Error seconds are detected
			-----------------------------
			ommp401InterfaceNumber:
			1 to 4 - CLIENT-1 to CLIENT-4
			-----------------------------
			Values:
			eg: 1234
			-----------------------------"
	::= { ommp401PerformanceEntry 144 }

	ommp401OduTcm3ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 145 }

	ommp401OduTcm3ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 146 }

	ommp401OduTcm3ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 147 }

	ommp401OduTcm3NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 148 }

	ommp401OduTcm3PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 149 }

	ommp401OduTcm3BackgroundBlockErrorRatio OBJECT-TYPE
		SYNTAX  DisplayString
		MAX-ACCESS  read-only
		STATUS  current
		DESCRIPTION
			"For port configured with OTU4/OTUC4 traffic,
			gives TCM3 Background Block Error Ratio i.e.
			the ratio of BBE in available time to total seconds
			in available time during a fixed measurement interval.
			-----------------------------
			ommp401InterfaceNumber:
			1 to 4 - CLIENT-1 to CLIENT-4
			-----------------------------
			Values:
			eg: 1e-3
			-----------------------------"
	::= { ommp401PerformanceEntry 150 }

	ommp401OduTcm3SevereErrorSecondsErrorRatio OBJECT-TYPE
		SYNTAX  DisplayString
		MAX-ACCESS  read-only
		STATUS  current
		DESCRIPTION
			"For port configured with OTU4/OTUC4 traffic,
			gives TCM3 Severe Error Seconds Error Ratio i.e.
			the ratio of SES in available time to total seconds
			in available time during a fixed measurement interval.
			-----------------------------
			ommp401InterfaceNumber:
			1 to 4 - CLIENT-1 to CLIENT-4
			-----------------------------
			Values:
			eg: 1e-3
			-----------------------------"
	::= { ommp401PerformanceEntry 151 }

	ommp401OduTcm3FarEndErrorFreeSeconds OBJECT-TYPE
		SYNTAX  DisplayString
		MAX-ACCESS  read-only
		STATUS  current
		DESCRIPTION
			"For port configured with OTU4/OTUC4 traffic,
			TCM3 Far end Error Free Seconds, increases when no
			far end errors or defects are detected
			-----------------------------
			ommp401InterfaceNumber:
			1 to 4 - CLIENT-1 to CLIENT-4
			-----------------------------
			Values:
			eg: 1234
			-----------------------------"
	::= { ommp401PerformanceEntry 152 }

	ommp401OduTcm3FarEndErrorSeconds OBJECT-TYPE
		SYNTAX  DisplayString
		MAX-ACCESS  read-only
		STATUS  current
		DESCRIPTION
			"For port configured with OTU4/OTUC4 traffic,
			TCM3 Far End Error Seconds increases on detection of
			defects like BDI and BEI at path monitoring level
			-----------------------------
			ommp401InterfaceNumber:
			1 to 4 - CLIENT-1 to CLIENT-4
			-----------------------------
			Values:
			eg: 1234
			-----------------------------"
	::= { ommp401PerformanceEntry 153 }

	ommp401OduTcm3FarEndBackgroundBlockErrors OBJECT-TYPE
		SYNTAX  DisplayString
		MAX-ACCESS  read-only
		STATUS  current
		DESCRIPTION
			"For port configured with OTU4/OTUC4 traffic,
			TCM3 Far End Background Block Errors increases when
			BEI errors are less than 15% Errored Blocks in
			incoming OTU signal.
			-----------------------------
			ommp401InterfaceNumber:
			1 to 4 - CLIENT-1 to CLIENT-4
			-----------------------------
			Values:
			eg: 1234
			-----------------------------"
	::= { ommp401PerformanceEntry 154 }

	ommp401OduTcm3FarEndSevereErrorSeconds OBJECT-TYPE
		SYNTAX  DisplayString
		MAX-ACCESS  read-only
		STATUS  current
		DESCRIPTION
			"For port configured with OTU4/OTUC4 traffic,
			TCM3 Far End Severe Error Seconds increases on defects
			like BDI are detected and when BEI errors are more than
			15% Errored Blocks in incoming OTU signal.
			-----------------------------
			ommp401InterfaceNumber:
			1 to 4 - CLIENT-1 to CLIENT-4
			-----------------------------
			Values:
			eg: 1234
			-----------------------------"
	::= { ommp401PerformanceEntry 155 }

	ommp401OduTcm3FarEndUnavailableSeconds OBJECT-TYPE
		SYNTAX  DisplayString
		MAX-ACCESS  read-only
		STATUS  current
		DESCRIPTION
			"For port configured with OTU4/OTUC4 traffic,
			TCM3 Far End Unavailable Seconds increases, when 10
			consecutive OTU Far End Error seconds are detected
			-----------------------------
			ommp401InterfaceNumber:
			1 to 4 - CLIENT-1 to CLIENT-4
			-----------------------------
			Values:
			eg: 1234
			-----------------------------"
	::= { ommp401PerformanceEntry 156 }

	ommp401OduTcm3FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 157 }

	ommp401OduTcm3FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 158 }

	ommp401OduTcm3FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 159 }

	ommp401OduTcm3FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 160 }

	ommp401OduTcm3FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 161 }

	ommp401OduTcm3FarEndBackgroundBlockErrorRatio OBJECT-TYPE
		SYNTAX  DisplayString
		MAX-ACCESS  read-only
		STATUS  current
		DESCRIPTION
			"For port configured with OTU4/OTUC4 traffic,
			gives TCM3 Far End Background Block Error Ratio i.e.
			the ratio of Far End BBE in available time to total
			seconds	in available time during a fixed measurement
			interval.
			-----------------------------
			ommp401InterfaceNumber:
			1 to 4 - CLIENT-1 to CLIENT-4
			-----------------------------
			Values:
			eg: 1e-3
			-----------------------------"
	::= { ommp401PerformanceEntry 162 }

	ommp401OduTcm3FarEndSevereErrorSecondsErrorRatio OBJECT-TYPE
		SYNTAX  DisplayString
		MAX-ACCESS  read-only
		STATUS  current
		DESCRIPTION
			"For port configured with OTU4/OTUC4 traffic,
			gives TCM3 Far End Severe Error Seconds Error Ratio i.e.
			The ratio of Far End SES in available time to total
			seconds in available time during a fixed measurement
			interval.
			-----------------------------
			ommp401InterfaceNumber:
			1 to 4 - CLIENT-1 to CLIENT-4
			-----------------------------
			Values:
			eg: 1e-3
			-----------------------------"
	::= { ommp401PerformanceEntry 163 }

	ommp401OduTcm4ErrorFreeSeconds OBJECT-TYPE
		SYNTAX  DisplayString
		MAX-ACCESS  read-only
		STATUS  current
		DESCRIPTION
			"For port configured with OTU4/OTUC4 traffic,
			TCM4 Error Free Seconds increases,
			when no BIP errors or defects are detected at the
			path monitoring level
			-----------------------------
			ommp401InterfaceNumber:
			1 to 4 - CLIENT-1 to CLIENT-4
			-----------------------------
			Values:
			eg: 1234
			-----------------------------"
	::= { ommp401PerformanceEntry 164 }

	ommp401OduTcm4ErrorSeconds OBJECT-TYPE
		SYNTAX  DisplayString
		MAX-ACCESS  read-only
		STATUS  current
		DESCRIPTION
			"For port configured with OTU4/OTUC4 traffic,
			TCM4 Error Seconds increases on defects detected at the
			path monitoring level
			-----------------------------
			ommp401InterfaceNumber:
			1 to 4 - CLIENT-1 to CLIENT-4
			-----------------------------
			Values:
			eg: 1234
			-----------------------------"
	::= { ommp401PerformanceEntry 165 }

	ommp401OduTcm4BackgroundBlockErrors OBJECT-TYPE
		SYNTAX  DisplayString
		MAX-ACCESS  read-only
		STATUS  current
		DESCRIPTION
			"For port configured with OTU4/OTUC4 traffic,
			TCM4 Background Block Errors increases on defects 
			detected and when BIP errors are less than 15% 
			Errored Blocks in incoming OTU signal.
			-----------------------------
			ommp401InterfaceNumber:
			1 to 4 - CLIENT-1 to CLIENT-4
			-----------------------------
			Values:
			eg: 1234
			-----------------------------"
	::= { ommp401PerformanceEntry 166 }

	ommp401OduTcm4SevereErrorSeconds OBJECT-TYPE
		SYNTAX  DisplayString
		MAX-ACCESS  read-only
		STATUS  current
		DESCRIPTION
			"For port configured with OTU4/OTUC4 traffic,
			TCM4 Severe Error Seconds increases on defects detected
			and when BIP errors are more than 15% Errored Blocks
			in incoming OTU signal.
			-----------------------------
			ommp401InterfaceNumber:
			1 to 4 - CLIENT-1 to CLIENT-4
			-----------------------------
			Values:
			eg: 1234
			-----------------------------"
	::= { ommp401PerformanceEntry 167 }

	ommp401OduTcm4UnavailableSeconds OBJECT-TYPE
		SYNTAX  DisplayString
		MAX-ACCESS  read-only
		STATUS  current
		DESCRIPTION
			"For port configured with OTU4/OTUC4 traffic,
			TCM4 Unavailable Seconds increases, when 10 consecutive
			Severe TCM4 Error seconds are detected
			-----------------------------
			ommp401InterfaceNumber:
			1 to 4 - CLIENT-1 to CLIENT-4
			-----------------------------
			Values:
			eg: 1234
			-----------------------------"
	::= { ommp401PerformanceEntry 168 }

	ommp401OduTcm4ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 169 }

	ommp401OduTcm4ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 170 }

	ommp401OduTcm4ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 171 }

	ommp401OduTcm4NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 172 }

	ommp401OduTcm4PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 173 }

	ommp401OduTcm4BackgroundBlockErrorRatio OBJECT-TYPE
		SYNTAX  DisplayString
		MAX-ACCESS  read-only
		STATUS  current
		DESCRIPTION
			"For port configured with OTU4/OTUC4 traffic,
			gives TCM4 Background Block Error Ratio i.e.
			the ratio of BBE in available time to total seconds
			in available time during a fixed measurement interval.
			-----------------------------
			ommp401InterfaceNumber:
			1 to 4 - CLIENT-1 to CLIENT-4
			-----------------------------
			Values:
			eg: 1e-3
			-----------------------------"
	::= { ommp401PerformanceEntry 174 }

	ommp401OduTcm4SevereErrorSecondsErrorRatio OBJECT-TYPE
		SYNTAX  DisplayString
		MAX-ACCESS  read-only
		STATUS  current
		DESCRIPTION
			"For port configured with OTU4/OTUC4 traffic,
			gives TCM4 Severe Error Seconds Error Ratio i.e.
			the ratio of SES in available time to total seconds
			in available time during a fixed measurement interval.
			-----------------------------
			ommp401InterfaceNumber:
			1 to 4 - CLIENT-1 to CLIENT-4
			-----------------------------
			Values:
			eg: 1e-3
			-----------------------------"
	::= { ommp401PerformanceEntry 175 }

	ommp401OduTcm4FarEndErrorFreeSeconds OBJECT-TYPE
		SYNTAX  DisplayString
		MAX-ACCESS  read-only
		STATUS  current
		DESCRIPTION
			"For port configured with OTU4/OTUC4 traffic,
			TCM4 Far end Error Free Seconds, increases when no
			far end errors or defects are detected
			-----------------------------
			ommp401InterfaceNumber:
			1 to 4 - CLIENT-1 to CLIENT-4
			-----------------------------
			Values:
			eg: 1234
			-----------------------------"
	::= { ommp401PerformanceEntry 176 }

	ommp401OduTcm4FarEndErrorSeconds OBJECT-TYPE
		SYNTAX  DisplayString
		MAX-ACCESS  read-only
		STATUS  current
		DESCRIPTION
			"For port configured with OTU4/OTUC4 traffic,
			TCM4 Far End Error Seconds increases on detection of
			defects like BDI and BEI at path monitoring level
			-----------------------------
			ommp401InterfaceNumber:
			1 to 4 - CLIENT-1 to CLIENT-4
			-----------------------------
			Values:
			eg: 1234
			-----------------------------"
	::= { ommp401PerformanceEntry 177 }

	ommp401OduTcm4FarEndBackgroundBlockErrors OBJECT-TYPE
		SYNTAX  DisplayString
		MAX-ACCESS  read-only
		STATUS  current
		DESCRIPTION
			"For port configured with OTU4/OTUC4 traffic,
			TCM4 Far End Background Block Errors increases when
			BEI errors are less than 15% Errored Blocks in
			incoming OTU signal.
			-----------------------------
			ommp401InterfaceNumber:
			1 to 4 - CLIENT-1 to CLIENT-4
			-----------------------------
			Values:
			eg: 1234
			-----------------------------"
	::= { ommp401PerformanceEntry 178 }

	ommp401OduTcm4FarEndSevereErrorSeconds OBJECT-TYPE
		SYNTAX  DisplayString
		MAX-ACCESS  read-only
		STATUS  current
		DESCRIPTION
			"For port configured with OTU4/OTUC4 traffic,
			TCM4 Far End Severe Error Seconds increases on defects
			like BDI are detected and when BEI errors are more than
			15% Errored Blocks in incoming OTU signal.
			-----------------------------
			ommp401InterfaceNumber:
			1 to 4 - CLIENT-1 to CLIENT-4
			-----------------------------
			Values:
			eg: 1234
			-----------------------------"
	::= { ommp401PerformanceEntry 179 }

	ommp401OduTcm4FarEndUnavailableSeconds OBJECT-TYPE
		SYNTAX  DisplayString
		MAX-ACCESS  read-only
		STATUS  current
		DESCRIPTION
			"For port configured with OTU4/OTUC4 traffic,
			TCM4 Far End Unavailable Seconds increases, when 10
			consecutive OTU Far End Error seconds are detected
			-----------------------------
			ommp401InterfaceNumber:
			1 to 4 - CLIENT-1 to CLIENT-4
			-----------------------------
			Values:
			eg: 1234
			-----------------------------"
	::= { ommp401PerformanceEntry 180 }

	ommp401OduTcm4FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 181 }

	ommp401OduTcm4FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 182 }

	ommp401OduTcm4FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 183 }

	ommp401OduTcm4FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 184 }

	ommp401OduTcm4FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 185 }

	ommp401OduTcm4FarEndBackgroundBlockErrorRatio OBJECT-TYPE
		SYNTAX  DisplayString
		MAX-ACCESS  read-only
		STATUS  current
		DESCRIPTION
			"For port configured with OTU4/OTUC4 traffic,
			gives TCM4 Far End Background Block Error Ratio i.e.
			the ratio of Far End BBE in available time to total
			seconds	in available time during a fixed measurement
			interval.
			-----------------------------
			ommp401InterfaceNumber:
			1 to 4 - CLIENT-1 to CLIENT-4
			-----------------------------
			Values:
			eg: 1e-3
			-----------------------------"
	::= { ommp401PerformanceEntry 186 }

	ommp401OduTcm4FarEndSevereErrorSecondsErrorRatio OBJECT-TYPE
		SYNTAX  DisplayString
		MAX-ACCESS  read-only
		STATUS  current
		DESCRIPTION
			"For port configured with OTU4/OTUC4 traffic,
			gives TCM4 Far End Severe Error Seconds Error Ratio i.e.
			The ratio of Far End SES in available time to total
			seconds in available time during a fixed measurement
			interval.
			-----------------------------
			ommp401InterfaceNumber:
			1 to 4 - CLIENT-1 to CLIENT-4
			-----------------------------
			Values:
			eg: 1e-3
			-----------------------------"
	::= { ommp401PerformanceEntry 187 }

	ommp401OduTcm5ErrorFreeSeconds OBJECT-TYPE
		SYNTAX  DisplayString
		MAX-ACCESS  read-only
		STATUS  current
		DESCRIPTION
			"For port configured with OTU4/OTUC4 traffic,
			TCM5 Error Free Seconds increases,
			when no BIP errors or defects are detected at the
			path monitoring level
			-----------------------------
			ommp401InterfaceNumber:
			1 to 4 - CLIENT-1 to CLIENT-4
			-----------------------------
			Values:
			eg: 1234
			-----------------------------"
	::= { ommp401PerformanceEntry 188 }

	ommp401OduTcm5ErrorSeconds OBJECT-TYPE
		SYNTAX  DisplayString
		MAX-ACCESS  read-only
		STATUS  current
		DESCRIPTION
			"For port configured with OTU4/OTUC4 traffic,
			TCM5 Error Seconds increases on defects detected at the
			path monitoring level
			-----------------------------
			ommp401InterfaceNumber:
			1 to 4 - CLIENT-1 to CLIENT-4
			-----------------------------
			Values:
			eg: 1234
			-----------------------------"
	::= { ommp401PerformanceEntry 189 }

	ommp401OduTcm5BackgroundBlockErrors OBJECT-TYPE
		SYNTAX  DisplayString
		MAX-ACCESS  read-only
		STATUS  current
		DESCRIPTION
			"For port configured with OTU4/OTUC4 traffic,
			TCM5 Background Block Errors increases on defects 
			detected and when BIP errors are less than 15% 
			Errored Blocks in incoming OTU signal.
			-----------------------------
			ommp401InterfaceNumber:
			1 to 4 - CLIENT-1 to CLIENT-4
			-----------------------------
			Values:
			eg: 1234
			-----------------------------"
	::= { ommp401PerformanceEntry 190 }

	ommp401OduTcm5SevereErrorSeconds OBJECT-TYPE
		SYNTAX  DisplayString
		MAX-ACCESS  read-only
		STATUS  current
		DESCRIPTION
			"For port configured with OTU4/OTUC4 traffic,
			TCM5 Severe Error Seconds increases on defects detected
			and when BIP errors are more than 15% Errored Blocks
			in incoming OTU signal.
			-----------------------------
			ommp401InterfaceNumber:
			1 to 4 - CLIENT-1 to CLIENT-4
			-----------------------------
			Values:
			eg: 1234
			-----------------------------"
	::= { ommp401PerformanceEntry 191 }

	ommp401OduTcm5UnavailableSeconds OBJECT-TYPE
		SYNTAX  DisplayString
		MAX-ACCESS  read-only
		STATUS  current
		DESCRIPTION
			"For port configured with OTU4/OTUC4 traffic,
			TCM5 Unavailable Seconds increases, when 10 consecutive
			Severe TCM5 Error seconds are detected
			-----------------------------
			ommp401InterfaceNumber:
			1 to 4 - CLIENT-1 to CLIENT-4
			-----------------------------
			Values:
			eg: 1234
			-----------------------------"
	::= { ommp401PerformanceEntry 192 }

	ommp401OduTcm5ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 193 }

	ommp401OduTcm5ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 194 }

	ommp401OduTcm5ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 195 }

	ommp401OduTcm5NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 196 }

	ommp401OduTcm5PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 197 }

	ommp401OduTcm5BackgroundBlockErrorRatio OBJECT-TYPE
		SYNTAX  DisplayString
		MAX-ACCESS  read-only
		STATUS  current
		DESCRIPTION
			"For port configured with OTU4/OTUC4 traffic,
			gives TCM5 Background Block Error Ratio i.e.
			the ratio of BBE in available time to total seconds
			in available time during a fixed measurement interval.
			-----------------------------
			ommp401InterfaceNumber:
			1 to 4 - CLIENT-1 to CLIENT-4
			-----------------------------
			Values:
			eg: 1e-3
			-----------------------------"
	::= { ommp401PerformanceEntry 198 }

	ommp401OduTcm5SevereErrorSecondsErrorRatio OBJECT-TYPE
		SYNTAX  DisplayString
		MAX-ACCESS  read-only
		STATUS  current
		DESCRIPTION
			"For port configured with OTU4/OTUC4 traffic,
			gives TCM5 Severe Error Seconds Error Ratio i.e.
			the ratio of SES in available time to total seconds
			in available time during a fixed measurement interval.
			-----------------------------
			ommp401InterfaceNumber:
			1 to 4 - CLIENT-1 to CLIENT-4
			-----------------------------
			Values:
			eg: 1e-3
			-----------------------------"
	::= { ommp401PerformanceEntry 199 }

	ommp401OduTcm5FarEndErrorFreeSeconds OBJECT-TYPE
		SYNTAX  DisplayString
		MAX-ACCESS  read-only
		STATUS  current
		DESCRIPTION
			"For port configured with OTU4/OTUC4 traffic,
			TCM5 Far end Error Free Seconds, increases when no
			far end errors or defects are detected
			-----------------------------
			ommp401InterfaceNumber:
			1 to 4 - CLIENT-1 to CLIENT-4
			-----------------------------
			Values:
			eg: 1234
			-----------------------------"
	::= { ommp401PerformanceEntry 200 }

	ommp401OduTcm5FarEndErrorSeconds OBJECT-TYPE
		SYNTAX  DisplayString
		MAX-ACCESS  read-only
		STATUS  current
		DESCRIPTION
			"For port configured with OTU4/OTUC4 traffic,
			TCM5 Far End Error Seconds increases on detection of
			defects like BDI and BEI at path monitoring level
			-----------------------------
			ommp401InterfaceNumber:
			1 to 4 - CLIENT-1 to CLIENT-4
			-----------------------------
			Values:
			eg: 1234
			-----------------------------"
	::= { ommp401PerformanceEntry 201 }

	ommp401OduTcm5FarEndBackgroundBlockErrors OBJECT-TYPE
		SYNTAX  DisplayString
		MAX-ACCESS  read-only
		STATUS  current
		DESCRIPTION
			"For port configured with OTU4/OTUC4 traffic,
			TCM5 Far End Background Block Errors increases when
			BEI errors are less than 15% Errored Blocks in
			incoming OTU signal.
			-----------------------------
			ommp401InterfaceNumber:
			1 to 4 - CLIENT-1 to CLIENT-4
			-----------------------------
			Values:
			eg: 1234
			-----------------------------"
	::= { ommp401PerformanceEntry 202 }

	ommp401OduTcm5FarEndSevereErrorSeconds OBJECT-TYPE
		SYNTAX  DisplayString
		MAX-ACCESS  read-only
		STATUS  current
		DESCRIPTION
			"For port configured with OTU4/OTUC4 traffic,
			TCM5 Far End Severe Error Seconds increases on defects
			like BDI are detected and when BEI errors are more than
			15% Errored Blocks in incoming OTU signal.
			-----------------------------
			ommp401InterfaceNumber:
			1 to 4 - CLIENT-1 to CLIENT-4
			-----------------------------
			Values:
			eg: 1234
			-----------------------------"
	::= { ommp401PerformanceEntry 203 }

	ommp401OduTcm5FarEndUnavailableSeconds OBJECT-TYPE
		SYNTAX  DisplayString
		MAX-ACCESS  read-only
		STATUS  current
		DESCRIPTION
			"For port configured with OTU4/OTUC4 traffic,
			TCM5 Far End Unavailable Seconds increases, when 10
			consecutive OTU Far End Error seconds are detected
			-----------------------------
			ommp401InterfaceNumber:
			1 to 4 - CLIENT-1 to CLIENT-4
			-----------------------------
			Values:
			eg: 1234
			-----------------------------"
	::= { ommp401PerformanceEntry 204 }

	ommp401OduTcm5FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 205 }

	ommp401OduTcm5FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 206 }

	ommp401OduTcm5FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 207 }

	ommp401OduTcm5FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 208 }

	ommp401OduTcm5FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 209 }

	ommp401OduTcm5FarEndBackgroundBlockErrorRatio OBJECT-TYPE
		SYNTAX  DisplayString
		MAX-ACCESS  read-only
		STATUS  current
		DESCRIPTION
			"For port configured with OTU4/OTUC4 traffic,
			gives TCM5 Far End Background Block Error Ratio i.e.
			the ratio of Far End BBE in available time to total
			seconds	in available time during a fixed measurement
			interval.
			-----------------------------
			ommp401InterfaceNumber:
			1 to 4 - CLIENT-1 to CLIENT-4
			-----------------------------
			Values:
			eg: 1e-3
			-----------------------------"
	::= { ommp401PerformanceEntry 210 }

	ommp401OduTcm5FarEndSevereErrorSecondsErrorRatio OBJECT-TYPE
		SYNTAX  DisplayString
		MAX-ACCESS  read-only
		STATUS  current
		DESCRIPTION
			"For port configured with OTU4/OTUC4 traffic,
			gives TCM5 Far End Severe Error Seconds Error Ratio i.e.
			The ratio of Far End SES in available time to total
			seconds in available time during a fixed measurement
			interval.
			-----------------------------
			ommp401InterfaceNumber:
			1 to 4 - CLIENT-1 to CLIENT-4
			-----------------------------
			Values:
			eg: 1e-3
			-----------------------------"
	::= { ommp401PerformanceEntry 211 }

	ommp401OduTcm6ErrorFreeSeconds OBJECT-TYPE
		SYNTAX  DisplayString
		MAX-ACCESS  read-only
		STATUS  current
		DESCRIPTION
			"For port configured with OTU4/OTUC4 traffic,
			TCM6 Error Free Seconds increases,
			when no BIP errors or defects are detected at the
			path monitoring level
			-----------------------------
			ommp401InterfaceNumber:
			1 to 4 - CLIENT-1 to CLIENT-4
			-----------------------------
			Values:
			eg: 1234
			-----------------------------"
	::= { ommp401PerformanceEntry 212 }

	ommp401OduTcm6ErrorSeconds OBJECT-TYPE
		SYNTAX  DisplayString
		MAX-ACCESS  read-only
		STATUS  current
		DESCRIPTION
			"For port configured with OTU4/OTUC4 traffic,
			TCM6 Error Seconds increases on defects detected at the
			path monitoring level
			-----------------------------
			ommp401InterfaceNumber:
			1 to 4 - CLIENT-1 to CLIENT-4
			-----------------------------
			Values:
			eg: 1234
			-----------------------------"
	::= { ommp401PerformanceEntry 213 }

	ommp401OduTcm6BackgroundBlockErrors OBJECT-TYPE
		SYNTAX  DisplayString
		MAX-ACCESS  read-only
		STATUS  current
		DESCRIPTION
			"For port configured with OTU4/OTUC4 traffic,
			TCM6 Background Block Errors increases on defects 
			detected and when BIP errors are less than 15% 
			Errored Blocks in incoming OTU signal.
			-----------------------------
			ommp401InterfaceNumber:
			1 to 4 - CLIENT-1 to CLIENT-4
			-----------------------------
			Values:
			eg: 1234
			-----------------------------"
	::= { ommp401PerformanceEntry 214 }

	ommp401OduTcm6SevereErrorSeconds OBJECT-TYPE
		SYNTAX  DisplayString
		MAX-ACCESS  read-only
		STATUS  current
		DESCRIPTION
			"For port configured with OTU4/OTUC4 traffic,
			TCM6 Severe Error Seconds increases on defects detected
			and when BIP errors are more than 15% Errored Blocks
			in incoming OTU signal.
			-----------------------------
			ommp401InterfaceNumber:
			1 to 4 - CLIENT-1 to CLIENT-4
			-----------------------------
			Values:
			eg: 1234
			-----------------------------"
	::= { ommp401PerformanceEntry 215 }

	ommp401OduTcm6UnavailableSeconds OBJECT-TYPE
		SYNTAX  DisplayString
		MAX-ACCESS  read-only
		STATUS  current
		DESCRIPTION
			"For port configured with OTU4/OTUC4 traffic,
			TCM6 Unavailable Seconds increases, when 10 consecutive
			Severe TCM6 Error seconds are detected
			-----------------------------
			ommp401InterfaceNumber:
			1 to 4 - CLIENT-1 to CLIENT-4
			-----------------------------
			Values:
			eg: 1234
			-----------------------------"
	::= { ommp401PerformanceEntry 216 }

	ommp401OduTcm6ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 217 }

	ommp401OduTcm6ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 218 }

	ommp401OduTcm6ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 219 }

	ommp401OduTcm6NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 220 }

	ommp401OduTcm6PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 221 }

	ommp401OduTcm6BackgroundBlockErrorRatio OBJECT-TYPE
		SYNTAX  DisplayString
		MAX-ACCESS  read-only
		STATUS  current
		DESCRIPTION
			"For port configured with OTU4/OTUC4 traffic,
			gives TCM6 Background Block Error Ratio i.e.
			the ratio of BBE in available time to total seconds
			in available time during a fixed measurement interval.
			-----------------------------
			ommp401InterfaceNumber:
			1 to 4 - CLIENT-1 to CLIENT-4
			-----------------------------
			Values:
			eg: 1e-3
			-----------------------------"
	::= { ommp401PerformanceEntry 222 }

	ommp401OduTcm6SevereErrorSecondsErrorRatio OBJECT-TYPE
		SYNTAX  DisplayString
		MAX-ACCESS  read-only
		STATUS  current
		DESCRIPTION
			"For port configured with OTU4/OTUC4 traffic,
			gives TCM6 Severe Error Seconds Error Ratio i.e.
			the ratio of SES in available time to total seconds
			in available time during a fixed measurement interval.
			-----------------------------
			ommp401InterfaceNumber:
			1 to 4 - CLIENT-1 to CLIENT-4
			-----------------------------
			Values:
			eg: 1e-3
			-----------------------------"
	::= { ommp401PerformanceEntry 223 }

	ommp401OduTcm6FarEndErrorFreeSeconds OBJECT-TYPE
		SYNTAX  DisplayString
		MAX-ACCESS  read-only
		STATUS  current
		DESCRIPTION
			"For port configured with OTU4/OTUC4 traffic,
			TCM6 Far end Error Free Seconds, increases when no
			far end errors or defects are detected
			-----------------------------
			ommp401InterfaceNumber:
			1 to 4 - CLIENT-1 to CLIENT-4
			-----------------------------
			Values:
			eg: 1234
			-----------------------------"
	::= { ommp401PerformanceEntry 224 }

	ommp401OduTcm6FarEndErrorSeconds OBJECT-TYPE
		SYNTAX  DisplayString
		MAX-ACCESS  read-only
		STATUS  current
		DESCRIPTION
			"For port configured with OTU4/OTUC4 traffic,
			TCM6 Far End Error Seconds increases on detection of
			defects like BDI and BEI at path monitoring level
			-----------------------------
			ommp401InterfaceNumber:
			1 to 4 - CLIENT-1 to CLIENT-4
			-----------------------------
			Values:
			eg: 1234
			-----------------------------"
	::= { ommp401PerformanceEntry 225 }

	ommp401OduTcm6FarEndBackgroundBlockErrors OBJECT-TYPE
		SYNTAX  DisplayString
		MAX-ACCESS  read-only
		STATUS  current
		DESCRIPTION
			"For port configured with OTU4/OTUC4 traffic,
			TCM6 Far End Background Block Errors increases when
			BEI errors are less than 15% Errored Blocks in
			incoming OTU signal.
			-----------------------------
			ommp401InterfaceNumber:
			1 to 4 - CLIENT-1 to CLIENT-4
			-----------------------------
			Values:
			eg: 1234
			-----------------------------"
	::= { ommp401PerformanceEntry 226 }

	ommp401OduTcm6FarEndSevereErrorSeconds OBJECT-TYPE
		SYNTAX  DisplayString
		MAX-ACCESS  read-only
		STATUS  current
		DESCRIPTION
			"For port configured with OTU4/OTUC4 traffic,
			TCM6 Far End Severe Error Seconds increases on defects
			like BDI are detected and when BEI errors are more than
			15% Errored Blocks in incoming OTU signal.
			-----------------------------
			ommp401InterfaceNumber:
			1 to 4 - CLIENT-1 to CLIENT-4
			-----------------------------
			Values:
			eg: 1234
			-----------------------------"
	::= { ommp401PerformanceEntry 227 }

	ommp401OduTcm6FarEndUnavailableSeconds OBJECT-TYPE
		SYNTAX  DisplayString
		MAX-ACCESS  read-only
		STATUS  current
		DESCRIPTION
			"For port configured with OTU4/OTUC4 traffic,
			TCM6 Far End Unavailable Seconds increases, when 10
			consecutive OTU Far End Error seconds are detected
			-----------------------------
			ommp401InterfaceNumber:
			1 to 4 - CLIENT-1 to CLIENT-4
			-----------------------------
			Values:
			eg: 1234
			-----------------------------"
	::= { ommp401PerformanceEntry 228 }

	ommp401OduTcm6FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401InterfaceNumber:
			1 to 4 - CLIENT-1 to CLIENT-4
			-----------------------------
			Values:
			eg: 1234
			-----------------------------"
	::= { ommp401PerformanceEntry 229 }

	ommp401OduTcm6FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401InterfaceNumber:
			1 to 4 - CLIENT-1 to CLIENT-4
			-----------------------------
			Values:
			eg: 1234
			-----------------------------"
	::= { ommp401PerformanceEntry 230 }

	ommp401OduTcm6FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401InterfaceNumber:
			1 to 4 - CLIENT-1 to CLIENT-4
			-----------------------------
			Values:
			eg: 1234
			-----------------------------"
	::= { ommp401PerformanceEntry 231 }

	ommp401OduTcm6FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401InterfaceNumber:
			1 to 4 - CLIENT-1 to CLIENT-4
			-----------------------------
			Values:
			eg: 1234
			-----------------------------"
	::= { ommp401PerformanceEntry 232 }

	ommp401OduTcm6FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401InterfaceNumber:
			1 to 4 - CLIENT-1 to CLIENT-4
			-----------------------------
			Values:
			eg: 1234
			-----------------------------"
	::= { ommp401PerformanceEntry 233 }

	ommp401OduTcm6FarEndBackgroundBlockErrorRatio OBJECT-TYPE
		SYNTAX  DisplayString
		MAX-ACCESS  read-only
		STATUS  current
		DESCRIPTION
			"For port configured with OTU4/OTUC4 traffic,
			gives TCM6 Far End Background Block Error Ratio i.e.
			the ratio of Far End BBE in available time to total
			seconds	in available time during a fixed measurement
			interval.
			-----------------------------
			ommp401InterfaceNumber:
			1 to 4 - CLIENT-1 to CLIENT-4
			-----------------------------
			Values:
			eg: 1e-3
			-----------------------------"
	::= { ommp401PerformanceEntry 234 }

	ommp401OduTcm6FarEndSevereErrorSecondsErrorRatio OBJECT-TYPE
		SYNTAX  DisplayString
		MAX-ACCESS  read-only
		STATUS  current
		DESCRIPTION
			"For port configured with OTU4/OTUC4 traffic,
			gives TCM6 Far End Severe Error Seconds Error Ratio i.e.
			The ratio of Far End SES in available time to total
			seconds in available time during a fixed measurement
			interval.
			-----------------------------
			ommp401InterfaceNumber:
			1 to 4 - CLIENT-1 to CLIENT-4
			-----------------------------
			Values:
			eg: 1e-3
			-----------------------------"
	::= { ommp401PerformanceEntry 235 }

	ommp401EthernetMacTerminatedFramesTransmitted OBJECT-TYPE
		SYNTAX  DisplayString
		MAX-ACCESS  read-only
		STATUS  current
		DESCRIPTION
			"For port configured with Ethernet traffic,
			gives Tx Good frames count.
			-----------------------------
			ommp401InterfaceNumber:
			1 to 4 - CLIENT-1 to CLIENT-4
			-----------------------------
			Values:
			eg: 1e-3
			-----------------------------"
	::= { ommp401PerformanceEntry 236 }

	ommp401EthernetMacTerminatedFramesReceived OBJECT-TYPE
		SYNTAX  DisplayString
		MAX-ACCESS  read-only
		STATUS  current
		DESCRIPTION
			"For port configured with Ethernet traffic,
			gives Tx Good Octects frames count.
			-----------------------------
			ommp401InterfaceNumber:
			1 to 4 - CLIENT-1 to CLIENT-4
			-----------------------------
			Values:
			eg: 1e-3
			-----------------------------"
	::= { ommp401PerformanceEntry 237 }

	ommp401EthernetMacTerminatedPauseFramesTransmitted OBJECT-TYPE
		SYNTAX  DisplayString
		MAX-ACCESS  read-only
		STATUS  current
		DESCRIPTION
			"For port configured with Ethernet traffic,
			gives Tx Good Multicast frames count.
			-----------------------------
			ommp401InterfaceNumber:
			1 to 4 - CLIENT-1 to CLIENT-4
			-----------------------------
			Values:
			eg: 1e-3
			-----------------------------"
	::= { ommp401PerformanceEntry 238 }

	ommp401EthernetMacTerminatedPauseFramesReceived OBJECT-TYPE
		SYNTAX  DisplayString
		MAX-ACCESS  read-only
		STATUS  current
		DESCRIPTION
			"For port configured with Ethernet traffic,
			gives Tx Good Broadcast frames count.
			-----------------------------
			ommp401InterfaceNumber:
			1 to 4 - CLIENT-1 to CLIENT-4
			-----------------------------
			Values:
			eg: 1e-3
			-----------------------------"
	::= { ommp401PerformanceEntry 239 }

	ommp401EthernetMacTerminatedUnicastFramesTransmitted OBJECT-TYPE
		SYNTAX  DisplayString
		MAX-ACCESS  read-only
		STATUS  current
		DESCRIPTION
			"For port configured with Ethernet traffic,
			gives Tx Good 64B pkt frames count.
			-----------------------------
			ommp401InterfaceNumber:
			1 to 4 - CLIENT-1 to CLIENT-4
			-----------------------------
			Values:
			eg: 1e-3
			-----------------------------"
	::= { ommp401PerformanceEntry 240 }

	ommp401EthernetMacTerminatedUnicastFramesReceived OBJECT-TYPE
		SYNTAX  DisplayString
		MAX-ACCESS  read-only
		STATUS  current
		DESCRIPTION
			"For port configured with Ethernet traffic,
			gives Tx Good 65B to 127Bpkt frames count.
			-----------------------------
			ommp401InterfaceNumber:
			1 to 4 - CLIENT-1 to CLIENT-4
			-----------------------------
			Values:
			eg: 1e-3
			-----------------------------"
	::= { ommp401PerformanceEntry 241 }

	ommp401EthernetMacTerminatedMulticastFramesTransmitted OBJECT-TYPE
		SYNTAX  DisplayString
		MAX-ACCESS  read-only
		STATUS  current
		DESCRIPTION
			"For port configured with Ethernet traffic,
			gives Tx Good 128B to 255Bpkt frames count.
			-----------------------------
			ommp401InterfaceNumber:
			1 to 4 - CLIENT-1 to CLIENT-4
			-----------------------------
			Values:
			eg: 1e-3
			-----------------------------"
	::= { ommp401PerformanceEntry 242 }

	ommp401EthernetMacTerminatedMulticastFramesReceived OBJECT-TYPE
		SYNTAX  DisplayString
		MAX-ACCESS  read-only
		STATUS  current
		DESCRIPTION
			"For port configured with Ethernet traffic,
			gives Tx Good 256B to 511Bpkt frames count.
			-----------------------------
			ommp401InterfaceNumber:
			1 to 4 - CLIENT-1 to CLIENT-4
			-----------------------------
			Values:
			eg: 1e-3
			-----------------------------"
	::= { ommp401PerformanceEntry 243 }

	ommp401EthernetMacTerminatedBroadcastFramesTransmitted OBJECT-TYPE
		SYNTAX  DisplayString
		MAX-ACCESS  read-only
		STATUS  current
		DESCRIPTION
			"For port configured with Ethernet traffic,
			gives Tx Good 512B to 1023Bpkt frames count.
			-----------------------------
			ommp401InterfaceNumber:
			1 to 4 - CLIENT-1 to CLIENT-4
			-----------------------------
			Values:
			eg: 1e-3
			-----------------------------"
	::= { ommp401PerformanceEntry 244 }

	ommp401EthernetMacTerminatedBroadcastFramesReceived OBJECT-TYPE
		SYNTAX  DisplayString
		MAX-ACCESS  read-only
		STATUS  current
		DESCRIPTION
			"For port configured with Ethernet traffic,
			gives Tx Good 1024B to 1518Bpkt frames count.
			-----------------------------
			ommp401InterfaceNumber:
			1 to 4 - CLIENT-1 to CLIENT-4
			-----------------------------
			Values:
			eg: 1e-3
			-----------------------------"
	::= { ommp401PerformanceEntry 245 }

	ommp401EthernetMacTerminatedUnderSizeFramesTransmitted OBJECT-TYPE
		SYNTAX  DisplayString
		MAX-ACCESS  read-only
		STATUS  current
		DESCRIPTION
			"For port configured with Ethernet traffic,
			gives Tx Good 1519BLTJpkt frames count.
			-----------------------------
			ommp401InterfaceNumber:
			1 to 4 - CLIENT-1 to CLIENT-4
			-----------------------------
			Values:
			eg: 1e-3
			-----------------------------"
	::= { ommp401PerformanceEntry 246 }

	ommp401EthernetMacTerminatedUnderSizeFramesReceived OBJECT-TYPE
		SYNTAX  DisplayString
		MAX-ACCESS  read-only
		STATUS  current
		DESCRIPTION
			"For port configured with Ethernet traffic,
			gives Tx Good jumbo frames count.
			-----------------------------
			ommp401InterfaceNumber:
			1 to 4 - CLIENT-1 to CLIENT-4
			-----------------------------
			Values:
			eg: 1e-3
			-----------------------------"
	::= { ommp401PerformanceEntry 247 }

	ommp401EthernetMacTerminatedOverSizeFramesTransmitted OBJECT-TYPE
		SYNTAX  DisplayString
		MAX-ACCESS  read-only
		STATUS  current
		DESCRIPTION
			"For port configured with Ethernet traffic,
			gives Tx Bad frames count.
			-----------------------------
			ommp401InterfaceNumber:
			1 to 4 - CLIENT-1 to CLIENT-4
			-----------------------------
			Values:
			eg: 1e-3
			-----------------------------"
	::= { ommp401PerformanceEntry 248 }

	ommp401EthernetMacTerminatedOverSizeFramesReceived OBJECT-TYPE
		SYNTAX  DisplayString
		MAX-ACCESS  read-only
		STATUS  current
		DESCRIPTION
			"For port configured with Ethernet traffic,
			gives Tx Bad Octects frames count.
			-----------------------------
			ommp401InterfaceNumber:
			1 to 4 - CLIENT-1 to CLIENT-4
			-----------------------------
			Values:
			eg: 1e-3
			-----------------------------"
	::= { ommp401PerformanceEntry 249 }

	ommp401EthernetMacTerminatedFragmentFramesTransmitted OBJECT-TYPE
		SYNTAX  DisplayString
		MAX-ACCESS  read-only
		STATUS  current
		DESCRIPTION
			"For port configured with Ethernet traffic,
			gives Tx Bad Multicast frames count.
			-----------------------------
			ommp401InterfaceNumber:
			1 to 4 - CLIENT-1 to CLIENT-4
			-----------------------------
			Values:
			eg: 1e-3
			-----------------------------"
	::= { ommp401PerformanceEntry 250 }

	ommp401EthernetMacTerminatedFragmentFramesReceived OBJECT-TYPE
		SYNTAX  DisplayString
		MAX-ACCESS  read-only
		STATUS  current
		DESCRIPTION
			"For port configured with Ethernet traffic,
			gives Tx Bad Broadcast frames count.
			-----------------------------
			ommp401InterfaceNumber:
			1 to 4 - CLIENT-1 to CLIENT-4
			-----------------------------
			Values:
			eg: 1e-3
			-----------------------------"
	::= { ommp401PerformanceEntry 251 }

	ommp401EthernetMacTerminatedFrameCheckSequenceErrorsTransmitted OBJECT-TYPE
		SYNTAX  DisplayString
		MAX-ACCESS  read-only
		STATUS  current
		DESCRIPTION
			"For port configured with Ethernet traffic,
			gives Tx Bad 64B pkt frames count.
			-----------------------------
			ommp401InterfaceNumber:
			1 to 4 - CLIENT-1 to CLIENT-4
			-----------------------------
			Values:
			eg: 1e-3
			-----------------------------"
	::= { ommp401PerformanceEntry 252 }

	ommp401EthernetMacTerminatedFrameCheckSequenceErrorsReceived OBJECT-TYPE
		SYNTAX  DisplayString
		MAX-ACCESS  read-only
		STATUS  current
		DESCRIPTION
			"For port configured with Ethernet traffic,
			gives Tx Bad 65B to 127Bpkt frames count.
			-----------------------------
			ommp401InterfaceNumber:
			1 to 4 - CLIENT-1 to CLIENT-4
			-----------------------------
			Values:
			eg: 1e-3
			-----------------------------"
	::= { ommp401PerformanceEntry 253 }

	ommp401EthernetMacTerminatedBytesTransmitted OBJECT-TYPE
		SYNTAX  DisplayString
		MAX-ACCESS  read-only
		STATUS  current
		DESCRIPTION
			"For port configured with Ethernet traffic,
			gives Tx Bad 128B to 255Bpkt frames count.
			-----------------------------
			ommp401InterfaceNumber:
			1 to 4 - CLIENT-1 to CLIENT-4
			-----------------------------
			Values:
			eg: 1e-3
			-----------------------------"
	::= { ommp401PerformanceEntry 254 }

	ommp401EthernetMacTerminatedBytesReceived OBJECT-TYPE
		SYNTAX  DisplayString
		MAX-ACCESS  read-only
		STATUS  current
		DESCRIPTION
			"For port configured with Ethernet traffic,
			gives Tx Bad 256B to 511Bpkt frames count.
			-----------------------------
			ommp401InterfaceNumber:
			1 to 4 - CLIENT-1 to CLIENT-4
			-----------------------------
			Values:
			eg: 1e-3
			-----------------------------"
	::= { ommp401PerformanceEntry 255 }

	ommp401EthernetMacTerminatedJabberFramesTransmitted OBJECT-TYPE
		SYNTAX  DisplayString
		MAX-ACCESS  read-only
		STATUS  current
		DESCRIPTION
			"For port configured with Ethernet traffic,
			gives Tx Bad 512B to 1023Bpkt frames count.
			-----------------------------
			ommp401InterfaceNumber:
			1 to 4 - CLIENT-1 to CLIENT-4
			-----------------------------
			Values:
			eg: 1e-3
			-----------------------------"
	::= { ommp401PerformanceEntry 256 }

	ommp401EthernetMacTerminatedJabberFramesReceived OBJECT-TYPE
		SYNTAX  DisplayString
		MAX-ACCESS  read-only
		STATUS  current
		DESCRIPTION
			"For port configured with Ethernet traffic,
			gives Tx Bad 1024B to 1518Bpkt frames count.
			-----------------------------
			ommp401InterfaceNumber:
			1 to 4 - CLIENT-1 to CLIENT-4
			-----------------------------
			Values:
			eg: 1e-3
			-----------------------------"
	::= { ommp401PerformanceEntry 257 }

	ommp401EthernetMacTerminated64BytesFramesTransmitted OBJECT-TYPE
		SYNTAX  DisplayString
		MAX-ACCESS  read-only
		STATUS  current
		DESCRIPTION
			"For port configured with Ethernet traffic,
			gives Tx Bad 1519BLTJpkt frames count.
			-----------------------------
			ommp401InterfaceNumber:
			1 to 4 - CLIENT-1 to CLIENT-4
			-----------------------------
			Values:
			eg: 1e-3
			-----------------------------"
	::= { ommp401PerformanceEntry 258 }

	ommp401EthernetMacTerminated64BytesFramesReceived OBJECT-TYPE
		SYNTAX  DisplayString
		MAX-ACCESS  read-only
		STATUS  current
		DESCRIPTION
			"For port configured with Ethernet traffic,
			gives Tx bad jumbo frames count.
			-----------------------------
			ommp401InterfaceNumber:
			1 to 4 - CLIENT-1 to CLIENT-4
			-----------------------------
			Values:
			eg: 1e-3
			-----------------------------"
	::= { ommp401PerformanceEntry 259 }

	ommp401EthernetMacTerminated65to127BytesFramesTransmitted OBJECT-TYPE
		SYNTAX  DisplayString
		MAX-ACCESS  read-only
		STATUS  current
		DESCRIPTION
			"For port configured with Ethernet traffic,
			gives Rx Good frames count.
			-----------------------------
			ommp401InterfaceNumber:
			1 to 4 - CLIENT-1 to CLIENT-4
			-----------------------------
			Values:
			eg: 1e-3
			-----------------------------"
	::= { ommp401PerformanceEntry 260 }

	ommp401EthernetMacTerminated65to127BytesFramesReceived OBJECT-TYPE
		SYNTAX  DisplayString
		MAX-ACCESS  read-only
		STATUS  current
		DESCRIPTION
			"For port configured with Ethernet traffic,
			gives Rx Good Octects frames count.
			-----------------------------
			ommp401InterfaceNumber:
			1 to 4 - CLIENT-1 to CLIENT-4
			-----------------------------
			Values:
			eg: 1e-3
			-----------------------------"
	::= { ommp401PerformanceEntry 261 }

	ommp401EthernetMacTerminated128to255BytesFramesTransmitted OBJECT-TYPE
		SYNTAX  DisplayString
		MAX-ACCESS  read-only
		STATUS  current
		DESCRIPTION
			"For port configured with Ethernet traffic,
			gives Rx Good Multicast frames count.
			-----------------------------
			ommp401InterfaceNumber:
			1 to 4 - CLIENT-1 to CLIENT-4
			-----------------------------
			Values:
			eg: 1e-3
			-----------------------------"
	::= { ommp401PerformanceEntry 262 }

	ommp401EthernetMacTerminated128to255BytesFramesReceived OBJECT-TYPE
		SYNTAX  DisplayString
		MAX-ACCESS  read-only
		STATUS  current
		DESCRIPTION
			"For port configured with Ethernet traffic,
			gives Rx Good Broadcast frames count.
			-----------------------------
			ommp401InterfaceNumber:
			1 to 4 - CLIENT-1 to CLIENT-4
			-----------------------------
			Values:
			eg: 1e-3
			-----------------------------"
	::= { ommp401PerformanceEntry 263 }

	ommp401EthernetMacTerminated256to511BytesFramesTransmitted OBJECT-TYPE
		SYNTAX  DisplayString
		MAX-ACCESS  read-only
		STATUS  current
		DESCRIPTION
			"For port configured with Ethernet traffic,
			gives Rx Good 64B pkt frames count.
			-----------------------------
			ommp401InterfaceNumber:
			1 to 4 - CLIENT-1 to CLIENT-4
			-----------------------------
			Values:
			eg: 1e-3
			-----------------------------"
	::= { ommp401PerformanceEntry 264 }

	ommp401EthernetMacTerminated256to511BytesFramesReceived OBJECT-TYPE
		SYNTAX  DisplayString
		MAX-ACCESS  read-only
		STATUS  current
		DESCRIPTION
			"For port configured with Ethernet traffic,
			gives Rx Good 65B to 127Bpkt frames count.
			-----------------------------
			ommp401InterfaceNumber:
			1 to 4 - CLIENT-1 to CLIENT-4
			-----------------------------
			Values:
			eg: 1e-3
			-----------------------------"
	::= { ommp401PerformanceEntry 265 }

	ommp401EthernetMacTerminated512to1023BytesFramesTransmitted OBJECT-TYPE
		SYNTAX  DisplayString
		MAX-ACCESS  read-only
		STATUS  current
		DESCRIPTION
			"For port configured with Ethernet traffic,
			gives Rx Good 128B to 255Bpkt frames count.
			-----------------------------
			ommp401InterfaceNumber:
			1 to 4 - CLIENT-1 to CLIENT-4
			-----------------------------
			Values:
			eg: 1e-3
			-----------------------------"
	::= { ommp401PerformanceEntry 266 }

	ommp401EthernetMacTerminated512to1023BytesFramesReceived OBJECT-TYPE
		SYNTAX  DisplayString
		MAX-ACCESS  read-only
		STATUS  current
		DESCRIPTION
			"For port configured with Ethernet traffic,
			gives Rx Good 256B to 511Bpkt frames count.
			-----------------------------
			ommp401InterfaceNumber:
			1 to 4 - CLIENT-1 to CLIENT-4
			-----------------------------
			Values:
			eg: 1e-3
			-----------------------------"
	::= { ommp401PerformanceEntry 267 }

	ommp401EthernetMacTerminated1024to1518BytesFramesTransmitted OBJECT-TYPE
		SYNTAX  DisplayString
		MAX-ACCESS  read-only
		STATUS  current
		DESCRIPTION
			"For port configured with Ethernet traffic,
			gives Rx Good 512B to 1023Bpkt frames count.
			-----------------------------
			ommp401InterfaceNumber:
			1 to 4 - CLIENT-1 to CLIENT-4
			-----------------------------
			Values:
			eg: 1e-3
			-----------------------------"
	::= { ommp401PerformanceEntry 268 }

	ommp401EthernetMacTerminated1024to1518BytesFramesReceived OBJECT-TYPE
		SYNTAX  DisplayString
		MAX-ACCESS  read-only
		STATUS  current
		DESCRIPTION
			"For port configured with Ethernet traffic,
			gives Rx Good 1024B to 1518Bpkt frames count.
			-----------------------------
			ommp401InterfaceNumber:
			1 to 4 - CLIENT-1 to CLIENT-4
			-----------------------------
			Values:
			eg: 1e-3
			-----------------------------"
	::= { ommp401PerformanceEntry 269 }

	ommp401EthernetMacTerminated1519toMaxBytesFramesTransmitted OBJECT-TYPE
		SYNTAX  DisplayString
		MAX-ACCESS  read-only
		STATUS  current
		DESCRIPTION
			"For port configured with Ethernet traffic,
			gives Rx Good 1519BLTJpkt frames count.
			-----------------------------
			ommp401InterfaceNumber:
			1 to 4 - CLIENT-1 to CLIENT-4
			-----------------------------
			Values:
			eg: 1e-3
			-----------------------------"
	::= { ommp401PerformanceEntry 270 }

	ommp401EthernetMacTerminated1519toMaxBytesFramesReceived OBJECT-TYPE
		SYNTAX  DisplayString
		MAX-ACCESS  read-only
		STATUS  current
		DESCRIPTION
			"For port configured with Ethernet traffic,
			gives Rx Good jumbo frames count.
			-----------------------------
			ommp401InterfaceNumber:
			1 to 4 - CLIENT-1 to CLIENT-4
			-----------------------------
			Values:
			eg: 1e-3
			-----------------------------"
	::= { ommp401PerformanceEntry 271 }

	ommp401EthernetMacTerminatedJumboFramesTransmitted OBJECT-TYPE
		SYNTAX  DisplayString
		MAX-ACCESS  read-only
		STATUS  current
		DESCRIPTION
			"For port configured with Ethernet traffic,
			gives Rx Bad frames count.
			-----------------------------
			ommp401InterfaceNumber:
			1 to 4 - CLIENT-1 to CLIENT-4
			-----------------------------
			Values:
			eg: 1e-3
			-----------------------------"
	::= { ommp401PerformanceEntry 272 }

	ommp401EthernetMacTerminatedJumboFramesReceived OBJECT-TYPE
		SYNTAX  DisplayString
		MAX-ACCESS  read-only
		STATUS  current
		DESCRIPTION
			"For port configured with Ethernet traffic,
			gives Rx Bad Octects frames count.
			-----------------------------
			ommp401InterfaceNumber:
			1 to 4 - CLIENT-1 to CLIENT-4
			-----------------------------
			Values:
			eg: 1e-3
			-----------------------------"
	::= { ommp401PerformanceEntry 273 }
	
	ommp401LineOtnFecUncorrectedWords OBJECT-TYPE
		SYNTAX  DisplayString
		MAX-ACCESS  read-only
		STATUS  current
		DESCRIPTION
			"For port configured with OTU4/OTUC4 traffic,
			OTU Uncorrected Word Error Counter counts the number of
			FEC errored code words that could not be corrected.
			-----------------------------
			ommp401 InterfaceNumber:
			1 to 4 - CLIENT-1 to CLIENT-4
			-----------------------------
			Values:
			eg: 1234
			-----------------------------"
	::= { ommp401PerformanceEntry 274 }

	ommp401LineOtnFecCorrectedBits OBJECT-TYPE
		SYNTAX  DisplayString
		MAX-ACCESS  read-only
		STATUS  current
		DESCRIPTION
			"For port configured with OTU4/OTUC4 traffic,
			OTU Corrected Bit Error Counter counts the number of
			FEC error bits that could be corrected(sum of ones
			corrected and zeros corrected bits).
			-----------------------------
			ommp401 InterfaceNumber:
			1 to 4 - CLIENT-1 to CLIENT-4
			-----------------------------
			Values:
			eg: 1234
			-----------------------------"
	::= { ommp401PerformanceEntry 275 }

	ommp401LineOtnFecZerosCorrectedBits OBJECT-TYPE
		SYNTAX  DisplayString
		MAX-ACCESS  read-only
		STATUS  current
		DESCRIPTION
			"For port configured with OTU4/OTUC4 traffic,
			OTU Zero Corrected Bits Error Counter counts the number
			of FEC error bits that could be corrected from
			one to zero value(Expected 0 but received as 1).
			-----------------------------
			ommp401 InterfaceNumber:
			1 to 4 - CLIENT-1 to CLIENT-4
			-----------------------------
			Values:
			eg: 1234
			-----------------------------"
	::= { ommp401PerformanceEntry 276 }

	ommp401LineOtnFecOnesCorrectedBits OBJECT-TYPE
		SYNTAX  DisplayString
		MAX-ACCESS  read-only
		STATUS  current
		DESCRIPTION
			"For port configured with OTU4/OTUC4 traffic,
			OTU Ones Corrected Byte Error Counter counts the number
			of FEC error bytes that could be corrected from
			zero to one value(Expected 1 but received as 0).
			-----------------------------
			ommp401 InterfaceNumber:
			1 to 4 - CLIENT-1 to CLIENT-4
			-----------------------------
			Values:
			eg: 1234
			-----------------------------"
	::= { ommp401PerformanceEntry 277 }

	ommp401LineOtuBitInterleavedParityErrors OBJECT-TYPE
		SYNTAX  DisplayString
		MAX-ACCESS  read-only
		STATUS  current
		DESCRIPTION
			"For port configured with OTU4/OTUC4 traffic,
			OTU-BIP Counter counts the Parity errors evaluated by
			SM field of an OTU4 frame.
			-----------------------------
			ommp401 InterfaceNumber:
			1 to 4 - CLIENT-1 to CLIENT-4
			-----------------------------
			Values:
			eg: 1234
			-----------------------------"
	::= { ommp401PerformanceEntry 278 }

	ommp401LineOtuIncomingAlignmentErrorSeconds OBJECT-TYPE
		SYNTAX  DisplayString
		MAX-ACCESS  read-only
		STATUS  current
		DESCRIPTION
			"For port configured with OTU4/OTUC4 traffic,
			OTU Incoming Alignment Error Second increases,
			when OTU IAE Alarm is detected in that particular second
			of the incoming OTU signal
			-----------------------------
			ommp401 InterfaceNumber:
			1 to 4 - CLIENT-1 to CLIENT-4
			-----------------------------
			Values:
			eg: 1234
			-----------------------------"
	::= { ommp401PerformanceEntry 279 }

	ommp401LineOtuBackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code.
			-----------------------------
			ommp401 InterfaceNumber:
			1 to 4 - CLIENT-1 to CLIENT-4
			-----------------------------
			Values:
			eg: 1234
			-----------------------------"
	::= { ommp401PerformanceEntry 280 }

	ommp401LineOtuBackwardIncomingAlignmentErrorSeconds OBJECT-TYPE
		SYNTAX  DisplayString
		MAX-ACCESS  read-only
		STATUS  current
		DESCRIPTION
			"For port configured with OTU4/OTUC4 traffic,
			OTU-BIAE Counter increases when SM-BIAE Alarm is 
			detected in that particular second
			of the incoming OTU signal
			-----------------------------
			ommp401 InterfaceNumber:
			1 to 4 - CLIENT-1 to CLIENT-4
			-----------------------------
			Values:
			eg: 1234
			-----------------------------"
	::= { ommp401PerformanceEntry 281 }

	ommp401LineOtuErrorFreeSeconds OBJECT-TYPE
		SYNTAX  DisplayString
		MAX-ACCESS  read-only
		STATUS  current
		DESCRIPTION
			"For port configured with OTU4/OTUC4 traffic,
			OTU Error Free Seconds increases when no BIP errors
			or defects are detected
			-----------------------------
			ommp401 InterfaceNumber:
			1 to 4 - CLIENT-1 to CLIENT-4
			-----------------------------
			Values:
			eg: 1234
			-----------------------------"
	::= { ommp401PerformanceEntry 282 }

	ommp401LineOtuErrorSeconds OBJECT-TYPE
		SYNTAX  DisplayString
		MAX-ACCESS  read-only
		STATUS  current
		DESCRIPTION
			"For port configured with OTU4/OTUC4 traffic,
			OTU Error Seconds increases when any defects like 
			OTU-AIS, SM-TIM etc are detected at the
			section monitoring level
			-----------------------------
			ommp401 InterfaceNumber:
			1 to 4 - CLIENT-1 to CLIENT-4
			-----------------------------
			Values:
			eg: 1234
			-----------------------------"
	::= { ommp401PerformanceEntry 283 }

	ommp401LineOtuBackgroundBlockErrors OBJECT-TYPE
		SYNTAX  DisplayString
		MAX-ACCESS  read-only
		STATUS  current
		DESCRIPTION
			"For port configured with OTU4/OTUC4 traffic,
			OTU Background Block Errors increases on defects 
			detected and when BIP errors are less than 15% errored
			blocks received 
			-----------------------------
			ommp401 InterfaceNumber:
			1 to 4 - CLIENT-1 to CLIENT-4
			-----------------------------
			Values:
			eg: 1234
			-----------------------------"
	::= { ommp401PerformanceEntry 284 }

	ommp401LineOtuSevereErrorSeconds OBJECT-TYPE
		SYNTAX  DisplayString
		MAX-ACCESS  read-only
		STATUS  current
		DESCRIPTION
			"For port configured with OTU4/OTUC4 traffic,
			OTU Severe Error Seconds increases on defects
			detected and when BIP errors are greater than or
			equal to 15% errored blocks received 
			-----------------------------
			ommp401 InterfaceNumber:
			1 to 4 - CLIENT-1 to CLIENT-4
			-----------------------------
			Values:
			eg: 1234
			-----------------------------"
	::= { ommp401PerformanceEntry 285 }

	ommp401LineOtuUnavailableSeconds OBJECT-TYPE
		SYNTAX  DisplayString
		MAX-ACCESS  read-only
		STATUS  current
		DESCRIPTION
			"For port configured with OTU4/OTUC4 traffic,
			OTU Unavailable Seconds increases,
			when 10 consecutive OTU Severe Error seconds
			are detected
			-----------------------------
			ommp401 InterfaceNumber:
			1 to 4 - CLIENT-1 to CLIENT-4
			-----------------------------
			Values:
			eg: 1234
			-----------------------------"
	::= { ommp401PerformanceEntry 286 }

	ommp401LineOtuErrorSecondsErrorRatio OBJECT-TYPE
		SYNTAX  DisplayString
		MAX-ACCESS  read-only
		STATUS  current
		DESCRIPTION
			"For port configured with OTU4/OTUC4 traffic,
			OTU Error Seconds increases when any defects like 
			OTU-AIS, SM-TIM etc are detected at the section monitoring level,
			The ratio of Error seconds in available time to total seconds
			in available time during a fixed measurement interval
			-----------------------------
			ommp401 InterfaceNumber:
			1 to 4 - CLIENT-1 to CLIENT-4
			-----------------------------
			Values:
			eg: 1234
			-----------------------------"
	::= { ommp401PerformanceEntry 287 }

	ommp401LineOtuErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 288 }

	ommp401LineOtuErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 289 }

	ommp401LineOtuConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 290 }

	ommp401LineOtuNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 291 }

	ommp401LineOtuPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 292 }

	ommp401LineOtuBackgroundBlockErrorRatio OBJECT-TYPE
		SYNTAX  DisplayString
		MAX-ACCESS  read-only
		STATUS  current
		DESCRIPTION
			"For port configured with OTU4/OTUC4 traffic,
			gives OTU Background Block Error Seconds Error Ratio.
			The ratio of BBE in available time to total seconds
			in available time during a fixed measurement interval.
			-----------------------------
			ommp401 InterfaceNumber:
			1 to 4 - CLIENT-1 to CLIENT-4
			-----------------------------
			Values:
			eg: 1e-3
			-----------------------------"
	::= { ommp401PerformanceEntry 293 }

	ommp401LineOtuSevereErrorSecondsErrorRatio OBJECT-TYPE
		SYNTAX  DisplayString
		MAX-ACCESS  read-only
		STATUS  current
		DESCRIPTION
			"For port configured with OTU4/OTUC4 traffic,
			gives OTU Severe Error Seconds Error Ratio.
			The ratio of SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 294 }

	ommp401LineOtuFarEndErrorFreeSeconds OBJECT-TYPE
		SYNTAX  DisplayString
		MAX-ACCESS  read-only
		STATUS  current
		DESCRIPTION
			"For port configured with OTU4/OTUC4 traffic,
			OTU Far end Error Free Seconds, increases when no
			backward errors or defects like BDI or BEI
			are detected in the incoming OTU signal.
			-----------------------------
			ommp401 InterfaceNumber:
			1 to 4 - CLIENT-1 to CLIENT-4
			-----------------------------
			Values:
			eg: 1234
			-----------------------------"
	::= { ommp401PerformanceEntry 295 }

	ommp401LineOtuFarEndBackgroundBlockErrors OBJECT-TYPE
		SYNTAX  DisplayString
		MAX-ACCESS  read-only
		STATUS  current
		DESCRIPTION
			"For port configured with OTU4/OTUC4 traffic,
			OTU Far End Background Block Errors increases when BEI
			errors are less than 15% Errored Blocks in incoming
			OTU signal.
			-----------------------------
			ommp401 InterfaceNumber:
			1 to 4 - CLIENT-1 to CLIENT-4
			-----------------------------
			Values:
			eg: 1234
			-----------------------------"
	::= { ommp401PerformanceEntry 296 }

	ommp401LineOtuFarEndSevereErrorSeconds OBJECT-TYPE
		SYNTAX  DisplayString
		MAX-ACCESS  read-only
		STATUS  current
		DESCRIPTION
			"For port configured with OTU4/OTUC4 traffic,
			OTU Far End Severe Error Seconds increases on defects
			like BDI are detected and when BEI errors are greater
			than or equal to 15% Errored Blocks in incoming OTU 
			signal.
			-----------------------------
			ommp401 InterfaceNumber:
			1 to 4 - CLIENT-1 to CLIENT-4
			-----------------------------
			Values:
			eg: 1234
			-----------------------------"
	::= { ommp401PerformanceEntry 297 }

	ommp401LineOtuFarEndUnavailableSeconds OBJECT-TYPE
		SYNTAX  DisplayString
		MAX-ACCESS  read-only
		STATUS  current
		DESCRIPTION
			"For port configured with OTU4/OTUC4 traffic,
			OTU Far End Unavailable Seconds increases, 
			after 9 consecutive OTU Far End Severe Error
			seconds are detected
			-----------------------------
			ommp401 InterfaceNumber:
			1 to 4 - CLIENT-1 to CLIENT-4
			-----------------------------
			Values:
			eg: 1234
			-----------------------------"
	::= { ommp401PerformanceEntry 298 }

	ommp401LineOtuFarEndErrorSecondsErrorRatio OBJECT-TYPE
		SYNTAX  DisplayString
		MAX-ACCESS  read-only
		STATUS  current
		DESCRIPTION
			"For port configured with OTU4/OTUC4 traffic,
			gives Otu Far End Error seconds Error Ratio.
			The ratio of Far End ES in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 299 }

	ommp401LineOtuFarEndErrorSeconds OBJECT-TYPE
		SYNTAX  DisplayString
		MAX-ACCESS  read-only
		STATUS  current
		DESCRIPTION
			"For port configured with OTU4/OTUC4 traffic,
			OTU Far End Error Seconds increases on
			detection of defects like BDI in incoming
			OTU signal.
			-----------------------------
			ommp401 InterfaceNumber:
			1 to 4 - CLIENT-1 to CLIENT-4
			-----------------------------
			Values:
			eg: 1234
			-----------------------------"
	::= { ommp401PerformanceEntry 300 }

	ommp401LineOtuFarEndBackgroundBlockErrorRatio OBJECT-TYPE
		SYNTAX  DisplayString
		MAX-ACCESS  read-only
		STATUS  current
		DESCRIPTION
			"For port configured with OTU4/OTUC4 traffic,
			gives Otu Far End Background Block Error Ratio.
			The ratio of Far End BBE in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 301 }

	ommp401LineOtuFarEndSevereErrorSecondsErrorRatio OBJECT-TYPE
		SYNTAX  DisplayString
		MAX-ACCESS  read-only
		STATUS  current
		DESCRIPTION
			"For port configured with OTU4/OTUC4 traffic,
			gives Otu Far End Severe Error Seconds Error Ratio.
			The ratio of Far End SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 302 }

	ommp401LineOtuErrorRatio   OBJECT-TYPE
              SYNTAX  DisplayString
              MAX-ACCESS  read-only
              STATUS  current
              DESCRIPTION
			"For port configured with OTU4/OTUC4 traffic,
			gives the OTU Error Ratio for requested port. The ratio  
			of number of error bits to the number of bits received in
			a particular second
			-----------------------------
			ommp401 InterfaceNumber:
			1 to 4 - CLIENT-1 to CLIENT-4
			-----------------------------	
			Value:
			eg: 4.0
			-----------------------------"
	::= { ommp401PerformanceEntry 303 } 

	ommp401LineOtuFarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 304 }

	ommp401LineOtuFarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 305 }

	ommp401LineOtuFarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 306 }

	ommp401LineOtuFarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 307 }

	ommp401LineOtuFarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 308 }

	ommp401LineOtuFramesReceived  OBJECT-TYPE
              SYNTAX  DisplayString
              MAX-ACCESS  read-only
              STATUS  current
              DESCRIPTION
			"For port configured with OTU4/OTUC4 traffic, gives the 
			gives the number of OTU frames transmitted.
			-----------------------------
			ommp401 InterfaceNumber:
			1 to 4 - CLIENT-1 to CLIENT-4
			-----------------------------	
			Value:
			eg: 4.0
			-----------------------------"
	::= { ommp401PerformanceEntry 309 }

	ommp401LineOtuBitErrorRate  OBJECT-TYPE
              SYNTAX  DisplayString
              MAX-ACCESS  read-only
              STATUS  current
              DESCRIPTION
			"For port configured with OTU4/OTUC4 traffic, gives the 
			Bit Error Rate. Bit error rate is the Error ratio 
			multiplied by the OTU4 standard signal 
			data-rate( 10.709225316 Gbps )
			-----------------------------
			ommp401 InterfaceNumber:
			1 to 4 - CLIENT-1 to CLIENT-4
			-----------------------------	
			Value:
			eg: 4.0
			-----------------------------"
	::= { ommp401PerformanceEntry 310 }

	ommp401LineOduBitInterleavedParityErrors OBJECT-TYPE
		SYNTAX  DisplayString
		MAX-ACCESS  read-only
		STATUS  current
		DESCRIPTION
			"For port configured with OTU4/OTUC4 traffic,
			ODU-BIP Counter counts the Parity errors evaluated by
			PM field of an OTU4 frame
			-----------------------------
			ommp401 InterfaceNumber:
			1 to 4 - CLIENT-1 to CLIENT-4
			-----------------------------
			Values:
			eg: 1234
			-----------------------------"
	::= { ommp401PerformanceEntry 311 }

	ommp401LineOduTcm1BitInterleavedParityErrors OBJECT-TYPE
		SYNTAX  DisplayString
		MAX-ACCESS  read-only
		STATUS  current
		DESCRIPTION
			"For port configured with OTU4/OTUC4 traffic,
			TCM1-BIP Counter counts the Parity errors evaluated by
			TCM1 field in ODU frame
			-----------------------------
			ommp401 InterfaceNumber:
			1 to 4 - CLIENT-1 to CLIENT-4
			-----------------------------
			Values:
			eg: 1234
			-----------------------------"
	::= { ommp401PerformanceEntry 312 }

	ommp401LineOduTcm2BitInterleavedParityErrors OBJECT-TYPE
		SYNTAX  DisplayString
		MAX-ACCESS  read-only
		STATUS  current
		DESCRIPTION
			"For port configured with OTU4/OTUC4 traffic,
			TCM2-BIP Counter counts the Parity errors evaluated by
			TCM2 field in ODU frame
			-----------------------------
			ommp401 InterfaceNumber:
			1 to 4 - CLIENT-1 to CLIENT-4
			-----------------------------
			Values:
			eg: 1234
			-----------------------------"
	::= { ommp401PerformanceEntry 313 }

	ommp401LineOduTcm3BitInterleavedParityErrors OBJECT-TYPE
		SYNTAX  DisplayString
		MAX-ACCESS  read-only
		STATUS  current
		DESCRIPTION
			"For port configured with OTU4/OTUC4 traffic,
			TCM3-BIP Counter counts the Parity errors evaluated by
			TCM3 field in ODU frame
			-----------------------------
			ommp401 InterfaceNumber:
			1 to 4 - CLIENT-1 to CLIENT-4
			-----------------------------
			Values:
			eg: 1234
			-----------------------------"
	::= { ommp401PerformanceEntry 314 }

	ommp401LineOduTcm4BitInterleavedParityErrors OBJECT-TYPE
		SYNTAX  DisplayString
		MAX-ACCESS  read-only
		STATUS  current
		DESCRIPTION
			"For port configured with OTU4/OTUC4 traffic,
			TCM4-BIP Counter counts the Parity errors evaluated by
			TCM4 field in ODU frame
			-----------------------------
			ommp401 InterfaceNumber:
			1 to 4 - CLIENT-1 to CLIENT-4
			-----------------------------
			Values:
			eg: 1234
			-----------------------------"
	::= { ommp401PerformanceEntry 315 }

	ommp401LineOduTcm5BitInterleavedParityErrors OBJECT-TYPE
		SYNTAX  DisplayString
		MAX-ACCESS  read-only
		STATUS  current
		DESCRIPTION
			"For port configured with OTU4/OTUC4 traffic,
			TCM5-BIP Counter counts the Parity errors evaluated by
			TCM5 field in ODU frame
			-----------------------------
			ommp401 InterfaceNumber:
			1 to 4 - CLIENT-1 to CLIENT-4
			-----------------------------
			Values:
			eg: 1234
			-----------------------------"
	::= { ommp401PerformanceEntry 316 }

	ommp401LineOduTcm6BitInterleavedParityErrors OBJECT-TYPE
		SYNTAX  DisplayString
		MAX-ACCESS  read-only
		STATUS  current
		DESCRIPTION
			"For port configured with OTU4/OTUC4 traffic,
			TCM6-BIP Counter counts the Parity errors evaluated by
			TCM6 field in ODU frame
			-----------------------------
			ommp401 InterfaceNumber:
			1 to 4 - CLIENT-1 to CLIENT-4
			-----------------------------
			Values:
			eg: 1234
			-----------------------------"
	::= { ommp401PerformanceEntry 317 }

	ommp401LineOduTcm1IncomingAlignmentErrorSeconds OBJECT-TYPE
		SYNTAX  DisplayString
		MAX-ACCESS  read-only
		STATUS  current
		DESCRIPTION
			"For port configured with OTU4/OTUC4 traffic,
			ODU Incoming Alignment Error Count increases,
			when ODU-TCM1-IAE is detected in that particular second
			of the incoming OTU signal
			-----------------------------
			ommp401 InterfaceNumber:
			1 to 4 - CLIENT-1 to CLIENT-4
			-----------------------------
			Values:
			eg: 1234
			-----------------------------"
	::= { ommp401PerformanceEntry 318 }

	ommp401LineOduBackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code.
			-----------------------------
			ommp401 InterfaceNumber:
			1 to 4 - CLIENT-1 to CLIENT-4
			-----------------------------
			Values:
			eg: 1234
			-----------------------------"
	::= { ommp401PerformanceEntry 319 }

	ommp401LineOduTcm1BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM1 level.
			-----------------------------
			ommp401 InterfaceNumber:
			1 to 4 - CLIENT-1 to CLIENT-4
			-----------------------------
			Values:
			eg: 1234
			-----------------------------"
	::= { ommp401PerformanceEntry 320 }

	ommp401LineOduTcm2BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM2 level.
			-----------------------------
			ommp401 InterfaceNumber:
			1 to 4 - CLIENT-1 to CLIENT-4
			-----------------------------
			Values:
			eg: 1234
			-----------------------------"
	::= { ommp401PerformanceEntry 321 }

	ommp401LineOduTcm3BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM3 level.
			-----------------------------
			ommp401 InterfaceNumber:
			1 to 4 - CLIENT-1 to CLIENT-4
			-----------------------------
			Values:
			eg: 1234
			-----------------------------"
	::= { ommp401PerformanceEntry 322 }

	ommp401LineOduTcm4BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM4 level.
			-----------------------------
			ommp401 InterfaceNumber:
			1 to 4 - CLIENT-1 to CLIENT-4
			-----------------------------
			Values:
			eg: 1234
			-----------------------------"
	::= { ommp401PerformanceEntry 323 }

	ommp401LineOduTcm5BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM5 level.
			-----------------------------
			ommp401 InterfaceNumber:
			1 to 4 - CLIENT-1 to CLIENT-4
			-----------------------------
			Values:
			eg: 1234
			-----------------------------"
	::= { ommp401PerformanceEntry 324 }

	ommp401LineOduTcm6BackwardErrorIndicationErrorCount OBJECT-TYPE
		SYNTAX  DisplayString
		MAX-ACCESS  read-only
		STATUS  current
		DESCRIPTION
			"For port configured with OTU4/OTUC4 traffic,
			this signal is used to convey in the upstream direction 
			the count of interleaved bit blocks that have 
			been detected in error using the BIP-8 code at
			TCM6 level.
			-----------------------------
			ommp401 InterfaceNumber:
			1 to 4 - CLIENT-1 to CLIENT-4
			-----------------------------
			Values:
			eg: 1234
			-----------------------------"
	::= { ommp401PerformanceEntry 325 }

	ommp401LineOduTcm1BackwardIncomingAlignmentErrorSeconds OBJECT-TYPE
		SYNTAX  DisplayString
		MAX-ACCESS  read-only
		STATUS  current
		DESCRIPTION
			"For port configured with OTU4/OTUC4 traffic,
			ODU Backward Incoming Alignment Error Count increases,
			when ODU-TCM1-BIAE is detected in that particular second
			of the incoming OTU signal
			-----------------------------
			ommp401 InterfaceNumber:
			1 to 4 - CLIENT-1 to CLIENT-4
			-----------------------------
			Values:
			eg: 1234
			-----------------------------"
	::= { ommp401PerformanceEntry 326 }

	ommp401LineOduDelayMeasurement OBJECT-TYPE
		SYNTAX  DisplayString
		MAX-ACCESS  read-only
		STATUS  current
		DESCRIPTION
			"For port configured with OTU4/OTUC4 traffic,
			gives delay measurement of ODU frame
			-----------------------------
			ommp401 InterfaceNumber:
			1 to 4 - CLIENT-1 to CLIENT-4
			-----------------------------
			Values:
			eg: Reserved for further study
			-----------------------------"
	::= { ommp401PerformanceEntry 327 }

	ommp401LineOduErrorFreeSeconds OBJECT-TYPE
		SYNTAX  DisplayString
		MAX-ACCESS  read-only
		STATUS  current
		DESCRIPTION
			"For port configured with OTU4/OTUC4 traffic,
			ODU Error Free Seconds increases,
			when no BIP errors or defects are detected at the
			path monitoring level
			-----------------------------
			ommp401 InterfaceNumber:
			1 to 4 - CLIENT-1 to CLIENT-4
			-----------------------------
			Values:
			eg: 1234
			-----------------------------"
	::= { ommp401PerformanceEntry 328 }

	ommp401LineOduErrorSeconds OBJECT-TYPE
		SYNTAX  DisplayString
		MAX-ACCESS  read-only
		STATUS  current
		DESCRIPTION
			"For port configured with OTU4/OTUC4 traffic,
			ODU Error Seconds increases on defects detected at the
			path monitoring level
			-----------------------------
			ommp401 InterfaceNumber:
			1 to 4 - CLIENT-1 to CLIENT-4
			-----------------------------
			Values:
			eg: 1234
			-----------------------------"
	::= { ommp401PerformanceEntry 329 }

	ommp401LineOduBackgroundBlockErrors OBJECT-TYPE
		SYNTAX  DisplayString
		MAX-ACCESS  read-only
		STATUS  current
		DESCRIPTION
			"For port configured with OTU4/OTUC4 traffic,
			ODU Background Block Errors increases on defects 
			detected and when BIP errors are less than 15% 
			Errored Blocks in incoming OTU signal.
			-----------------------------
			ommp401 InterfaceNumber:
			1 to 4 - CLIENT-1 to CLIENT-4
			-----------------------------
			Values:
			eg: 1234
			-----------------------------"
	::= { ommp401PerformanceEntry 330 }

	ommp401LineOduSevereErrorSeconds OBJECT-TYPE
		SYNTAX  DisplayString
		MAX-ACCESS  read-only
		STATUS  current
		DESCRIPTION
			"For port configured with OTU4/OTUC4 traffic,
			ODU Severe Error Seconds increases on defects detected
			and when BIP errors are more than 15% Errored Blocks
			in incoming OTU signal.
			-----------------------------
			ommp401 InterfaceNumber:
			1 to 4 - CLIENT-1 to CLIENT-4
			-----------------------------
			Values:
			eg: 1234
			-----------------------------"
	::= { ommp401PerformanceEntry 331 }

	ommp401LineOduUnavailableSeconds OBJECT-TYPE
		SYNTAX  DisplayString
		MAX-ACCESS  read-only
		STATUS  current
		DESCRIPTION
			"For port configured with OTU4/OTUC4 traffic,
			ODU Unavailable Seconds increases, when 10 consecutive
			Severe ODU Error seconds are detected
			-----------------------------
			ommp401 InterfaceNumber:
			1 to 4 - CLIENT-1 to CLIENT-4
			-----------------------------
			Values:
			eg: 1234
			-----------------------------"
	::= { ommp401PerformanceEntry 332 }

	ommp401LineOduErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 333 }

	ommp401LineOduErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 334 }

	ommp401LineOduConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 335 }

	ommp401LineOduNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 336 }

	ommp401LineOduPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 337 }

	ommp401LineOduFarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 338 }

	ommp401LineOduFarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 339 }

	ommp401LineOduFarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 340 }

	ommp401LineOduFarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 341 }

	ommp401LineOduFarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 342 }

	ommp401LineOduFramesReceived OBJECT-TYPE
		SYNTAX  DisplayString
		MAX-ACCESS  read-only
		STATUS  current
		DESCRIPTION
			"For port configured with OTU4/OTUC4 traffic,
			The number of frames received in ODU layer
			-----------------------------
			ommp401 InterfaceNumber:
			1 to 4 - CLIENT-1 to CLIENT-4
			-----------------------------
			Values:
			eg: 1234
			-----------------------------"
	::= { ommp401PerformanceEntry 343 }

	ommp401LineOduErrorSecondsErrorRatio OBJECT-TYPE
		SYNTAX  DisplayString
		MAX-ACCESS  read-only
		STATUS  current
		DESCRIPTION
			"For port configured with OTU4/OTUC4 traffic,
			OTU Error Seconds increases when any defects like 
			OTU-AIS, SM-TIM etc are detected at the section monitoring level,
			The ratio of Error seconds in available time to total seconds
			in available time during a fixed measurement interval
			-----------------------------
			ommp401 InterfaceNumber:
			1 to 4 - CLIENT-1 to CLIENT-4
			-----------------------------
			Values:
			eg: 1234
			-----------------------------"
	::= { ommp401PerformanceEntry 344 }

	ommp401LineOduBackgroundBlockErrorRatio OBJECT-TYPE
		SYNTAX  DisplayString
		MAX-ACCESS  read-only
		STATUS  current
		DESCRIPTION
			"For port configured with OTU4/OTUC4 traffic,
			gives ODU Background Block Error Ratio i.e.
			the ratio of BBE in available time to total seconds
			in available time during a fixed measurement interval.
			-----------------------------
			ommp401 InterfaceNumber:
			1 to 4 - CLIENT-1 to CLIENT-4
			-----------------------------
			Values:
			eg: 1e-3
			-----------------------------"
	::= { ommp401PerformanceEntry 345 }

	ommp401LineOduSevereErrorSecondsErrorRatio OBJECT-TYPE
		SYNTAX  DisplayString
		MAX-ACCESS  read-only
		STATUS  current
		DESCRIPTION
			"For port configured with OTU4/OTUC4 traffic,
			gives ODU Severe Error Seconds Error Ratio i.e.
			the ratio of SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 346 }

	ommp401LineOduFarEndErrorFreeSeconds OBJECT-TYPE
		SYNTAX  DisplayString
		MAX-ACCESS  read-only
		STATUS  current
		DESCRIPTION
			"For port configured with OTU4/OTUC4 traffic,
			ODU Far end Error Free Seconds, increases when no
			far end errors or defects are detected
			-----------------------------
			ommp401 InterfaceNumber:
			1 to 4 - CLIENT-1 to CLIENT-4
			-----------------------------
			Values:
			eg: 1234
			-----------------------------"
	::= { ommp401PerformanceEntry 347 }

	ommp401LineOduFarEndErrorSeconds OBJECT-TYPE
		SYNTAX  DisplayString
		MAX-ACCESS  read-only
		STATUS  current
		DESCRIPTION
			"For port configured with OTU4/OTUC4 traffic,
			ODU Far End Error Seconds increases on detection of
			defects like BDI and BEI at path monitoring level
			-----------------------------
			ommp401 InterfaceNumber:
			1 to 4 - CLIENT-1 to CLIENT-4
			-----------------------------
			Values:
			eg: 1234
			-----------------------------"
	::= { ommp401PerformanceEntry 348 }

	ommp401LineOduFarEndBackgroundBlockErrors OBJECT-TYPE
		SYNTAX  DisplayString
		MAX-ACCESS  read-only
		STATUS  current
		DESCRIPTION
			"For port configured with OTU4/OTUC4 traffic,
			ODU Far End Background Block Errors increases when
			BEI errors are less than 15% Errored Blocks in
			incoming OTU signal.
			-----------------------------
			ommp401 InterfaceNumber:
			1 to 4 - CLIENT-1 to CLIENT-4
			-----------------------------
			Values:
			eg: 1234
			-----------------------------"
	::= { ommp401PerformanceEntry 349 }

	ommp401LineOduFarEndSevereErrorSeconds OBJECT-TYPE
		SYNTAX  DisplayString
		MAX-ACCESS  read-only
		STATUS  current
		DESCRIPTION
			"For port configured with OTU4/OTUC4 traffic,
			ODU Far End Severe Error Seconds increases on defects
			like BDI are detected and when BEI errors are more than
			15% Errored Blocks in incoming OTU signal.
			-----------------------------
			ommp401 InterfaceNumber:
			1 to 4 - CLIENT-1 to CLIENT-4
			-----------------------------
			Values:
			eg: 1234
			-----------------------------"
	::= { ommp401PerformanceEntry 350 }

	ommp401LineOduFarEndUnavailableSeconds OBJECT-TYPE
		SYNTAX  DisplayString
		MAX-ACCESS  read-only
		STATUS  current
		DESCRIPTION
			"For port configured with OTU4/OTUC4 traffic,
			ODU Far End Unavailable Seconds increases, when 10
			consecutive OTU Far End Error seconds are detected
			-----------------------------
			ommp401 InterfaceNumber:
			1 to 4 - CLIENT-1 to CLIENT-4
			-----------------------------
			Values:
			eg: 1234
			-----------------------------"
	::= { ommp401PerformanceEntry 351 }

	ommp401LineOduFarEndErrorSecondsErrorRatio OBJECT-TYPE
		SYNTAX  DisplayString
		MAX-ACCESS  read-only
		STATUS  current
		DESCRIPTION
			"For port configured with OTU4/OTUC4 traffic,
			OTU Error Seconds increases when any defects like 
			OTU-AIS, SM-TIM etc are detected at the section monitoring level,
			The ratio of Error seconds in available time to total seconds
			in available time during a fixed measurement interval
			-----------------------------
			ommp401 InterfaceNumber:
			1 to 4 - CLIENT-1 to CLIENT-4
			-----------------------------
			Values:
			eg: 1234
			-----------------------------"
	::= { ommp401PerformanceEntry 352 }

	ommp401LineOduFarEndBackgroundBlockErrorRatio OBJECT-TYPE
		SYNTAX  DisplayString
		MAX-ACCESS  read-only
		STATUS  current
		DESCRIPTION
			"For port configured with OTU4/OTUC4 traffic,
			gives ODU Far End Background Block Error Ratio i.e.
			the ratio of Far End BBE in available time to total
			seconds	in available time during a fixed measurement
			interval.
			-----------------------------
			ommp401 InterfaceNumber:
			1 to 4 - CLIENT-1 to CLIENT-4
			-----------------------------
			Values:
			eg: 1e-3
			-----------------------------"
	::= { ommp401PerformanceEntry 353 }

	ommp401LineOduFarEndSevereErrorSecondsErrorRatio OBJECT-TYPE
		SYNTAX  DisplayString
		MAX-ACCESS  read-only
		STATUS  current
		DESCRIPTION
			"For port configured with OTU4/OTUC4 traffic,
			gives ODU Far End Severe Error Seconds Error Ratio i.e.
			The ratio of Far End SES in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 354 }

	ommp401LineOtnMeasurementPeriod OBJECT-TYPE
		SYNTAX  DisplayString
		MAX-ACCESS  read-only
		STATUS  current
		DESCRIPTION
			"For port configured with OTU4/OTUC4 traffic,
			gives measurement period of OTN frame
			-----------------------------
			ommp401 InterfaceNumber:
			1 to 4 - CLIENT-1 to CLIENT-4
			-----------------------------
			Values:
			eg: Reserved for further study
			-----------------------------"
	::= { ommp401PerformanceEntry 355 }

	ommp401LineOduTcm1ErrorFreeSeconds OBJECT-TYPE
		SYNTAX  DisplayString
		MAX-ACCESS  read-only
		STATUS  current
		DESCRIPTION
			"For port configured with OTU4/OTUC4 traffic,
			TCM1 Error Free Seconds increases,
			when no BIP errors or defects are detected at the
			path monitoring level
			-----------------------------
			ommp401 InterfaceNumber:
			1 to 4 - CLIENT-1 to CLIENT-4
			-----------------------------
			Values:
			eg: 1234
			-----------------------------"
	::= { ommp401PerformanceEntry 356 }

	ommp401LineOduTcm1ErrorSeconds OBJECT-TYPE
		SYNTAX  DisplayString
		MAX-ACCESS  read-only
		STATUS  current
		DESCRIPTION
			"For port configured with OTU4/OTUC4 traffic,
			TCM1 Error Seconds increases on defects detected at the
			path monitoring level
			-----------------------------
			ommp401 InterfaceNumber:
			1 to 4 - CLIENT-1 to CLIENT-4
			-----------------------------
			Values:
			eg: 1234
			-----------------------------"
	::= { ommp401PerformanceEntry 357 }

	ommp401LineOduTcm1BackgroundBlockErrors OBJECT-TYPE
		SYNTAX  DisplayString
		MAX-ACCESS  read-only
		STATUS  current
		DESCRIPTION
			"For port configured with OTU4/OTUC4 traffic,
			TCM1 Background Block Errors increases on defects 
			detected and when BIP errors are less than 15% 
			Errored Blocks in incoming OTU signal.
			-----------------------------
			ommp401 InterfaceNumber:
			1 to 4 - CLIENT-1 to CLIENT-4
			-----------------------------
			Values:
			eg: 1234
			-----------------------------"
	::= { ommp401PerformanceEntry 358 }

	ommp401LineOduTcm1SevereErrorSeconds OBJECT-TYPE
		SYNTAX  DisplayString
		MAX-ACCESS  read-only
		STATUS  current
		DESCRIPTION
			"For port configured with OTU4/OTUC4 traffic,
			TCM1 Severe Error Seconds increases on defects detected
			and when BIP errors are more than 15% Errored Blocks
			in incoming OTU signal.
			-----------------------------
			ommp401 InterfaceNumber:
			1 to 4 - CLIENT-1 to CLIENT-4
			-----------------------------
			Values:
			eg: 1234
			-----------------------------"
	::= { ommp401PerformanceEntry 359 }

	ommp401LineOduTcm1UnavailableSeconds OBJECT-TYPE
		SYNTAX  DisplayString
		MAX-ACCESS  read-only
		STATUS  current
		DESCRIPTION
			"For port configured with OTU4/OTUC4 traffic,
			TCM1 Unavailable Seconds increases, when 10 consecutive
			Severe TCM1 Error seconds are detected
			-----------------------------
			ommp401 InterfaceNumber:
			1 to 4 - CLIENT-1 to CLIENT-4
			-----------------------------
			Values:
			eg: 1234
			-----------------------------"
	::= { ommp401PerformanceEntry 360 }

	ommp401LineOduTcm1ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 361 }

	ommp401LineOduTcm1ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 362 }

	ommp401LineOduTcm1ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 363 }

	ommp401LineOduTcm1NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 364 }

	ommp401LineOduTcm1PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 365 }

	ommp401LineOduTcm1BackgroundBlockErrorRatio OBJECT-TYPE
		SYNTAX  DisplayString
		MAX-ACCESS  read-only
		STATUS  current
		DESCRIPTION
			"For port configured with OTU4/OTUC4 traffic,
			gives TCM1 Background Block Error Ratio i.e.
			the ratio of BBE in available time to total seconds
			in available time during a fixed measurement interval.
			-----------------------------
			ommp401 InterfaceNumber:
			1 to 4 - CLIENT-1 to CLIENT-4
			-----------------------------
			Values:
			eg: 1e-3
			-----------------------------"
	::= { ommp401PerformanceEntry 366 }

	ommp401LineOduTcm1SevereErrorSecondsErrorRatio OBJECT-TYPE
		SYNTAX  DisplayString
		MAX-ACCESS  read-only
		STATUS  current
		DESCRIPTION
			"For port configured with OTU4/OTUC4 traffic,
			gives TCM1 Severe Error Seconds Error Ratio i.e.
			the ratio of SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 367 }

	ommp401LineOduTcm1FarEndErrorFreeSeconds OBJECT-TYPE
		SYNTAX  DisplayString
		MAX-ACCESS  read-only
		STATUS  current
		DESCRIPTION
			"For port configured with OTU4/OTUC4 traffic,
			TCM1 Far end Error Free Seconds, increases when no
			far end errors or defects are detected
			-----------------------------
			ommp401 InterfaceNumber:
			1 to 4 - CLIENT-1 to CLIENT-4
			-----------------------------
			Values:
			eg: 1234
			-----------------------------"
	::= { ommp401PerformanceEntry 368 }

	ommp401LineOduTcm1FarEndErrorSeconds OBJECT-TYPE
		SYNTAX  DisplayString
		MAX-ACCESS  read-only
		STATUS  current
		DESCRIPTION
			"For port configured with OTU4/OTUC4 traffic,
			TCM1 Far End Error Seconds increases on detection of
			defects like BDI and BEI at path monitoring level
			-----------------------------
			ommp401 InterfaceNumber:
			1 to 4 - CLIENT-1 to CLIENT-4
			-----------------------------
			Values:
			eg: 1234
			-----------------------------"
	::= { ommp401PerformanceEntry 369 }

	ommp401LineOduTcm1FarEndBackgroundBlockErrors OBJECT-TYPE
		SYNTAX  DisplayString
		MAX-ACCESS  read-only
		STATUS  current
		DESCRIPTION
			"For port configured with OTU4/OTUC4 traffic,
			TCM1 Far End Background Block Errors increases when
			BEI errors are less than 15% Errored Blocks in
			incoming OTU signal.
			-----------------------------
			ommp401 InterfaceNumber:
			1 to 4 - CLIENT-1 to CLIENT-4
			-----------------------------
			Values:
			eg: 1234
			-----------------------------"
	::= { ommp401PerformanceEntry 370 }

	ommp401LineOduTcm1FarEndSevereErrorSeconds OBJECT-TYPE
		SYNTAX  DisplayString
		MAX-ACCESS  read-only
		STATUS  current
		DESCRIPTION
			"For port configured with OTU4/OTUC4 traffic,
			TCM1 Far End Severe Error Seconds increases on defects
			like BDI are detected and when BEI errors are more than
			15% Errored Blocks in incoming OTU signal.
			-----------------------------
			ommp401 InterfaceNumber:
			1 to 4 - CLIENT-1 to CLIENT-4
			-----------------------------
			Values:
			eg: 1234
			-----------------------------"
	::= { ommp401PerformanceEntry 371 }

	ommp401LineOduTcm1FarEndUnavailableSeconds OBJECT-TYPE
		SYNTAX  DisplayString
		MAX-ACCESS  read-only
		STATUS  current
		DESCRIPTION
			"For port configured with OTU4/OTUC4 traffic,
			TCM1 Far End Unavailable Seconds increases, when 10
			consecutive OTU Far End Error seconds are detected
			-----------------------------
			ommp401 InterfaceNumber:
			1 to 4 - CLIENT-1 to CLIENT-4
			-----------------------------
			Values:
			eg: 1234
			-----------------------------"
	::= { ommp401PerformanceEntry 372 }

	ommp401LineOduTcm1FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 373 }

	ommp401LineOduTcm1FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 374 }

	ommp401LineOduTcm1FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 375 }

	ommp401LineOduTcm1FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 376 }

	ommp401LineOduTcm1FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 377 }

	ommp401LineOduTcm1FarEndBackgroundBlockErrorRatio OBJECT-TYPE
		SYNTAX  DisplayString
		MAX-ACCESS  read-only
		STATUS  current
		DESCRIPTION
			"For port configured with OTU4/OTUC4 traffic,
			gives TCM1 Far End Background Block Error Ratio i.e.
			the ratio of Far End BBE in available time to total
			seconds	in available time during a fixed measurement
			interval.
			-----------------------------
			ommp401 InterfaceNumber:
			1 to 4 - CLIENT-1 to CLIENT-4
			-----------------------------
			Values:
			eg: 1e-3
			-----------------------------"
	::= { ommp401PerformanceEntry 378 }

	ommp401LineOduTcm1FarEndSevereErrorSecondsErrorRatio OBJECT-TYPE
		SYNTAX  DisplayString
		MAX-ACCESS  read-only
		STATUS  current
		DESCRIPTION
			"For port configured with OTU4/OTUC4 traffic,
			gives TCM1 Far End Severe Error Seconds Error Ratio i.e.
			The ratio of Far End SES in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 379 } 

	ommp401LineOduTcm2ErrorFreeSeconds OBJECT-TYPE
		SYNTAX  DisplayString
		MAX-ACCESS  read-only
		STATUS  current
		DESCRIPTION
			"For port configured with OTU4/OTUC4 traffic,
			TCM2 Error Free Seconds increases,
			when no BIP errors or defects are detected at the
			path monitoring level
			-----------------------------
			ommp401 InterfaceNumber:
			1 to 4 - CLIENT-1 to CLIENT-4
			-----------------------------
			Values:
			eg: 1234
			-----------------------------"
	::= { ommp401PerformanceEntry 380 }

	ommp401LineOduTcm2ErrorSeconds OBJECT-TYPE
		SYNTAX  DisplayString
		MAX-ACCESS  read-only
		STATUS  current
		DESCRIPTION
			"For port configured with OTU4/OTUC4 traffic,
			TCM2 Error Seconds increases on defects detected at the
			path monitoring level
			-----------------------------
			ommp401 InterfaceNumber:
			1 to 4 - CLIENT-1 to CLIENT-4
			-----------------------------
			Values:
			eg: 1234
			-----------------------------"
	::= { ommp401PerformanceEntry 381 }

	ommp401LineOduTcm2BackgroundBlockErrors OBJECT-TYPE
		SYNTAX  DisplayString
		MAX-ACCESS  read-only
		STATUS  current
		DESCRIPTION
			"For port configured with OTU4/OTUC4 traffic,
			TCM2 Background Block Errors increases on defects 
			detected and when BIP errors are less than 15% 
			Errored Blocks in incoming OTU signal.
			-----------------------------
			ommp401 InterfaceNumber:
			1 to 4 - CLIENT-1 to CLIENT-4
			-----------------------------
			Values:
			eg: 1234
			-----------------------------"
	::= { ommp401PerformanceEntry 382 }

	ommp401LineOduTcm2SevereErrorSeconds OBJECT-TYPE
		SYNTAX  DisplayString
		MAX-ACCESS  read-only
		STATUS  current
		DESCRIPTION
			"For port configured with OTU4/OTUC4 traffic,
			TCM2 Severe Error Seconds increases on defects detected
			and when BIP errors are more than 15% Errored Blocks
			in incoming OTU signal.
			-----------------------------
			ommp401 InterfaceNumber:
			1 to 4 - CLIENT-1 to CLIENT-4
			-----------------------------
			Values:
			eg: 1234
			-----------------------------"
	::= { ommp401PerformanceEntry 383 }

	ommp401LineOduTcm2UnavailableSeconds OBJECT-TYPE
		SYNTAX  DisplayString
		MAX-ACCESS  read-only
		STATUS  current
		DESCRIPTION
			"For port configured with OTU4/OTUC4 traffic,
			TCM2 Unavailable Seconds increases, when 10 consecutive
			Severe TCM2 Error seconds are detected
			-----------------------------
			ommp401 InterfaceNumber:
			1 to 4 - CLIENT-1 to CLIENT-4
			-----------------------------
			Values:
			eg: 1234
			-----------------------------"
	::= { ommp401PerformanceEntry 384 }

	ommp401LineOduTcm2ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 385 }

	ommp401LineOduTcm2ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 386 }

	ommp401LineOduTcm2ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 387 }

	ommp401LineOduTcm2NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 388 }

	ommp401LineOduTcm2PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 389 }

	ommp401LineOduTcm2BackgroundBlockErrorRatio OBJECT-TYPE
		SYNTAX  DisplayString
		MAX-ACCESS  read-only
		STATUS  current
		DESCRIPTION
			"For port configured with OTU4/OTUC4 traffic,
			gives TCM2 Background Block Error Ratio i.e.
			the ratio of BBE in available time to total seconds
			in available time during a fixed measurement interval.
			-----------------------------
			ommp401 InterfaceNumber:
			1 to 4 - CLIENT-1 to CLIENT-4
			-----------------------------
			Values:
			eg: 1e-3
			-----------------------------"
	::= { ommp401PerformanceEntry 390 }

	ommp401LineOduTcm2SevereErrorSecondsErrorRatio OBJECT-TYPE
		SYNTAX  DisplayString
		MAX-ACCESS  read-only
		STATUS  current
		DESCRIPTION
			"For port configured with OTU4/OTUC4 traffic,
			gives TCM2 Severe Error Seconds Error Ratio i.e.
			the ratio of SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 391 }

	ommp401LineOduTcm2FarEndErrorFreeSeconds OBJECT-TYPE
		SYNTAX  DisplayString
		MAX-ACCESS  read-only
		STATUS  current
		DESCRIPTION
			"For port configured with OTU4/OTUC4 traffic,
			TCM2 Far end Error Free Seconds, increases when no
			far end errors or defects are detected
			-----------------------------
			ommp401 InterfaceNumber:
			1 to 4 - CLIENT-1 to CLIENT-4
			-----------------------------
			Values:
			eg: 1234
			-----------------------------"
	::= { ommp401PerformanceEntry 392 }

	ommp401LineOduTcm2FarEndErrorSeconds OBJECT-TYPE
		SYNTAX  DisplayString
		MAX-ACCESS  read-only
		STATUS  current
		DESCRIPTION
			"For port configured with OTU4/OTUC4 traffic,
			TCM2 Far End Error Seconds increases on detection of
			defects like BDI and BEI at path monitoring level
			-----------------------------
			ommp401 InterfaceNumber:
			1 to 4 - CLIENT-1 to CLIENT-4
			-----------------------------
			Values:
			eg: 1234
			-----------------------------"
	::= { ommp401PerformanceEntry 393 }

	ommp401LineOduTcm2FarEndBackgroundBlockErrors OBJECT-TYPE
		SYNTAX  DisplayString
		MAX-ACCESS  read-only
		STATUS  current
		DESCRIPTION
			"For port configured with OTU4/OTUC4 traffic,
			TCM2 Far End Background Block Errors increases when
			BEI errors are less than 15% Errored Blocks in
			incoming OTU signal.
			-----------------------------
			ommp401 InterfaceNumber:
			1 to 4 - CLIENT-1 to CLIENT-4
			-----------------------------
			Values:
			eg: 1234
			-----------------------------"
	::= { ommp401PerformanceEntry 394 }

	ommp401LineOduTcm2FarEndSevereErrorSeconds OBJECT-TYPE
		SYNTAX  DisplayString
		MAX-ACCESS  read-only
		STATUS  current
		DESCRIPTION
			"For port configured with OTU4/OTUC4 traffic,
			TCM2 Far End Severe Error Seconds increases on defects
			like BDI are detected and when BEI errors are more than
			15% Errored Blocks in incoming OTU signal.
			-----------------------------
			ommp401 InterfaceNumber:
			1 to 4 - CLIENT-1 to CLIENT-4
			-----------------------------
			Values:
			eg: 1234
			-----------------------------"
	::= { ommp401PerformanceEntry 395 }

	ommp401LineOduTcm2FarEndUnavailableSeconds OBJECT-TYPE
		SYNTAX  DisplayString
		MAX-ACCESS  read-only
		STATUS  current
		DESCRIPTION
			"For port configured with OTU4/OTUC4 traffic,
			TCM2 Far End Unavailable Seconds increases, when 10
			consecutive OTU Far End Error seconds are detected
			-----------------------------
			ommp401 InterfaceNumber:
			1 to 4 - CLIENT-1 to CLIENT-4
			-----------------------------
			Values:
			eg: 1234
			-----------------------------"
	::= { ommp401PerformanceEntry 396 }

	ommp401LineOduTcm2FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 397 }

	ommp401LineOduTcm2FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 398 }

	ommp401LineOduTcm2FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 399 }

	ommp401LineOduTcm2FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 400 }

	ommp401LineOduTcm2FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 401 }

	ommp401LineOduTcm2FarEndBackgroundBlockErrorRatio OBJECT-TYPE
		SYNTAX  DisplayString
		MAX-ACCESS  read-only
		STATUS  current
		DESCRIPTION
			"For port configured with OTU4/OTUC4 traffic,
			gives TCM2 Far End Background Block Error Ratio i.e.
			the ratio of Far End BBE in available time to total
			seconds	in available time during a fixed measurement
			interval.
			-----------------------------
			ommp401 InterfaceNumber:
			1 to 4 - CLIENT-1 to CLIENT-4
			-----------------------------
			Values:
			eg: 1e-3
			-----------------------------"
	::= { ommp401PerformanceEntry 402 }

	ommp401LineOduTcm2FarEndSevereErrorSecondsErrorRatio OBJECT-TYPE
		SYNTAX  DisplayString
		MAX-ACCESS  read-only
		STATUS  current
		DESCRIPTION
			"For port configured with OTU4/OTUC4 traffic,
			gives TCM2 Far End Severe Error Seconds Error Ratio i.e.
			The ratio of Far End SES in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 403 }

	ommp401LineOduTcm3ErrorFreeSeconds OBJECT-TYPE
		SYNTAX  DisplayString
		MAX-ACCESS  read-only
		STATUS  current
		DESCRIPTION
			"For port configured with OTU4/OTUC4 traffic,
			TCM3 Error Free Seconds increases,
			when no BIP errors or defects are detected at the
			path monitoring level
			-----------------------------
			ommp401 InterfaceNumber:
			1 to 4 - CLIENT-1 to CLIENT-4
			-----------------------------
			Values:
			eg: 1234
			-----------------------------"
	::= { ommp401PerformanceEntry 404 }

	ommp401LineOduTcm3ErrorSeconds OBJECT-TYPE
		SYNTAX  DisplayString
		MAX-ACCESS  read-only
		STATUS  current
		DESCRIPTION
			"For port configured with OTU4/OTUC4 traffic,
			TCM3 Error Seconds increases on defects detected at the
			path monitoring level
			-----------------------------
			ommp401 InterfaceNumber:
			1 to 4 - CLIENT-1 to CLIENT-4
			-----------------------------
			Values:
			eg: 1234
			-----------------------------"
	::= { ommp401PerformanceEntry 405 }

	ommp401LineOduTcm3BackgroundBlockErrors OBJECT-TYPE
		SYNTAX  DisplayString
		MAX-ACCESS  read-only
		STATUS  current
		DESCRIPTION
			"For port configured with OTU4/OTUC4 traffic,
			TCM3 Background Block Errors increases on defects 
			detected and when BIP errors are less than 15% 
			Errored Blocks in incoming OTU signal.
			-----------------------------
			ommp401 InterfaceNumber:
			1 to 4 - CLIENT-1 to CLIENT-4
			-----------------------------
			Values:
			eg: 1234
			-----------------------------"
	::= { ommp401PerformanceEntry 406 }

	ommp401LineOduTcm3SevereErrorSeconds OBJECT-TYPE
		SYNTAX  DisplayString
		MAX-ACCESS  read-only
		STATUS  current
		DESCRIPTION
			"For port configured with OTU4/OTUC4 traffic,
			TCM3 Severe Error Seconds increases on defects detected
			and when BIP errors are more than 15% Errored Blocks
			in incoming OTU signal.
			-----------------------------
			ommp401 InterfaceNumber:
			1 to 4 - CLIENT-1 to CLIENT-4
			-----------------------------
			Values:
			eg: 1234
			-----------------------------"
	::= { ommp401PerformanceEntry 407 }

	ommp401LineOduTcm3UnavailableSeconds OBJECT-TYPE
		SYNTAX  DisplayString
		MAX-ACCESS  read-only
		STATUS  current
		DESCRIPTION
			"For port configured with OTU4/OTUC4 traffic,
			TCM3 Unavailable Seconds increases, when 10 consecutive
			Severe TCM3 Error seconds are detected
			-----------------------------
			ommp401 InterfaceNumber:
			1 to 4 - CLIENT-1 to CLIENT-4
			-----------------------------
			Values:
			eg: 1234
			-----------------------------"
	::= { ommp401PerformanceEntry 408 }

	ommp401LineOduTcm3ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 409 }

	ommp401LineOduTcm3ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 410 }

	ommp401LineOduTcm3ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 411 }

	ommp401LineOduTcm3NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 412 }

	ommp401LineOduTcm3PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 413 }

	ommp401LineOduTcm3BackgroundBlockErrorRatio OBJECT-TYPE
		SYNTAX  DisplayString
		MAX-ACCESS  read-only
		STATUS  current
		DESCRIPTION
			"For port configured with OTU4/OTUC4 traffic,
			gives TCM3 Background Block Error Ratio i.e.
			the ratio of BBE in available time to total seconds
			in available time during a fixed measurement interval.
			-----------------------------
			ommp401 InterfaceNumber:
			1 to 4 - CLIENT-1 to CLIENT-4
			-----------------------------
			Values:
			eg: 1e-3
			-----------------------------"
	::= { ommp401PerformanceEntry 414 }

	ommp401LineOduTcm3SevereErrorSecondsErrorRatio OBJECT-TYPE
		SYNTAX  DisplayString
		MAX-ACCESS  read-only
		STATUS  current
		DESCRIPTION
			"For port configured with OTU4/OTUC4 traffic,
			gives TCM3 Severe Error Seconds Error Ratio i.e.
			the ratio of SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 415 }

	ommp401LineOduTcm3FarEndErrorFreeSeconds OBJECT-TYPE
		SYNTAX  DisplayString
		MAX-ACCESS  read-only
		STATUS  current
		DESCRIPTION
			"For port configured with OTU4/OTUC4 traffic,
			TCM3 Far end Error Free Seconds, increases when no
			far end errors or defects are detected
			-----------------------------
			ommp401 InterfaceNumber:
			1 to 4 - CLIENT-1 to CLIENT-4
			-----------------------------
			Values:
			eg: 1234
			-----------------------------"
	::= { ommp401PerformanceEntry 416 }

	ommp401LineOduTcm3FarEndErrorSeconds OBJECT-TYPE
		SYNTAX  DisplayString
		MAX-ACCESS  read-only
		STATUS  current
		DESCRIPTION
			"For port configured with OTU4/OTUC4 traffic,
			TCM3 Far End Error Seconds increases on detection of
			defects like BDI and BEI at path monitoring level
			-----------------------------
			ommp401 InterfaceNumber:
			1 to 4 - CLIENT-1 to CLIENT-4
			-----------------------------
			Values:
			eg: 1234
			-----------------------------"
	::= { ommp401PerformanceEntry 417 }

	ommp401LineOduTcm3FarEndBackgroundBlockErrors OBJECT-TYPE
		SYNTAX  DisplayString
		MAX-ACCESS  read-only
		STATUS  current
		DESCRIPTION
			"For port configured with OTU4/OTUC4 traffic,
			TCM3 Far End Background Block Errors increases when
			BEI errors are less than 15% Errored Blocks in
			incoming OTU signal.
			-----------------------------
			ommp401 InterfaceNumber:
			1 to 4 - CLIENT-1 to CLIENT-4
			-----------------------------
			Values:
			eg: 1234
			-----------------------------"
	::= { ommp401PerformanceEntry 418 }

	ommp401LineOduTcm3FarEndSevereErrorSeconds OBJECT-TYPE
		SYNTAX  DisplayString
		MAX-ACCESS  read-only
		STATUS  current
		DESCRIPTION
			"For port configured with OTU4/OTUC4 traffic,
			TCM3 Far End Severe Error Seconds increases on defects
			like BDI are detected and when BEI errors are more than
			15% Errored Blocks in incoming OTU signal.
			-----------------------------
			ommp401 InterfaceNumber:
			1 to 4 - CLIENT-1 to CLIENT-4
			-----------------------------
			Values:
			eg: 1234
			-----------------------------"
	::= { ommp401PerformanceEntry 419 }

	ommp401LineOduTcm3FarEndUnavailableSeconds OBJECT-TYPE
		SYNTAX  DisplayString
		MAX-ACCESS  read-only
		STATUS  current
		DESCRIPTION
			"For port configured with OTU4/OTUC4 traffic,
			TCM3 Far End Unavailable Seconds increases, when 10
			consecutive OTU Far End Error seconds are detected
			-----------------------------
			ommp401 InterfaceNumber:
			1 to 4 - CLIENT-1 to CLIENT-4
			-----------------------------
			Values:
			eg: 1234
			-----------------------------"
	::= { ommp401PerformanceEntry 420 }

	ommp401LineOduTcm3FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 421 }

	ommp401LineOduTcm3FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 422 }

	ommp401LineOduTcm3FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 423 }

	ommp401LineOduTcm3FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 424 }

	ommp401LineOduTcm3FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 425 }

	ommp401LineOduTcm3FarEndBackgroundBlockErrorRatio OBJECT-TYPE
		SYNTAX  DisplayString
		MAX-ACCESS  read-only
		STATUS  current
		DESCRIPTION
			"For port configured with OTU4/OTUC4 traffic,
			gives TCM3 Far End Background Block Error Ratio i.e.
			the ratio of Far End BBE in available time to total
			seconds	in available time during a fixed measurement
			interval.
			-----------------------------
			ommp401 InterfaceNumber:
			1 to 4 - CLIENT-1 to CLIENT-4
			-----------------------------
			Values:
			eg: 1e-3
			-----------------------------"
	::= { ommp401PerformanceEntry 426 }

	ommp401LineOduTcm3FarEndSevereErrorSecondsErrorRatio OBJECT-TYPE
		SYNTAX  DisplayString
		MAX-ACCESS  read-only
		STATUS  current
		DESCRIPTION
			"For port configured with OTU4/OTUC4 traffic,
			gives TCM3 Far End Severe Error Seconds Error Ratio i.e.
			The ratio of Far End SES in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 427 }

	ommp401LineOduTcm4ErrorFreeSeconds OBJECT-TYPE
		SYNTAX  DisplayString
		MAX-ACCESS  read-only
		STATUS  current
		DESCRIPTION
			"For port configured with OTU4/OTUC4 traffic,
			TCM4 Error Free Seconds increases,
			when no BIP errors or defects are detected at the
			path monitoring level
			-----------------------------
			ommp401 InterfaceNumber:
			1 to 4 - CLIENT-1 to CLIENT-4
			-----------------------------
			Values:
			eg: 1234
			-----------------------------"
	::= { ommp401PerformanceEntry 428 }

	ommp401LineOduTcm4ErrorSeconds OBJECT-TYPE
		SYNTAX  DisplayString
		MAX-ACCESS  read-only
		STATUS  current
		DESCRIPTION
			"For port configured with OTU4/OTUC4 traffic,
			TCM4 Error Seconds increases on defects detected at the
			path monitoring level
			-----------------------------
			ommp401 InterfaceNumber:
			1 to 4 - CLIENT-1 to CLIENT-4
			-----------------------------
			Values:
			eg: 1234
			-----------------------------"
	::= { ommp401PerformanceEntry 429 }

	ommp401LineOduTcm4BackgroundBlockErrors OBJECT-TYPE
		SYNTAX  DisplayString
		MAX-ACCESS  read-only
		STATUS  current
		DESCRIPTION
			"For port configured with OTU4/OTUC4 traffic,
			TCM4 Background Block Errors increases on defects 
			detected and when BIP errors are less than 15% 
			Errored Blocks in incoming OTU signal.
			-----------------------------
			ommp401 InterfaceNumber:
			1 to 4 - CLIENT-1 to CLIENT-4
			-----------------------------
			Values:
			eg: 1234
			-----------------------------"
	::= { ommp401PerformanceEntry 430 }

	ommp401LineOduTcm4SevereErrorSeconds OBJECT-TYPE
		SYNTAX  DisplayString
		MAX-ACCESS  read-only
		STATUS  current
		DESCRIPTION
			"For port configured with OTU4/OTUC4 traffic,
			TCM4 Severe Error Seconds increases on defects detected
			and when BIP errors are more than 15% Errored Blocks
			in incoming OTU signal.
			-----------------------------
			ommp401 InterfaceNumber:
			1 to 4 - CLIENT-1 to CLIENT-4
			-----------------------------
			Values:
			eg: 1234
			-----------------------------"
	::= { ommp401PerformanceEntry 431 }

	ommp401LineOduTcm4UnavailableSeconds OBJECT-TYPE
		SYNTAX  DisplayString
		MAX-ACCESS  read-only
		STATUS  current
		DESCRIPTION
			"For port configured with OTU4/OTUC4 traffic,
			TCM4 Unavailable Seconds increases, when 10 consecutive
			Severe TCM4 Error seconds are detected
			-----------------------------
			ommp401 InterfaceNumber:
			1 to 4 - CLIENT-1 to CLIENT-4
			-----------------------------
			Values:
			eg: 1234
			-----------------------------"
	::= { ommp401PerformanceEntry 432 }

	ommp401LineOduTcm4ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 433 }

	ommp401LineOduTcm4ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 434 }

	ommp401LineOduTcm4ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 435 }

	ommp401LineOduTcm4NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 436 }

	ommp401LineOduTcm4PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 437 }

	ommp401LineOduTcm4BackgroundBlockErrorRatio OBJECT-TYPE
		SYNTAX  DisplayString
		MAX-ACCESS  read-only
		STATUS  current
		DESCRIPTION
			"For port configured with OTU4/OTUC4 traffic,
			gives TCM4 Background Block Error Ratio i.e.
			the ratio of BBE in available time to total seconds
			in available time during a fixed measurement interval.
			-----------------------------
			ommp401 InterfaceNumber:
			1 to 4 - CLIENT-1 to CLIENT-4
			-----------------------------
			Values:
			eg: 1e-3
			-----------------------------"
	::= { ommp401PerformanceEntry 438 }

	ommp401LineOduTcm4SevereErrorSecondsErrorRatio OBJECT-TYPE
		SYNTAX  DisplayString
		MAX-ACCESS  read-only
		STATUS  current
		DESCRIPTION
			"For port configured with OTU4/OTUC4 traffic,
			gives TCM4 Severe Error Seconds Error Ratio i.e.
			the ratio of SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 439 }

	ommp401LineOduTcm4FarEndErrorFreeSeconds OBJECT-TYPE
		SYNTAX  DisplayString
		MAX-ACCESS  read-only
		STATUS  current
		DESCRIPTION
			"For port configured with OTU4/OTUC4 traffic,
			TCM4 Far end Error Free Seconds, increases when no
			far end errors or defects are detected
			-----------------------------
			ommp401 InterfaceNumber:
			1 to 4 - CLIENT-1 to CLIENT-4
			-----------------------------
			Values:
			eg: 1234
			-----------------------------"
	::= { ommp401PerformanceEntry 440 }

	ommp401LineOduTcm4FarEndErrorSeconds OBJECT-TYPE
		SYNTAX  DisplayString
		MAX-ACCESS  read-only
		STATUS  current
		DESCRIPTION
			"For port configured with OTU4/OTUC4 traffic,
			TCM4 Far End Error Seconds increases on detection of
			defects like BDI and BEI at path monitoring level
			-----------------------------
			ommp401 InterfaceNumber:
			1 to 4 - CLIENT-1 to CLIENT-4
			-----------------------------
			Values:
			eg: 1234
			-----------------------------"
	::= { ommp401PerformanceEntry 441 }

	ommp401LineOduTcm4FarEndBackgroundBlockErrors OBJECT-TYPE
		SYNTAX  DisplayString
		MAX-ACCESS  read-only
		STATUS  current
		DESCRIPTION
			"For port configured with OTU4/OTUC4 traffic,
			TCM4 Far End Background Block Errors increases when
			BEI errors are less than 15% Errored Blocks in
			incoming OTU signal.
			-----------------------------
			ommp401 InterfaceNumber:
			1 to 4 - CLIENT-1 to CLIENT-4
			-----------------------------
			Values:
			eg: 1234
			-----------------------------"
	::= { ommp401PerformanceEntry 442 }

	ommp401LineOduTcm4FarEndSevereErrorSeconds OBJECT-TYPE
		SYNTAX  DisplayString
		MAX-ACCESS  read-only
		STATUS  current
		DESCRIPTION
			"For port configured with OTU4/OTUC4 traffic,
			TCM4 Far End Severe Error Seconds increases on defects
			like BDI are detected and when BEI errors are more than
			15% Errored Blocks in incoming OTU signal.
			-----------------------------
			ommp401 InterfaceNumber:
			1 to 4 - CLIENT-1 to CLIENT-4
			-----------------------------
			Values:
			eg: 1234
			-----------------------------"
	::= { ommp401PerformanceEntry 443 }

	ommp401LineOduTcm4FarEndUnavailableSeconds OBJECT-TYPE
		SYNTAX  DisplayString
		MAX-ACCESS  read-only
		STATUS  current
		DESCRIPTION
			"For port configured with OTU4/OTUC4 traffic,
			TCM4 Far End Unavailable Seconds increases, when 10
			consecutive OTU Far End Error seconds are detected
			-----------------------------
			ommp401 InterfaceNumber:
			1 to 4 - CLIENT-1 to CLIENT-4
			-----------------------------
			Values:
			eg: 1234
			-----------------------------"
	::= { ommp401PerformanceEntry 444 }

	ommp401LineOduTcm4FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 445 }

	ommp401LineOduTcm4FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 446 }

	ommp401LineOduTcm4FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 447 }

	ommp401LineOduTcm4FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 448 }

	ommp401LineOduTcm4FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 449 }

	ommp401LineOduTcm4FarEndBackgroundBlockErrorRatio OBJECT-TYPE
		SYNTAX  DisplayString
		MAX-ACCESS  read-only
		STATUS  current
		DESCRIPTION
			"For port configured with OTU4/OTUC4 traffic,
			gives TCM4 Far End Background Block Error Ratio i.e.
			the ratio of Far End BBE in available time to total
			seconds	in available time during a fixed measurement
			interval.
			-----------------------------
			ommp401 InterfaceNumber:
			1 to 4 - CLIENT-1 to CLIENT-4
			-----------------------------
			Values:
			eg: 1e-3
			-----------------------------"
	::= { ommp401PerformanceEntry 450 }

	ommp401LineOduTcm4FarEndSevereErrorSecondsErrorRatio OBJECT-TYPE
		SYNTAX  DisplayString
		MAX-ACCESS  read-only
		STATUS  current
		DESCRIPTION
			"For port configured with OTU4/OTUC4 traffic,
			gives TCM4 Far End Severe Error Seconds Error Ratio i.e.
			The ratio of Far End SES in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 451 }

	ommp401LineOduTcm5ErrorFreeSeconds OBJECT-TYPE
		SYNTAX  DisplayString
		MAX-ACCESS  read-only
		STATUS  current
		DESCRIPTION
			"For port configured with OTU4/OTUC4 traffic,
			TCM5 Error Free Seconds increases,
			when no BIP errors or defects are detected at the
			path monitoring level
			-----------------------------
			ommp401 InterfaceNumber:
			1 to 4 - CLIENT-1 to CLIENT-4
			-----------------------------
			Values:
			eg: 1234
			-----------------------------"
	::= { ommp401PerformanceEntry 452 }

	ommp401LineOduTcm5ErrorSeconds OBJECT-TYPE
		SYNTAX  DisplayString
		MAX-ACCESS  read-only
		STATUS  current
		DESCRIPTION
			"For port configured with OTU4/OTUC4 traffic,
			TCM5 Error Seconds increases on defects detected at the
			path monitoring level
			-----------------------------
			ommp401 InterfaceNumber:
			1 to 4 - CLIENT-1 to CLIENT-4
			-----------------------------
			Values:
			eg: 1234
			-----------------------------"
	::= { ommp401PerformanceEntry 453 }

	ommp401LineOduTcm5BackgroundBlockErrors OBJECT-TYPE
		SYNTAX  DisplayString
		MAX-ACCESS  read-only
		STATUS  current
		DESCRIPTION
			"For port configured with OTU4/OTUC4 traffic,
			TCM5 Background Block Errors increases on defects 
			detected and when BIP errors are less than 15% 
			Errored Blocks in incoming OTU signal.
			-----------------------------
			ommp401 InterfaceNumber:
			1 to 4 - CLIENT-1 to CLIENT-4
			-----------------------------
			Values:
			eg: 1234
			-----------------------------"
	::= { ommp401PerformanceEntry 454 }

	ommp401LineOduTcm5SevereErrorSeconds OBJECT-TYPE
		SYNTAX  DisplayString
		MAX-ACCESS  read-only
		STATUS  current
		DESCRIPTION
			"For port configured with OTU4/OTUC4 traffic,
			TCM5 Severe Error Seconds increases on defects detected
			and when BIP errors are more than 15% Errored Blocks
			in incoming OTU signal.
			-----------------------------
			ommp401 InterfaceNumber:
			1 to 4 - CLIENT-1 to CLIENT-4
			-----------------------------
			Values:
			eg: 1234
			-----------------------------"
	::= { ommp401PerformanceEntry 455 }

	ommp401LineOduTcm5UnavailableSeconds OBJECT-TYPE
		SYNTAX  DisplayString
		MAX-ACCESS  read-only
		STATUS  current
		DESCRIPTION
			"For port configured with OTU4/OTUC4 traffic,
			TCM5 Unavailable Seconds increases, when 10 consecutive
			Severe TCM5 Error seconds are detected
			-----------------------------
			ommp401 InterfaceNumber:
			1 to 4 - CLIENT-1 to CLIENT-4
			-----------------------------
			Values:
			eg: 1234
			-----------------------------"
	::= { ommp401PerformanceEntry 456 }

	ommp401LineOduTcm5ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 457 }

	ommp401LineOduTcm5ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 458 }

	ommp401LineOduTcm5ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 459 }

	ommp401LineOduTcm5NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 460 }

	ommp401LineOduTcm5PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 461 }

	ommp401LineOduTcm5BackgroundBlockErrorRatio OBJECT-TYPE
		SYNTAX  DisplayString
		MAX-ACCESS  read-only
		STATUS  current
		DESCRIPTION
			"For port configured with OTU4/OTUC4 traffic,
			gives TCM5 Background Block Error Ratio i.e.
			the ratio of BBE in available time to total seconds
			in available time during a fixed measurement interval.
			-----------------------------
			ommp401 InterfaceNumber:
			1 to 4 - CLIENT-1 to CLIENT-4
			-----------------------------
			Values:
			eg: 1e-3
			-----------------------------"
	::= { ommp401PerformanceEntry 462 }

	ommp401LineOduTcm5SevereErrorSecondsErrorRatio OBJECT-TYPE
		SYNTAX  DisplayString
		MAX-ACCESS  read-only
		STATUS  current
		DESCRIPTION
			"For port configured with OTU4/OTUC4 traffic,
			gives TCM5 Severe Error Seconds Error Ratio i.e.
			the ratio of SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 463 }

	ommp401LineOduTcm5FarEndErrorFreeSeconds OBJECT-TYPE
		SYNTAX  DisplayString
		MAX-ACCESS  read-only
		STATUS  current
		DESCRIPTION
			"For port configured with OTU4/OTUC4 traffic,
			TCM5 Far end Error Free Seconds, increases when no
			far end errors or defects are detected
			-----------------------------
			ommp401 InterfaceNumber:
			1 to 4 - CLIENT-1 to CLIENT-4
			-----------------------------
			Values:
			eg: 1234
			-----------------------------"
	::= { ommp401PerformanceEntry 464 }

	ommp401LineOduTcm5FarEndErrorSeconds OBJECT-TYPE
		SYNTAX  DisplayString
		MAX-ACCESS  read-only
		STATUS  current
		DESCRIPTION
			"For port configured with OTU4/OTUC4 traffic,
			TCM5 Far End Error Seconds increases on detection of
			defects like BDI and BEI at path monitoring level
			-----------------------------
			ommp401 InterfaceNumber:
			1 to 4 - CLIENT-1 to CLIENT-4
			-----------------------------
			Values:
			eg: 1234
			-----------------------------"
	::= { ommp401PerformanceEntry 465 }

	ommp401LineOduTcm5FarEndBackgroundBlockErrors OBJECT-TYPE
		SYNTAX  DisplayString
		MAX-ACCESS  read-only
		STATUS  current
		DESCRIPTION
			"For port configured with OTU4/OTUC4 traffic,
			TCM5 Far End Background Block Errors increases when
			BEI errors are less than 15% Errored Blocks in
			incoming OTU signal.
			-----------------------------
			ommp401 InterfaceNumber:
			1 to 4 - CLIENT-1 to CLIENT-4
			-----------------------------
			Values:
			eg: 1234
			-----------------------------"
	::= { ommp401PerformanceEntry 466 }

	ommp401LineOduTcm5FarEndSevereErrorSeconds OBJECT-TYPE
		SYNTAX  DisplayString
		MAX-ACCESS  read-only
		STATUS  current
		DESCRIPTION
			"For port configured with OTU4/OTUC4 traffic,
			TCM5 Far End Severe Error Seconds increases on defects
			like BDI are detected and when BEI errors are more than
			15% Errored Blocks in incoming OTU signal.
			-----------------------------
			ommp401 InterfaceNumber:
			1 to 4 - CLIENT-1 to CLIENT-4
			-----------------------------
			Values:
			eg: 1234
			-----------------------------"
	::= { ommp401PerformanceEntry 467 }

	ommp401LineOduTcm5FarEndUnavailableSeconds OBJECT-TYPE
		SYNTAX  DisplayString
		MAX-ACCESS  read-only
		STATUS  current
		DESCRIPTION
			"For port configured with OTU4/OTUC4 traffic,
			TCM5 Far End Unavailable Seconds increases, when 10
			consecutive OTU Far End Error seconds are detected
			-----------------------------
			ommp401 InterfaceNumber:
			1 to 4 - CLIENT-1 to CLIENT-4
			-----------------------------
			Values:
			eg: 1234
			-----------------------------"
	::= { ommp401PerformanceEntry 468 }

	ommp401LineOduTcm5FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 469 }

	ommp401LineOduTcm5FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 470 }

	ommp401LineOduTcm5FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 471 }

	ommp401LineOduTcm5FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 472 }

	ommp401LineOduTcm5FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 473 }

	ommp401LineOduTcm5FarEndBackgroundBlockErrorRatio OBJECT-TYPE
		SYNTAX  DisplayString
		MAX-ACCESS  read-only
		STATUS  current
		DESCRIPTION
			"For port configured with OTU4/OTUC4 traffic,
			gives TCM5 Far End Background Block Error Ratio i.e.
			the ratio of Far End BBE in available time to total
			seconds	in available time during a fixed measurement
			interval.
			-----------------------------
			ommp401 InterfaceNumber:
			1 to 4 - CLIENT-1 to CLIENT-4
			-----------------------------
			Values:
			eg: 1e-3
			-----------------------------"
	::= { ommp401PerformanceEntry 474 }

	ommp401LineOduTcm5FarEndSevereErrorSecondsErrorRatio OBJECT-TYPE
		SYNTAX  DisplayString
		MAX-ACCESS  read-only
		STATUS  current
		DESCRIPTION
			"For port configured with OTU4/OTUC4 traffic,
			gives TCM5 Far End Severe Error Seconds Error Ratio i.e.
			The ratio of Far End SES in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 475 }

	ommp401LineOduTcm6ErrorFreeSeconds OBJECT-TYPE
		SYNTAX  DisplayString
		MAX-ACCESS  read-only
		STATUS  current
		DESCRIPTION
			"For port configured with OTU4/OTUC4 traffic,
			TCM6 Error Free Seconds increases,
			when no BIP errors or defects are detected at the
			path monitoring level
			-----------------------------
			ommp401 InterfaceNumber:
			1 to 4 - CLIENT-1 to CLIENT-4
			-----------------------------
			Values:
			eg: 1234
			-----------------------------"
	::= { ommp401PerformanceEntry 476 }

	ommp401LineOduTcm6ErrorSeconds OBJECT-TYPE
		SYNTAX  DisplayString
		MAX-ACCESS  read-only
		STATUS  current
		DESCRIPTION
			"For port configured with OTU4/OTUC4 traffic,
			TCM6 Error Seconds increases on defects detected at the
			path monitoring level
			-----------------------------
			ommp401 InterfaceNumber:
			1 to 4 - CLIENT-1 to CLIENT-4
			-----------------------------
			Values:
			eg: 1234
			-----------------------------"
	::= { ommp401PerformanceEntry 477 }

	ommp401LineOduTcm6BackgroundBlockErrors OBJECT-TYPE
		SYNTAX  DisplayString
		MAX-ACCESS  read-only
		STATUS  current
		DESCRIPTION
			"For port configured with OTU4/OTUC4 traffic,
			TCM6 Background Block Errors increases on defects 
			detected and when BIP errors are less than 15% 
			Errored Blocks in incoming OTU signal.
			-----------------------------
			ommp401 InterfaceNumber:
			1 to 4 - CLIENT-1 to CLIENT-4
			-----------------------------
			Values:
			eg: 1234
			-----------------------------"
	::= { ommp401PerformanceEntry 478 }

	ommp401LineOduTcm6SevereErrorSeconds OBJECT-TYPE
		SYNTAX  DisplayString
		MAX-ACCESS  read-only
		STATUS  current
		DESCRIPTION
			"For port configured with OTU4/OTUC4 traffic,
			TCM6 Severe Error Seconds increases on defects detected
			and when BIP errors are more than 15% Errored Blocks
			in incoming OTU signal.
			-----------------------------
			ommp401 InterfaceNumber:
			1 to 4 - CLIENT-1 to CLIENT-4
			-----------------------------
			Values:
			eg: 1234
			-----------------------------"
	::= { ommp401PerformanceEntry 479 }

	ommp401LineOduTcm6UnavailableSeconds OBJECT-TYPE
		SYNTAX  DisplayString
		MAX-ACCESS  read-only
		STATUS  current
		DESCRIPTION
			"For port configured with OTU4/OTUC4 traffic,
			TCM6 Unavailable Seconds increases, when 10 consecutive
			Severe TCM6 Error seconds are detected
			-----------------------------
			ommp401 InterfaceNumber:
			1 to 4 - CLIENT-1 to CLIENT-4
			-----------------------------
			Values:
			eg: 1234
			-----------------------------"
	::= { ommp401PerformanceEntry 480 }

	ommp401LineOduTcm6ErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 481 }

	ommp401LineOduTcm6ErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 482 }

	ommp401LineOduTcm6ConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 483 }

	ommp401LineOduTcm6NonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 484 }

	ommp401LineOduTcm6PathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 485 }

	ommp401LineOduTcm6BackgroundBlockErrorRatio OBJECT-TYPE
		SYNTAX  DisplayString
		MAX-ACCESS  read-only
		STATUS  current
		DESCRIPTION
			"For port configured with OTU4/OTUC4 traffic,
			gives TCM6 Background Block Error Ratio i.e.
			the ratio of BBE in available time to total seconds
			in available time during a fixed measurement interval.
			-----------------------------
			ommp401 InterfaceNumber:
			1 to 4 - CLIENT-1 to CLIENT-4
			-----------------------------
			Values:
			eg: 1e-3
			-----------------------------"
	::= { ommp401PerformanceEntry 486 }

	ommp401LineOduTcm6SevereErrorSecondsErrorRatio OBJECT-TYPE
		SYNTAX  DisplayString
		MAX-ACCESS  read-only
		STATUS  current
		DESCRIPTION
			"For port configured with OTU4/OTUC4 traffic,
			gives TCM6 Severe Error Seconds Error Ratio i.e.
			the ratio of SES in available time to total seconds
			in available time during a fixed measurement interval.
			-----------------------------
			ommp401 InterfaceNumber:
			1 to 4 - CLIENT-1 to CLIENT-4
			-----------------------------
			Values:
			eg: 1e-3
			-----------------------------"
	::= { ommp401PerformanceEntry 487 }

	ommp401LineOduTcm6FarEndErrorFreeSeconds OBJECT-TYPE
		SYNTAX  DisplayString
		MAX-ACCESS  read-only
		STATUS  current
		DESCRIPTION
			"For port configured with OTU4/OTUC4 traffic,
			TCM6 Far end Error Free Seconds, increases when no
			far end errors or defects are detected
			-----------------------------
			ommp401 InterfaceNumber:
			1 to 4 - CLIENT-1 to CLIENT-4
			-----------------------------
			Values:
			eg: 1234
			-----------------------------"
	::= { ommp401PerformanceEntry 488 }

	ommp401LineOduTcm6FarEndErrorSeconds OBJECT-TYPE
		SYNTAX  DisplayString
		MAX-ACCESS  read-only
		STATUS  current
		DESCRIPTION
			"For port configured with OTU4/OTUC4 traffic,
			TCM6 Far End Error Seconds increases on detection of
			defects like BDI and BEI at path monitoring level
			-----------------------------
			ommp401 InterfaceNumber:
			1 to 4 - CLIENT-1 to CLIENT-4
			-----------------------------
			Values:
			eg: 1234
			-----------------------------"
	::= { ommp401PerformanceEntry 489 }

	ommp401LineOduTcm6FarEndBackgroundBlockErrors OBJECT-TYPE
		SYNTAX  DisplayString
		MAX-ACCESS  read-only
		STATUS  current
		DESCRIPTION
			"For port configured with OTU4/OTUC4 traffic,
			TCM6 Far End Background Block Errors increases when
			BEI errors are less than 15% Errored Blocks in
			incoming OTU signal.
			-----------------------------
			ommp401 InterfaceNumber:
			1 to 4 - CLIENT-1 to CLIENT-4
			-----------------------------
			Values:
			eg: 1234
			-----------------------------"
	::= { ommp401PerformanceEntry 490 }

	ommp401LineOduTcm6FarEndSevereErrorSeconds OBJECT-TYPE
		SYNTAX  DisplayString
		MAX-ACCESS  read-only
		STATUS  current
		DESCRIPTION
			"For port configured with OTU4/OTUC4 traffic,
			TCM6 Far End Severe Error Seconds increases on defects
			like BDI are detected and when BEI errors are more than
			15% Errored Blocks in incoming OTU signal.
			-----------------------------
			ommp401 InterfaceNumber:
			1 to 4 - CLIENT-1 to CLIENT-4
			-----------------------------
			Values:
			eg: 1234
			-----------------------------"
	::= { ommp401PerformanceEntry 491 }

	ommp401LineOduTcm6FarEndUnavailableSeconds OBJECT-TYPE
		SYNTAX  DisplayString
		MAX-ACCESS  read-only
		STATUS  current
		DESCRIPTION
			"For port configured with OTU4/OTUC4 traffic,
			TCM6 Far End Unavailable Seconds increases, when 10
			consecutive OTU Far End Error seconds are detected
			-----------------------------
			ommp401 InterfaceNumber:
			1 to 4 - CLIENT-1 to CLIENT-4
			-----------------------------
			Values:
			eg: 1234
			-----------------------------"
	::= { ommp401PerformanceEntry 492 }

	ommp401LineOduTcm6FarEndErrorFreePeriod OBJECT-TYPE
		SYNTAX  DisplayString
		MAX-ACCESS  read-only
		STATUS  current
		DESCRIPTION
			"For port configured with OTU4/OTUC4 traffic,
			OTU Error Free Seconds increases when no BIP errors
			or defects are detected at the section monitoring level,
			The ratio of Error Free seconds in available time to total seconds
			in available time during a fixed measurement interval
			-----------------------------
			ommp401 InterfaceNumber:
			1 to 4 - CLIENT-1 to CLIENT-4
			-----------------------------
			Values:
			eg: 1234
			-----------------------------"
	::= { ommp401PerformanceEntry 493 }

	ommp401LineOduTcm6FarEndErroredPeriod OBJECT-TYPE
		SYNTAX  DisplayString
		MAX-ACCESS  read-only
		STATUS  current
		DESCRIPTION
			"For port configured with OTU4/OTUC4 traffic,
			The ratio of Errors in available time to total seconds
			in available time during a fixed measurement interval
			-----------------------------
			ommp401 InterfaceNumber:
			1 to 4 - CLIENT-1 to CLIENT-4
			-----------------------------
			Values:
			eg: 1234
			-----------------------------"
	::= { ommp401PerformanceEntry 494 }

	ommp401LineOduTcm6FarEndConsecutiveSevereErrorSecond OBJECT-TYPE
		SYNTAX  DisplayString
		MAX-ACCESS  read-only
		STATUS  current
		DESCRIPTION
			"For port configured with OTU4/OTUC4 traffic,
			The ratio of severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 495 }

	ommp401LineOduTcm6FarEndNonConsecutiveSevereErrorSecond OBJECT-TYPE
		SYNTAX  DisplayString
		MAX-ACCESS  read-only
		STATUS  current
		DESCRIPTION
			"For port configured with OTU4/OTUC4 traffic,
			The ratio of non severe Errors in available time to total seconds
			in available time during a fixed measurement interval
			-----------------------------
			ommp401 InterfaceNumber:
			1 to 4 - CLIENT-1 to CLIENT-4
			-----------------------------
			Values:
			eg: 1234
			-----------------------------"
	::= { ommp401PerformanceEntry 496 }

	ommp401LineOduTcm6FarEndPathAvailabilityStatus OBJECT-TYPE
		SYNTAX  DisplayString
		MAX-ACCESS  read-only
		STATUS  current
		DESCRIPTION
			"For port configured with OTU4/OTUC4 traffic,
			The ratio of no Errors in available time to total seconds
			in available time during a fixed measurement interval
			-----------------------------
			ommp401 InterfaceNumber:
			1 to 4 - CLIENT-1 to CLIENT-4
			-----------------------------
			Values:
			eg: 1234
			-----------------------------"
	::= { ommp401PerformanceEntry 497 }

	ommp401LineOduTcm6FarEndBackgroundBlockErrorRatio OBJECT-TYPE
		SYNTAX  DisplayString
		MAX-ACCESS  read-only
		STATUS  current
		DESCRIPTION
			"For port configured with OTU4/OTUC4 traffic,
			gives TCM6 Far End Background Block Error Ratio i.e.
			the ratio of Far End BBE in available time to total
			seconds	in available time during a fixed measurement
			interval.
			-----------------------------
			ommp401 InterfaceNumber:
			1 to 4 - CLIENT-1 to CLIENT-4
			-----------------------------
			Values:
			eg: 1e-3
			-----------------------------"
	::= { ommp401PerformanceEntry 498 }

	ommp401LineOduTcm6FarEndSevereErrorSecondsErrorRatio OBJECT-TYPE
		SYNTAX  DisplayString
		MAX-ACCESS  read-only
		STATUS  current
		DESCRIPTION
			"For port configured with OTU4/OTUC4 traffic,
			gives TCM6 Far End Severe Error Seconds Error Ratio i.e.
			The ratio of Far End SES in available time to total
			seconds in available time during a fixed measurement
			interval.
			-----------------------------
			ommp401 InterfaceNumber:
			1 to 4 - CLIENT-1 to CLIENT-4
			-----------------------------
			Values:
			eg: 1e-3
			-----------------------------"
	::= { ommp401PerformanceEntry 499 }

	ommp401PerformanceTableRowStatus OBJECT-TYPE
              SYNTAX      RowStatus
              MAX-ACCESS  read-write
              STATUS      current
              DESCRIPTION
			"*****************************
			This is MIB realted property,
			NOT to be considered as a card property
			*****************************"
              ::= { ommp401PerformanceEntry 500 }
              
--*****************************************************************************

--*****************************************************************************

	snmpCurrentNotificationsGroup NOTIFICATION-GROUP
		NOTIFICATIONS { 
					ommp401Cfp2InputPowerFailureAlarmTrap,
					ommp401Cfp2OutputPowerFailureAlarmTrap,
					ommp401Cfp2HighTemperatureAlarmTrap,
					ommp401Cfp2LowTemperatureAlarmTrap,
					ommp401Cfp2HighTemperatureWarningTrap,
					ommp401Cfp2LowTemperatureWarningTrap,
					ommp401Cfp2InputHighPowerAlarmTrap,
					ommp401Cfp2InputLowPowerAlarmTrap,
					ommp401Cfp2InputHighPowerWarningTrap,
					ommp401Cfp2InputLowPowerWarningTrap,
					ommp401Cfp2OutputHighPowerAlarmTrap,
					ommp401Cfp2OutputLowPowerAlarmTrap,
					ommp401Cfp2OutputHighPowerWarningTrap,
					ommp401Cfp2OutputLowPowerWarningTrap,
					ommp401Cfp2HighSupplyVoltageAlarmTrap,
					ommp401Cfp2LowSupplyVoltageAlarmTrap,
					ommp401Cfp2HighSupplyVoltageWarningTrap,
					ommp401Cfp2LowSupplyVoltageWarningTrap,
					ommp401Cfp2PresenceAbsenceNotificationTrap,
					ommp401Qsfp28InputPowerFailureAlarmTrap,
					ommp401Qsfp28OutputPowerFailureAlarmTrap,
					ommp401Qsfp28HighTemperatureAlarmTrap,
					ommp401Qsfp28LowTemperatureAlarmTrap,
					ommp401Qsfp28HighTemperatureWarningTrap,
					ommp401Qsfp28LowTemperatureWarningTrap,
					ommp401Qsfp28HighBiasCurrentAlarmTrap,
					ommp401Qsfp28LowBiasCurrentAlarmTrap,
					ommp401Qsfp28HighBiasCurrentWarningTrap,
					ommp401Qsfp28LowBiasCurrentWarningTrap,
					ommp401Qsfp28InputHighPowerAlarmTrap,
					ommp401Qsfp28InputLowPowerAlarmTrap,
					ommp401Qsfp28InputHighPowerWarningTrap,
					ommp401Qsfp28InputLowPowerWarningTrap,
					ommp401Qsfp28OutputHighPowerAlarmTrap,
					ommp401Qsfp28OutputLowPowerAlarmTrap,
					ommp401Qsfp28OutputHighPowerWarningTrap,
					ommp401Qsfp28OutputLowPowerWarningTrap,
					ommp401Qsfp28HighSupplyVoltageAlarmTrap,
					ommp401Qsfp28LowSupplyVoltageAlarmTrap,
					ommp401Qsfp28HighSupplyVoltageWarningTrap,
					ommp401Qsfp28LowSupplyVoltageWarningTrap,
					ommp401Qsfp28PresenceAbsenceNotificationTrap,
					ommp401OtuLossOfSignalAlarmTrap,
					ommp401OtuLossOfFrameAlarmTrap,
					ommp401OtuOutOfFrameAlarmTrap,
					ommp401OtuLossOfMultiFrameAlarmTrap,
					ommp401OtuOutOfMultiFrameAlarmTrap,
					ommp401OtuSignalFailAlarmTrap,
					ommp401OtuSignalDegradeAlarmTrap,
					ommp401OtuAlarmIndicationSignalAlarmTrap,
					ommp401OtuIncomingAlignmentErrorAlarmTrap,
					ommp401OtuTrailTraceIdentifierMismatchAlarmTrap,
					ommp401OtuBackwardIncomingAlignmentErrorAlarmTrap,
					ommp401OtuBackwardDefectIndicationAlarmTrap,
					ommp401OduSignalFailAlarmTrap,
					ommp401OduSignalDegradeAlarmTrap,
					ommp401OduAlarmIndicationSignalAlarmTrap,
					ommp401OduTrailTraceIdentifierMismatchAlarmTrap,
					ommp401OduLockedDefectAlarmTrap,
					ommp401OduOpenConnectionIndicationAlarmTrap,
					ommp401OduBackwardDefectIndicationAlarmTrap,
					ommp401OduTcm1BackwardDefectIndicationAlarmTrap,
					ommp401OduTcm2BackwardDefectIndicationAlarmTrap,
					ommp401OduTcm3BackwardDefectIndicationAlarmTrap,
					ommp401OduTcm4BackwardDefectIndicationAlarmTrap,
					ommp401OduTcm5BackwardDefectIndicationAlarmTrap,
					ommp401OduTcm6BackwardDefectIndicationAlarmTrap,
					ommp401OduTcm1BackwardIncomingAlignmentErrorAlarmTrap,
					ommp401OduTcm2BackwardIncomingAlignmentErrorAlarmTrap,
					ommp401OduTcm3BackwardIncomingAlignmentErrorAlarmTrap,
					ommp401OduTcm4BackwardIncomingAlignmentErrorAlarmTrap,
					ommp401OduTcm5BackwardIncomingAlignmentErrorAlarmTrap,
					ommp401OduTcm6BackwardIncomingAlignmentErrorAlarmTrap,
					ommp401OduTcm1LossOfTandemConnectionAlarmTrap,
					ommp401OduTcm2LossOfTandemConnectionAlarmTrap,
					ommp401OduTcm3LossOfTandemConnectionAlarmTrap,
					ommp401OduTcm4LossOfTandemConnectionAlarmTrap,
					ommp401OduTcm5LossOfTandemConnectionAlarmTrap,
					ommp401OduTcm6LossOfTandemConnectionAlarmTrap,
					ommp401OpuPayloadMismatchAlarmTrap,
					ommp401EthernetLossOfSignalAlarmTrap,
					ommp401EthernetIngressRemoteFaultAlarmTrap,
					ommp401EthernetIngressPcsErrorBlocksDetectedAlarmTrap,
					ommp401EthernetIngressPcsBipErrorsDetectedAlarmTrap,
					ommp401EthernetIngressOpuClientServerFailIndicationAlarmTrap,
					ommp401EthernetIngressLocalFaultAlarmTrap,
					ommp401EthernetIngressLossOfAlignmentAlarmTrap,
					ommp401EthernetIngressLossOfAlignmentMarkerLockAlarmTrap,
					ommp401EthernetIngressLossOfBlockLockAlarmTrap,
					ommp401EthernetEgressRemoteFaultAlarmTrap,
					ommp401EthernetEgressPcsErrorBlocksDetectedAlarmTrap,
					ommp401EthernetEgressPcsBipErrorsDetectedAlarmTrap,
					ommp401EthernetEgressHighBerAlarmTrap,
					ommp401EthernetEgressLocalFaultAlarmTrap,
					ommp401EthernetEgressLossOfAlignmentAlarmTrap,
					ommp401EthernetEgressLossOfAlignmentMarkerLockAlarmTrap,
					ommp401EthernetEgressLossOfBlockLockAlarmTrap,
					ommp401LineOtuLossOfSignalAlarmTrap,
					ommp401LineOtuLossOfFrameAlarmTrap,
					ommp401LineOtuOutOfFrameAlarmTrap,
					ommp401LineOtuLossOfMultiFrameAlarmTrap,
					ommp401LineOtuOutOfMultiFrameAlarmTrap,
					ommp401LineOtuSignalDegradeAlarmTrap,
					ommp401LineOtuAlarmIndicationSignalAlarmTrap,
					ommp401LineOtuIncomingAlignmentErrorAlarmTrap,
					ommp401LineOtuTrailTraceIdentifierMismatchAlarmTrap,
					ommp401LineOtuBackwardIncomingAlignmentErrorAlarmTrap,
					ommp401LineOtuBackwardDefectIndicationAlarmTrap,
					ommp401LineOduSignalDegradeAlarmTrap,
					ommp401LineOduAlarmIndicationSignalAlarmTrap,
					ommp401LineOduTrailTraceIdentifierMismatchAlarmTrap,
					ommp401LineOduLockedDefectAlarmTrap,
					ommp401LineOduOpenConnectionIndicationAlarmTrap,
					ommp401LineOduBackwardDefectIndicationAlarmTrap,
					ommp401LineOduTcm1BackwardDefectIndicationAlarmTrap,
					ommp401LineOduTcm2BackwardDefectIndicationAlarmTrap,
					ommp401LineOduTcm3BackwardDefectIndicationAlarmTrap,
					ommp401LineOduTcm4BackwardDefectIndicationAlarmTrap,
					ommp401LineOduTcm5BackwardDefectIndicationAlarmTrap,
					ommp401LineOduTcm6BackwardDefectIndicationAlarmTrap,
					ommp401LineOduTcm1BackwardIncomingAlignmentErrorAlarmTrap,
					ommp401LineOduTcm2BackwardIncomingAlignmentErrorAlarmTrap,
					ommp401LineOduTcm3BackwardIncomingAlignmentErrorAlarmTrap,
					ommp401LineOduTcm4BackwardIncomingAlignmentErrorAlarmTrap,
					ommp401LineOduTcm5BackwardIncomingAlignmentErrorAlarmTrap,
					ommp401LineOduTcm6BackwardIncomingAlignmentErrorAlarmTrap,
					ommp401LineOduTcm1LossOfTandemConnectionAlarmTrap,
					ommp401LineOduTcm2LossOfTandemConnectionAlarmTrap,
					ommp401LineOduTcm3LossOfTandemConnectionAlarmTrap,
					ommp401LineOduTcm4LossOfTandemConnectionAlarmTrap,
					ommp401LineOduTcm5LossOfTandemConnectionAlarmTrap,
					ommp401LineOduTcm6LossOfTandemConnectionAlarmTrap,
					ommp401LineOpuPayloadMismatchAlarmTrap		
				}
  	STATUS current
	DESCRIPTION
  	   	"The UTL OMMP401 current notifications group"
  	::= { ommp401 6 }

            snmpcurrentGroup OBJECT-GROUP
    OBJECTS 	{ 
			ommp401InterfaceNumber,	
    			ommp401EepromCardId,
			ommp401EepromCardName,
			ommp401EepromPartCode,
			ommp401EepromCardSerialNumber,
			ommp401EepromHardwareExternalReleaseVersion,
			ommp401SoftwareExternalReleaseVersion,
			ommp401EepromHardwareInternalReleaseVersion,
			ommp401SoftwareInternalReleaseVersion,
			ommp401EepromCardUidNumber,
			ommp401EepromCardEui48Number,
			ommp401EepromCardEui64Number,
			ommp401CardInstallationDate,
			ommp401CardCommissionDate,
			ommp401CardRunningTime,
			ommp401CardRestartCount,
			ommp401Cfp2ReadyForOperation,
			ommp401Cfp2VendorName,
			ommp401Cfp2VendorIeeeId,
			ommp401Cfp2PartNumber,
			ommp401Cfp2SerialNumber,
			ommp401Cfp2ManufacturingDate,
			ommp401Cfp2HardwareVersionNumber,
			ommp401Cfp2FirmwareVersionNumber,
			ommp401Cfp2MediaType,
			ommp401NumberOfNetworkLanesInCfp2,
			ommp401NumberOfHostLanesInCfp2,
			ommp401Cfp2ModuleId,
			ommp401Cfp2PowerClass,
			ommp401Cfp2ProductCodeValue,
			ommp401Cfp2WavelengthTunabilitySupported,
			ommp401TunableCfp2LaserFirstFrequency,
			ommp401TunableCfp2LaserLastFrequency,
			ommp401Cfp2ConnectorType,
			ommp401Cfp2SignalEncodingTypeSupported,
			ommp401Cfp2MaximumBitrateSupported,
			ommp401Cfp2MaximumCaseTemperatureSupported,
			ommp401Cfp2MinimumCaseTemperatureSupported,
			ommp401Cfp2ActiveWavelengthControlSupported,
			ommp401Cfp2TransmitterIsCooledOrUncooled,
			ommp401Qsfp28EepromPage,
			ommp401Qsfp28VendorName,
			ommp401Qsfp28VendorIeeeId,
			ommp401Qsfp28PartNumber,
			ommp401Qsfp28SerialNumber,
			ommp401Qsfp28RevisionNumber,
			ommp401Qsfp28ManufacturingDate,
			ommp401FixedQsfp28LaserWavelength,
			ommp401Qsfp28ConnectorType,
			ommp401Qsfp28LinkLength,
			ommp401Qsfp28SignalEncodingTypeSupported,
			ommp401Qsfp28TransceiverCodesSupported,
			ommp401Qsfp28NominalBitrateSupported,
			ommp401Cfp2ModuleInfo,
			ommp401CardGeneralDetailsTableRowStatus,
			ommp401CardSoftwareUpgrade,
			ommp401CardSignalMonitorState,
			ommp401CardOpticalMonitorState,
			ommp401CardSoftReset,
			ommp401CardFactoryReset,
			ommp401SyncSystemTimeWithNtpServer,
			ommp401SyncRtcWithNtpServer,
			ommp401SyncRtcWithSystemTime,
			ommp401UpdateGivenTimeIntoSystem,
			ommp401UpdateGivenTimeIntoRtc,
			ommp401SystemTimeAndRtcTime,
			ommp401TrafficConfiguration,
			ommp401LoopbackState,
			ommp401PortSignalMonitorState,
			ommp401PortOpticalMonitorState,
			ommp401ClearSignalPerformance,
			ommp401AlsState,
			ommp401AlsPulseRepetitionTime,
			ommp401OtuFecConfiguration,
			ommp401OtuSignalFailThreshold,
			ommp401OtuSignalDegradeThreshold,
			ommp401OtuSapiTransmitTraceMessage,
			ommp401OtuDapiTransmitTraceMessage,
			ommp401OtuOperatorSpecificTransmitTraceMessage,
			ommp401OtuSapiExpectedTraceMessage,
			ommp401OtuDapiExpectedTraceMessage,
			ommp401OtuOperatorSpecificExpectedTraceMessage,
			ommp401OduSignalFailThreshold,
			ommp401OduSignalDegradeThreshold,
			ommp401OduSapiTransmitTraceMessage,
			ommp401OduDapiTransmitTraceMessage,
			ommp401OduOperatorSpecificTransmitTraceMessage,
			ommp401OduSapiExpectedTraceMessage,
			ommp401OduDapiExpectedTraceMessage,
			ommp401OduOperatorSpecificExpectedTraceMessage,
			ommp401TunableCfp2LaserWavelength,
			ommp401Cfp2LaserState,
			ommp401Cfp2Reset,
			ommp401Cfp2PowerDownMode,
			ommp401Cfp2HighTemperatureAlarmThreshold,
			ommp401Cfp2LowTemperatureAlarmThreshold,
			ommp401Cfp2HighTemperatureWarningThreshold,
			ommp401Cfp2LowTemperatureWarningThreshold,
			ommp401Cfp2InputHighPowerAlarmThreshold,
			ommp401Cfp2InputLowPowerAlarmThreshold,
			ommp401Cfp2InputHighPowerWarningThreshold,
			ommp401Cfp2InputLowPowerWarningThreshold,
			ommp401Cfp2OutputHighPowerAlarmThreshold,
			ommp401Cfp2OutputLowPowerAlarmThreshold,
			ommp401Cfp2OutputHighPowerWarningThreshold,
			ommp401Cfp2OutputLowPowerWarningThreshold,
			ommp401Cfp2HighSupplyVoltageAlarmThreshold,
			ommp401Cfp2LowSupplyVoltageAlarmThreshold,
			ommp401Cfp2HighSupplyVoltageWarningThreshold,
			ommp401Cfp2LowSupplyVoltageWarningThreshold,
			ommp401Qsfp28LaserState,
			ommp401Qsfp28Reset,
			ommp401Qsfp28PowerDownMode,
			ommp401Qsfp28HighTemperatureAlarmThreshold,
			ommp401Qsfp28LowTemperatureAlarmThreshold,
			ommp401Qsfp28HighTemperatureWarningThreshold,
			ommp401Qsfp28LowTemperatureWarningThreshold,
			ommp401Qsfp28HighBiasCurrentAlarmThreshold,
			ommp401Qsfp28LowBiasCurrentAlarmThreshold,
			ommp401Qsfp28HighBiasCurrentWarningThreshold,
			ommp401Qsfp28LowBiasCurrentWarningThreshold,
			ommp401Qsfp28InputHighPowerAlarmThreshold,
			ommp401Qsfp28InputLowPowerAlarmThreshold,
			ommp401Qsfp28InputHighPowerWarningThreshold,
			ommp401Qsfp28InputLowPowerWarningThreshold,
			ommp401Qsfp28OutputHighPowerAlarmThreshold,
			ommp401Qsfp28OutputLowPowerAlarmThreshold,
			ommp401Qsfp28OutputHighPowerWarningThreshold,
			ommp401Qsfp28OutputLowPowerWarningThreshold,
			ommp401Qsfp28HighSupplyVoltageAlarmThreshold,
			ommp401Qsfp28LowSupplyVoltageAlarmThreshold,
			ommp401Qsfp28HighSupplyVoltageWarningThreshold,
			ommp401Qsfp28LowSupplyVoltageWarningThreshold,
			ommp401Cfp2InputPowerFailureAlarmInhibit,
			ommp401Cfp2OutputPowerFailureAlarmInhibit,
			ommp401Cfp2HighTemperatureAlarmInhibit,
			ommp401Cfp2LowTemperatureAlarmInhibit,
			ommp401Cfp2HighTemperatureWarningInhibit,
			ommp401Cfp2LowTemperatureWarningInhibit,
			ommp401Cfp2InputHighPowerAlarmInhibit,
			ommp401Cfp2InputLowPowerAlarmInhibit,
			ommp401Cfp2InputHighPowerWarningInhibit,
			ommp401Cfp2InputLowPowerWarningInhibit,
			ommp401Cfp2OutputHighPowerAlarmInhibit,
			ommp401Cfp2OutputLowPowerAlarmInhibit,
			ommp401Cfp2OutputHighPowerWarningInhibit,
			ommp401Cfp2OutputLowPowerWarningInhibit,
			ommp401Cfp2HighSupplyVoltageAlarmInhibit,
			ommp401Cfp2LowSupplyVoltageAlarmInhibit,
			ommp401Cfp2HighSupplyVoltageWarningInhibit,
			ommp401Cfp2LowSupplyVoltageWarningInhibit,
			ommp401Cfp2PresenceAbsenceNotificationInhibit,
			ommp401Qsfp28InputPowerFailureAlarmInhibit,
			ommp401Qsfp28OutputPowerFailureAlarmInhibit,
			ommp401Qsfp28HighTemperatureAlarmInhibit,
			ommp401Qsfp28LowTemperatureAlarmInhibit,
			ommp401Qsfp28HighTemperatureWarningInhibit,
			ommp401Qsfp28LowTemperatureWarningInhibit,
			ommp401Qsfp28HighBiasCurrentAlarmInhibit,
			ommp401Qsfp28LowBiasCurrentAlarmInhibit,
			ommp401Qsfp28HighBiasCurrentWarningInhibit,
			ommp401Qsfp28LowBiasCurrentWarningInhibit,
			ommp401Qsfp28InputHighPowerAlarmInhibit,
			ommp401Qsfp28InputLowPowerAlarmInhibit,
			ommp401Qsfp28InputHighPowerWarningInhibit,
			ommp401Qsfp28InputLowPowerWarningInhibit,
			ommp401Qsfp28OutputHighPowerAlarmInhibit,
			ommp401Qsfp28OutputLowPowerAlarmInhibit,
			ommp401Qsfp28OutputHighPowerWarningInhibit,
			ommp401Qsfp28OutputLowPowerWarningInhibit,
			ommp401Qsfp28HighSupplyVoltageAlarmInhibit,
			ommp401Qsfp28LowSupplyVoltageAlarmInhibit,
			ommp401Qsfp28HighSupplyVoltageWarningInhibit,
			ommp401Qsfp28LowSupplyVoltageWarningInhibit,
			ommp401Qsfp28PresenceAbsenceNotificationInhibit,
			ommp401OtuLossOfSignalAlarmInhibit,
			ommp401OtuLossOfFrameAlarmInhibit,
			ommp401OtuOutOfFrameAlarmInhibit,
			ommp401OtuLossOfMultiFrameAlarmInhibit,
			ommp401OtuOutOfMultiFrameAlarmInhibit,
			ommp401OtuSignalDegradeAlarmInhibit,
			ommp401OtuAlarmIndicationSignalAlarmInhibit,
			ommp401OtuIncomingAlignmentErrorAlarmInhibit,
			ommp401OtuTrailTraceIdentifierMismatchAlarmInhibit,
			ommp401OtuBackwardIncomingAlignmentErrorAlarmInhibit,
			ommp401OtuBackwardDefectIndicationAlarmInhibit,
			ommp401OduSignalDegradeAlarmInhibit,
			ommp401OduAlarmIndicationSignalAlarmInhibit,
			ommp401OduTrailTraceIdentifierMismatchAlarmInhibit,
			ommp401OduLockedDefectAlarmInhibit,
			ommp401OduOpenConnectionIndicationAlarmInhibit,
			ommp401OduBackwardDefectIndicationAlarmInhibit,
			ommp401OduTcm1BackwardDefectIndicationAlarmInhibit,
			ommp401OduTcm2BackwardDefectIndicationAlarmInhibit,
			ommp401OduTcm3BackwardDefectIndicationAlarmInhibit,
			ommp401OduTcm4BackwardDefectIndicationAlarmInhibit,
			ommp401OduTcm5BackwardDefectIndicationAlarmInhibit,
			ommp401OduTcm6BackwardDefectIndicationAlarmInhibit,
			ommp401OduTcm1LossOfTandemConnectionAlarmInhibit,
			ommp401OduTcm2LossOfTandemConnectionAlarmInhibit,
			ommp401OduTcm3LossOfTandemConnectionAlarmInhibit,
			ommp401OduTcm4LossOfTandemConnectionAlarmInhibit,
			ommp401OduTcm5LossOfTandemConnectionAlarmInhibit,
			ommp401OduTcm6LossOfTandemConnectionAlarmInhibit,
			ommp401OduTcm1BackwardIncomingAlignmentErrorAlarmInhibit,
			ommp401OduTcm2BackwardIncomingAlignmentErrorAlarmInhibit,
			ommp401OduTcm3BackwardIncomingAlignmentErrorAlarmInhibit,
			ommp401OduTcm4BackwardIncomingAlignmentErrorAlarmInhibit,
			ommp401OduTcm5BackwardIncomingAlignmentErrorAlarmInhibit,
			ommp401OduTcm6BackwardIncomingAlignmentErrorAlarmInhibit,
			ommp401OpuPayloadMismatchAlarmInhibit,
			ommp401EthernetLossOfSignalAlarmInhibit,
			ommp401EthernetIngressRemoteFaultAlarmInhibit,
			ommp401EthernetIngressPcsErrorBlocksDetectedAlarmInhibit,
			ommp401EthernetIngressPcsBipErrorsDetectedAlarmInhibit,
			ommp401EthernetIngressOpuClientServerFailIndicationAlarmInhibit,
			ommp401EthernetIngressLocalFaultAlarmInhibit,
			ommp401EthernetIngressLossOfAlignmentAlarmInhibit,
			ommp401EthernetIngressLossOfAlignmentMarkerLockAlarmInhibit,
			ommp401EthernetIngressLossOfBlockLockAlarmInhibit,
			ommp401EthernetEgressRemoteFaultAlarmInhibit,
			ommp401EthernetEgressPcsErrorBlocksDetectedAlarmInhibit,
			ommp401EthernetEgressPcsBipErrorsDetectedAlarmInhibit,
			ommp401EthernetEgressHighBerAlarmInhibit,
			ommp401EthernetEgressLocalFaultAlarmInhibit,
			ommp401EthernetEgressLossOfAlignmentAlarmInhibit,
			ommp401EthernetEgressLossOfAlignmentMarkerLockAlarmInhibit,
			ommp401EthernetEgressLossOfBlockLockAlarmInhibit,
			ommp401Cfp2InputPowerFailureAlarmSeverity,
			ommp401Cfp2OutputPowerFailureAlarmSeverity,
			ommp401Cfp2HighTemperatureAlarmSeverity,
			ommp401Cfp2LowTemperatureAlarmSeverity,
			ommp401Cfp2HighTemperatureWarningSeverity,
			ommp401Cfp2LowTemperatureWarningSeverity,
			ommp401Cfp2InputHighPowerAlarmSeverity,
			ommp401Cfp2InputLowPowerAlarmSeverity,
			ommp401Cfp2InputHighPowerWarningSeverity,
			ommp401Cfp2InputLowPowerWarningSeverity,
			ommp401Cfp2OutputHighPowerAlarmSeverity,
			ommp401Cfp2OutputLowPowerAlarmSeverity,
			ommp401Cfp2OutputHighPowerWarningSeverity,
			ommp401Cfp2OutputLowPowerWarningSeverity,
			ommp401Cfp2HighSupplyVoltageAlarmSeverity,
			ommp401Cfp2LowSupplyVoltageAlarmSeverity,
			ommp401Cfp2HighSupplyVoltageWarningSeverity,
			ommp401Cfp2LowSupplyVoltageWarningSeverity,
			ommp401Cfp2PresenceAbsenceNotificationSeverity,
			ommp401Qsfp28InputPowerFailureAlarmSeverity,
			ommp401Qsfp28OutputPowerFailureAlarmSeverity,
			ommp401Qsfp28HighTemperatureAlarmSeverity,
			ommp401Qsfp28LowTemperatureAlarmSeverity,
			ommp401Qsfp28HighTemperatureWarningSeverity,
			ommp401Qsfp28LowTemperatureWarningSeverity,
			ommp401Qsfp28HighBiasCurrentAlarmSeverity,
			ommp401Qsfp28LowBiasCurrentAlarmSeverity,
			ommp401Qsfp28HighBiasCurrentWarningSeverity,
			ommp401Qsfp28LowBiasCurrentWarningSeverity,
			ommp401Qsfp28InputHighPowerAlarmSeverity,
			ommp401Qsfp28InputLowPowerAlarmSeverity,
			ommp401Qsfp28InputHighPowerWarningSeverity,
			ommp401Qsfp28InputLowPowerWarningSeverity,
			ommp401Qsfp28OutputHighPowerAlarmSeverity,
			ommp401Qsfp28OutputLowPowerAlarmSeverity,
			ommp401Qsfp28OutputHighPowerWarningSeverity,
			ommp401Qsfp28OutputLowPowerWarningSeverity,
			ommp401Qsfp28HighSupplyVoltageAlarmSeverity,
			ommp401Qsfp28LowSupplyVoltageAlarmSeverity,
			ommp401Qsfp28HighSupplyVoltageWarningSeverity,
			ommp401Qsfp28LowSupplyVoltageWarningSeverity,
			ommp401Qsfp28PresenceAbsenceNotificationSeverity,
			ommp401OtuLossOfSignalAlarmSeverity,
			ommp401OtuLossOfFrameAlarmSeverity,
			ommp401OtuOutOfFrameAlarmSeverity,
			ommp401OtuOutOfMultiFrameAlarmSeverity,
			ommp401OtuSignalDegradeAlarmSeverity,
			ommp401OtuAlarmIndicationSignalAlarmSeverity,
			ommp401OtuIncomingAlignmentErrorAlarmSeverity,
			ommp401OtuTrailTraceIdentifierMismatchAlarmSeverity,
			ommp401OtuBackwardIncomingAlignmentErrorAlarmSeverity,
			ommp401OtuBackwardDefectIndicationAlarmSeverity,
			ommp401OduSignalDegradeAlarmSeverity,
			ommp401OduAlarmIndicationSignalAlarmSeverity,
			ommp401OduTrailTraceIdentifierMismatchAlarmSeverity,
			ommp401OduLockedDefectAlarmSeverity,
			ommp401OduOpenConnectionIndicationAlarmSeverity,
			ommp401OduBackwardDefectIndicationAlarmSeverity,
			ommp401OduTcm1BackwardDefectIndicationAlarmSeverity,
			ommp401OduTcm2BackwardDefectIndicationAlarmSeverity,
			ommp401OduTcm3BackwardDefectIndicationAlarmSeverity,
			ommp401OduTcm4BackwardDefectIndicationAlarmSeverity,
			ommp401OduTcm5BackwardDefectIndicationAlarmSeverity,
			ommp401OduTcm6BackwardDefectIndicationAlarmSeverity,
			ommp401OduTcm1LossOfTandemConnectionAlarmSeverity,
			ommp401OduTcm2LossOfTandemConnectionAlarmSeverity,
			ommp401OduTcm3LossOfTandemConnectionAlarmSeverity,
			ommp401OduTcm4LossOfTandemConnectionAlarmSeverity,
			ommp401OduTcm5LossOfTandemConnectionAlarmSeverity,
			ommp401OduTcm6LossOfTandemConnectionAlarmSeverity,
			ommp401OduTcm1BackwardIncomingAlignmentErrorAlarmSeverity,
			ommp401OduTcm2BackwardIncomingAlignmentErrorAlarmSeverity,
			ommp401OduTcm3BackwardIncomingAlignmentErrorAlarmSeverity,
			ommp401OduTcm4BackwardIncomingAlignmentErrorAlarmSeverity,
			ommp401OduTcm5BackwardIncomingAlignmentErrorAlarmSeverity,
			ommp401OduTcm6BackwardIncomingAlignmentErrorAlarmSeverity,
			ommp401OpuPayloadMismatchAlarmSeverity,
			ommp401EthernetLossOfSignalAlarmSeverity,
			ommp401EthernetIngressRemoteFaultAlarmSeverity,
			ommp401EthernetIngressPcsErrorBlocksDetectedAlarmSeverity,
			ommp401EthernetIngressPcsBipErrorsDetectedAlarmSeverity,
			ommp401EthernetIngressOpuClientServerFailIndicationAlarmSeverity,
			ommp401EthernetIngressLocalFaultAlarmSeverity,
			ommp401EthernetIngressLossOfAlignmentAlarmSeverity,
			ommp401EthernetIngressLossOfAlignmentMarkerLockAlarmSeverity,
			ommp401EthernetIngressLossOfBlockLockAlarmSeverity,
			ommp401EthernetEgressRemoteFaultAlarmSeverity,
			ommp401EthernetEgressPcsErrorBlocksDetectedAlarmSeverity,
			ommp401EthernetEgressPcsBipErrorsDetectedAlarmSeverity,
			ommp401EthernetEgressHighBerAlarmSeverity,
			ommp401EthernetEgressLocalFaultAlarmSeverity,
			ommp401EthernetEgressLossOfAlignmentAlarmSeverity,
			ommp401EthernetEgressLossOfAlignmentMarkerLockAlarmSeverity,
			ommp401EthernetEgressLossOfBlockLockAlarmSeverity,
			ommp401TunableCfp2WavelengthGridSpacing,
			ommp401LineOtuSignalFailThreshold,
			ommp401LineOtuSignalDegradeThreshold,
			ommp401LineOtuSapiTransmitTraceMessage,
			ommp401LineOtuDapiTransmitTraceMessage,
			ommp401LineOtuOperatorSpecificTransmitTraceMessage,
			ommp401LineOtuSapiExpectedTraceMessage,
			ommp401LineOtuDapiExpectedTraceMessage,
			ommp401LineOtuOperatorSpecificExpectedTraceMessage,
			ommp401LineOduSignalFailThreshold,
			ommp401LineOduSignalDegradeThreshold,
			ommp401LineOduSapiTransmitTraceMessage,
			ommp401LineOduDapiTransmitTraceMessage,
			ommp401LineOduOperatorSpecificTransmitTraceMessage,
			ommp401LineOduSapiExpectedTraceMessage,
			ommp401LineOduDapiExpectedTraceMessage,
			ommp401LineOduOperatorSpecificExpectedTraceMessage,
			ommp401LineOtuLossOfSignalAlarmInhibit,
			ommp401LineOtuLossOfFrameAlarmInhibit,
			ommp401LineOtuOutOfFrameAlarmInhibit,
			ommp401LineOtuLossOfMultiFrameAlarmInhibit,
			ommp401LineOtuOutOfMultiFrameAlarmInhibit,
			ommp401LineOtuSignalDegradeAlarmInhibit,
			ommp401LineOtuAlarmIndicationSignalAlarmInhibit,
			ommp401LineOtuIncomingAlignmentErrorAlarmInhibit,
			ommp401LineOtuTrailTraceIdentifierMismatchAlarmInhibit,
			ommp401LineOtuBackwardIncomingAlignmentErrorAlarmInhibit,
			ommp401LineOtuBackwardDefectIndicationAlarmInhibit,
			ommp401LineOduSignalDegradeAlarmInhibit,
			ommp401LineOduAlarmIndicationSignalAlarmInhibit,
			ommp401LineOduTrailTraceIdentifierMismatchAlarmInhibit,
			ommp401LineOduLockedDefectAlarmInhibit,
			ommp401LineOduOpenConnectionIndicationAlarmInhibit,
			ommp401LineOduBackwardDefectIndicationAlarmInhibit,
			ommp401LineOduTcm1BackwardDefectIndicationAlarmInhibit,
			ommp401LineOduTcm2BackwardDefectIndicationAlarmInhibit,
			ommp401LineOduTcm3BackwardDefectIndicationAlarmInhibit,
			ommp401LineOduTcm4BackwardDefectIndicationAlarmInhibit,
			ommp401LineOduTcm5BackwardDefectIndicationAlarmInhibit,
			ommp401LineOduTcm6BackwardDefectIndicationAlarmInhibit,
			ommp401LineOduTcm1LossOfTandemConnectionAlarmInhibit,
			ommp401LineOduTcm2LossOfTandemConnectionAlarmInhibit,
			ommp401LineOduTcm3LossOfTandemConnectionAlarmInhibit,
			ommp401LineOduTcm4LossOfTandemConnectionAlarmInhibit,
			ommp401LineOduTcm5LossOfTandemConnectionAlarmInhibit,
			ommp401LineOduTcm6LossOfTandemConnectionAlarmInhibit,
			ommp401LineOduTcm1BackwardIncomingAlignmentErrorAlarmInhibit,
			ommp401LineOduTcm2BackwardIncomingAlignmentErrorAlarmInhibit,
			ommp401LineOduTcm3BackwardIncomingAlignmentErrorAlarmInhibit,
			ommp401LineOduTcm4BackwardIncomingAlignmentErrorAlarmInhibit,
			ommp401LineOduTcm5BackwardIncomingAlignmentErrorAlarmInhibit,
			ommp401LineOduTcm6BackwardIncomingAlignmentErrorAlarmInhibit,
			ommp401LineOpuPayloadMismatchAlarmInhibit,
			ommp401LineOtuLossOfSignalAlarmSeverity,
			ommp401LineOtuLossOfFrameAlarmSeverity,
			ommp401LineOtuOutOfFrameAlarmSeverity,
			ommp401LineOtuOutOfMultiFrameAlarmSeverity,
			ommp401LineOtuSignalDegradeAlarmSeverity,
			ommp401LineOtuAlarmIndicationSignalAlarmSeverity,
			ommp401LineOtuIncomingAlignmentErrorAlarmSeverity,
			ommp401LineOtuTrailTraceIdentifierMismatchAlarmSeverity,
			ommp401LineOtuBackwardIncomingAlignmentErrorAlarmSeverity,
			ommp401LineOtuBackwardDefectIndicationAlarmSeverity,
			ommp401LineOduSignalDegradeAlarmSeverity,
			ommp401LineOduAlarmIndicationSignalAlarmSeverity,
			ommp401LineOduTrailTraceIdentifierMismatchAlarmSeverity,
			ommp401LineOduLockedDefectAlarmSeverity,
			ommp401LineOduOpenConnectionIndicationAlarmSeverity,
			ommp401LineOduBackwardDefectIndicationAlarmSeverity,
			ommp401LineOduTcm1BackwardDefectIndicationAlarmSeverity,
			ommp401LineOduTcm2BackwardDefectIndicationAlarmSeverity,
			ommp401LineOduTcm3BackwardDefectIndicationAlarmSeverity,
			ommp401LineOduTcm4BackwardDefectIndicationAlarmSeverity,
			ommp401LineOduTcm5BackwardDefectIndicationAlarmSeverity,
			ommp401LineOduTcm6BackwardDefectIndicationAlarmSeverity,
			ommp401LineOduTcm1LossOfTandemConnectionAlarmSeverity,
			ommp401LineOduTcm2LossOfTandemConnectionAlarmSeverity,
			ommp401LineOduTcm3LossOfTandemConnectionAlarmSeverity,
			ommp401LineOduTcm4LossOfTandemConnectionAlarmSeverity,
			ommp401LineOduTcm5LossOfTandemConnectionAlarmSeverity,
			ommp401LineOduTcm6LossOfTandemConnectionAlarmSeverity,
			ommp401LineOduTcm1BackwardIncomingAlignmentErrorAlarmSeverity,
			ommp401LineOduTcm2BackwardIncomingAlignmentErrorAlarmSeverity,
			ommp401LineOduTcm3BackwardIncomingAlignmentErrorAlarmSeverity,
			ommp401LineOduTcm4BackwardIncomingAlignmentErrorAlarmSeverity,
			ommp401LineOduTcm5BackwardIncomingAlignmentErrorAlarmSeverity,
			ommp401LineOduTcm6BackwardIncomingAlignmentErrorAlarmSeverity,
			ommp401LineOpuPayloadMismatchAlarmSeverity,
			ommp401ConfigurationTableRowStatus,
			ommp401Cfp2InputPowerFailureAlarm,
			ommp401Cfp2OutputPowerFailureAlarm,
			ommp401Cfp2HighTemperatureAlarm,
			ommp401Cfp2LowTemperatureAlarm,
			ommp401Cfp2HighTemperatureWarning,
			ommp401Cfp2LowTemperatureWarning,
			ommp401Cfp2InputHighPowerAlarm,
			ommp401Cfp2InputLowPowerAlarm,
			ommp401Cfp2InputHighPowerWarning,
			ommp401Cfp2InputLowPowerWarning,
			ommp401Cfp2OutputHighPowerAlarm,
			ommp401Cfp2OutputLowPowerAlarm,
			ommp401Cfp2OutputHighPowerWarning,
			ommp401Cfp2OutputLowPowerWarning,
			ommp401Cfp2HighSupplyVoltageAlarm,
			ommp401Cfp2LowSupplyVoltageAlarm,
			ommp401Cfp2HighSupplyVoltageWarning,
			ommp401Cfp2LowSupplyVoltageWarning,
			ommp401Cfp2PresenceAbsenceNotification,
			ommp401Qsfp28InputPowerFailureAlarm,
			ommp401Qsfp28OutputPowerFailureAlarm,
			ommp401Qsfp28HighTemperatureAlarm,
			ommp401Qsfp28LowTemperatureAlarm,
			ommp401Qsfp28HighTemperatureWarning,
			ommp401Qsfp28LowTemperatureWarning,
			ommp401Qsfp28HighBiasCurrentAlarm,
			ommp401Qsfp28LowBiasCurrentAlarm,
			ommp401Qsfp28HighBiasCurrentWarning,
			ommp401Qsfp28LowBiasCurrentWarning,
			ommp401Qsfp28InputHighPowerAlarm,
			ommp401Qsfp28InputLowPowerAlarm,
			ommp401Qsfp28InputHighPowerWarning,
			ommp401Qsfp28InputLowPowerWarning,
			ommp401Qsfp28OutputHighPowerAlarm,
			ommp401Qsfp28OutputLowPowerAlarm,
			ommp401Qsfp28OutputHighPowerWarning,
			ommp401Qsfp28OutputLowPowerWarning,
			ommp401Qsfp28HighSupplyVoltageAlarm,
			ommp401Qsfp28LowSupplyVoltageAlarm,
			ommp401Qsfp28HighSupplyVoltageWarning,
			ommp401Qsfp28LowSupplyVoltageWarning,
			ommp401Qsfp28PresenceAbsenceNotification,
			ommp401OtuLossOfSignalAlarm,
			ommp401OtuLossOfFrameAlarm,
			ommp401OtuOutOfFrameAlarm,
			ommp401OtuLossOfMultiFrameAlarm,
			ommp401OtuOutOfMultiFrameAlarm,
			ommp401OtuSignalFailAlarm,
			ommp401OtuSignalDegradeAlarm,
			ommp401OtuAlarmIndicationSignalAlarm,
			ommp401OtuIncomingAlignmentErrorAlarm,
			ommp401OtuTrailTraceIdentifierMismatchAlarm,
			ommp401OtuBackwardIncomingAlignmentErrorAlarm,
			ommp401OtuBackwardDefectIndicationAlarm,
			ommp401OduSignalFailAlarm,
			ommp401OduSignalDegradeAlarm,
			ommp401OduAlarmIndicationSignalAlarm,
			ommp401OduTrailTraceIdentifierMismatchAlarm,
			ommp401OduLockedDefectAlarm,
			ommp401OduOpenConnectionIndicationAlarm,
			ommp401OduBackwardDefectIndicationAlarm,
			ommp401OduTcm1BackwardDefectIndicationAlarm,
			ommp401OduTcm2BackwardDefectIndicationAlarm,
			ommp401OduTcm3BackwardDefectIndicationAlarm,
			ommp401OduTcm4BackwardDefectIndicationAlarm,
			ommp401OduTcm5BackwardDefectIndicationAlarm,
			ommp401OduTcm6BackwardDefectIndicationAlarm,
			ommp401OduTcm1BackwardIncomingAlignmentErrorAlarm,
			ommp401OduTcm2BackwardIncomingAlignmentErrorAlarm,
			ommp401OduTcm3BackwardIncomingAlignmentErrorAlarm,
			ommp401OduTcm4BackwardIncomingAlignmentErrorAlarm,
			ommp401OduTcm5BackwardIncomingAlignmentErrorAlarm,
			ommp401OduTcm6BackwardIncomingAlignmentErrorAlarm,
			ommp401OduTcm1LossOfTandemConnectionAlarm,
			ommp401OduTcm2LossOfTandemConnectionAlarm,
			ommp401OduTcm3LossOfTandemConnectionAlarm,
			ommp401OduTcm4LossOfTandemConnectionAlarm,
			ommp401OduTcm5LossOfTandemConnectionAlarm,
			ommp401OduTcm6LossOfTandemConnectionAlarm,
			ommp401OpuPayloadMismatchAlarm,
			ommp401EthernetLossOfSignalAlarm,
			ommp401EthernetIngressRemoteFaultAlarm,
			ommp401EthernetIngressPcsErrorBlocksDetectedAlarm,
			ommp401EthernetIngressPcsBipErrorsDetectedAlarm,
			ommp401EthernetIngressOpuClientServerFailIndicationAlarm,
			ommp401EthernetIngressLocalFaultAlarm,
			ommp401EthernetIngressLossOfAlignmentAlarm,
			ommp401EthernetIngressLossOfAlignmentMarkerLockAlarm,
			ommp401EthernetIngressLossOfBlockLockAlarm,
			ommp401EthernetEgressRemoteFaultAlarm,
			ommp401EthernetEgressPcsErrorBlocksDetectedAlarm,
			ommp401EthernetEgressPcsBipErrorsDetectedAlarm,
			ommp401EthernetEgressHighBerAlarm,
			ommp401EthernetEgressLocalFaultAlarm,
			ommp401EthernetEgressLossOfAlignmentAlarm,
			ommp401EthernetEgressLossOfAlignmentMarkerLockAlarm,
			ommp401EthernetEgressLossOfBlockLockAlarm,
			ommp401LineOtuLossOfSignalAlarm,
			ommp401LineOtuLossOfFrameAlarm,
			ommp401LineOtuOutOfFrameAlarm,
			ommp401LineOtuLossOfMultiFrameAlarm,
			ommp401LineOtuOutOfMultiFrameAlarm,
			ommp401LineOtuSignalDegradeAlarm,
			ommp401LineOtuAlarmIndicationSignalAlarm,
			ommp401LineOtuIncomingAlignmentErrorAlarm,
			ommp401LineOtuTrailTraceIdentifierMismatchAlarm,
			ommp401LineOtuBackwardIncomingAlignmentErrorAlarm,
			ommp401LineOtuBackwardDefectIndicationAlarm,
			ommp401LineOduSignalDegradeAlarm,
			ommp401LineOduAlarmIndicationSignalAlarm,
			ommp401LineOduTrailTraceIdentifierMismatchAlarm,
			ommp401LineOduLockedDefectAlarm,
			ommp401LineOduOpenConnectionIndicationAlarm,
			ommp401LineOduBackwardDefectIndicationAlarm,
			ommp401LineOduTcm1BackwardDefectIndicationAlarm,
			ommp401LineOduTcm2BackwardDefectIndicationAlarm,
			ommp401LineOduTcm3BackwardDefectIndicationAlarm,
			ommp401LineOduTcm4BackwardDefectIndicationAlarm,
			ommp401LineOduTcm5BackwardDefectIndicationAlarm,
			ommp401LineOduTcm6BackwardDefectIndicationAlarm,
			ommp401LineOduTcm1BackwardIncomingAlignmentErrorAlarm,
			ommp401LineOduTcm2BackwardIncomingAlignmentErrorAlarm,
			ommp401LineOduTcm3BackwardIncomingAlignmentErrorAlarm,
			ommp401LineOduTcm4BackwardIncomingAlignmentErrorAlarm,
			ommp401LineOduTcm5BackwardIncomingAlignmentErrorAlarm,
			ommp401LineOduTcm6BackwardIncomingAlignmentErrorAlarm,
			ommp401LineOduTcm1LossOfTandemConnectionAlarm,
			ommp401LineOduTcm2LossOfTandemConnectionAlarm,
			ommp401LineOduTcm3LossOfTandemConnectionAlarm,
			ommp401LineOduTcm4LossOfTandemConnectionAlarm,
			ommp401LineOduTcm5LossOfTandemConnectionAlarm,
			ommp401LineOduTcm6LossOfTandemConnectionAlarm,
			ommp401LineOpuPayloadMismatchAlarm,
			ommp401AlarmQueryTableRowStatus,
			ommp401Cfp2InputPower,
			ommp401Cfp2OutputPower,
			ommp401Cfp2SupplyVoltage,
			ommp401Cfp2Temperature,
			ommp401Qsfp28InputPower,
			ommp401Qsfp28OutputPower,
			ommp401Qsfp28BiasCurrent,
			ommp401Qsfp28SupplyVoltage,
			ommp401Qsfp28Temperature,
			ommp401OtnFecUncorrectedWords,
			ommp401OtnFecCorrectedBits,
			ommp401OtnFecZerosCorrectedBits,
			ommp401OtnFecOnesCorrectedBits,
			ommp401OtuBitInterleavedParityErrors,
			ommp401OtuIncomingAlignmentErrorSeconds,
			ommp401OtuBackwardErrorIndicationErrorCount,
			ommp401OtuBackwardIncomingAlignmentErrorSeconds,
			ommp401OtuErrorFreeSeconds,
			ommp401OtuErrorSeconds,
			ommp401OtuBackgroundBlockErrors,
			ommp401OtuSevereErrorSeconds,
			ommp401OtuUnavailableSeconds,
			ommp401OtuErrorSecondsErrorRatio,
			ommp401OtuErrorFreePeriod,
			ommp401OtuErroredPeriod,
			ommp401OtuConsecutiveSevereErrorSecond,
			ommp401OtuNonConsecutiveSevereErrorSecond,
			ommp401OtuPathAvailabilityStatus,
			ommp401OtuBackgroundBlockErrorRatio,
			ommp401OtuSevereErrorSecondsErrorRatio,
			ommp401OtuFarEndErrorFreeSeconds,
			ommp401OtuFarEndBackgroundBlockErrors,
			ommp401OtuFarEndSevereErrorSeconds,
			ommp401OtuFarEndUnavailableSeconds,
			ommp401OtuFarEndErrorSecondsErrorRatio,
			ommp401OtuFarEndErrorSeconds,
			ommp401OtuFarEndBackgroundBlockErrorRatio,
			ommp401OtuFarEndSevereErrorSecondsErrorRatio,
			ommp401OtuErrorRatio,
			ommp401OtuFarEndErrorFreePeriod,
			ommp401OtuFarEndErroredPeriod,
			ommp401OtuFarEndConsecutiveSevereErrorSecond,
			ommp401OtuFarEndNonConsecutiveSevereErrorSecond,
			ommp401OtuFarEndPathAvailabilityStatus,
			ommp401OtuFramesReceived,
			ommp401OtuBitErrorRate,
			ommp401OduBitInterleavedParityErrors,
			ommp401OduTcm1BitInterleavedParityErrors,
			ommp401OduTcm2BitInterleavedParityErrors,
			ommp401OduTcm3BitInterleavedParityErrors,
			ommp401OduTcm4BitInterleavedParityErrors,
			ommp401OduTcm5BitInterleavedParityErrors,
			ommp401OduTcm6BitInterleavedParityErrors,
			ommp401OduTcm1IncomingAlignmentErrorSeconds,
			ommp401OduBackwardErrorIndicationErrorCount,
			ommp401OduTcm1BackwardErrorIndicationErrorCount,
			ommp401OduTcm2BackwardErrorIndicationErrorCount,
			ommp401OduTcm3BackwardErrorIndicationErrorCount,
			ommp401OduTcm4BackwardErrorIndicationErrorCount,
			ommp401OduTcm5BackwardErrorIndicationErrorCount,
			ommp401OduTcm6BackwardErrorIndicationErrorCount,
			ommp401OduTcm1BackwardIncomingAlignmentErrorSeconds,
			ommp401OduDelayMeasurement,
			ommp401OduErrorFreeSeconds,
			ommp401OduErrorSeconds,
			ommp401OduBackgroundBlockErrors,
			ommp401OduSevereErrorSeconds,
			ommp401OduUnavailableSeconds,
			ommp401OduErrorFreePeriod,
			ommp401OduErroredPeriod,
			ommp401OduConsecutiveSevereErrorSecond,
			ommp401OduNonConsecutiveSevereErrorSecond,
			ommp401OduPathAvailabilityStatus,
			ommp401OduFarEndErrorFreePeriod,
			ommp401OduFarEndErroredPeriod,
			ommp401OduFarEndConsecutiveSevereErrorSecond,
			ommp401OduFarEndNonConsecutiveSevereErrorSecond,
			ommp401OduFarEndPathAvailabilityStatus,
			ommp401OduFramesReceived,
			ommp401OduErrorSecondsErrorRatio,
			ommp401OduBackgroundBlockErrorRatio,
			ommp401OduSevereErrorSecondsErrorRatio,
			ommp401OduFarEndErrorFreeSeconds,
			ommp401OduFarEndErrorSeconds,
			ommp401OduFarEndBackgroundBlockErrors,
			ommp401OduFarEndSevereErrorSeconds,
			ommp401OduFarEndUnavailableSeconds,
			ommp401OduFarEndErrorSecondsErrorRatio,
			ommp401OduFarEndBackgroundBlockErrorRatio,
			ommp401OduFarEndSevereErrorSecondsErrorRatio,
			ommp401OtnMeasurementPeriod,
			ommp401OduTcm1ErrorFreeSeconds,
			ommp401OduTcm1ErrorSeconds,
			ommp401OduTcm1BackgroundBlockErrors,
			ommp401OduTcm1SevereErrorSeconds,
			ommp401OduTcm1UnavailableSeconds,
			ommp401OduTcm1ErrorFreePeriod,
			ommp401OduTcm1ErroredPeriod,
			ommp401OduTcm1ConsecutiveSevereErrorSecond,
			ommp401OduTcm1NonConsecutiveSevereErrorSecond,
			ommp401OduTcm1PathAvailabilityStatus,
			ommp401OduTcm1BackgroundBlockErrorRatio,
			ommp401OduTcm1SevereErrorSecondsErrorRatio,
			ommp401OduTcm1FarEndErrorFreeSeconds,
			ommp401OduTcm1FarEndErrorSeconds,
			ommp401OduTcm1FarEndBackgroundBlockErrors,
			ommp401OduTcm1FarEndSevereErrorSeconds,
			ommp401OduTcm1FarEndUnavailableSeconds,
			ommp401OduTcm1FarEndErrorFreePeriod,
			ommp401OduTcm1FarEndErroredPeriod,
			ommp401OduTcm1FarEndConsecutiveSevereErrorSecond,
			ommp401OduTcm1FarEndNonConsecutiveSevereErrorSecond,
			ommp401OduTcm1FarEndPathAvailabilityStatus,
			ommp401OduTcm1FarEndBackgroundBlockErrorRatio,
			ommp401OduTcm1FarEndSevereErrorSecondsErrorRatio,
			ommp401OduTcm2ErrorFreeSeconds,
			ommp401OduTcm2ErrorSeconds,
			ommp401OduTcm2BackgroundBlockErrors,
			ommp401OduTcm2SevereErrorSeconds,
			ommp401OduTcm2UnavailableSeconds,
			ommp401OduTcm2ErrorFreePeriod,
			ommp401OduTcm2ErroredPeriod,
			ommp401OduTcm2ConsecutiveSevereErrorSecond,
			ommp401OduTcm2NonConsecutiveSevereErrorSecond,
			ommp401OduTcm2PathAvailabilityStatus,
			ommp401OduTcm2BackgroundBlockErrorRatio,
			ommp401OduTcm2SevereErrorSecondsErrorRatio,
			ommp401OduTcm2FarEndErrorFreeSeconds,
			ommp401OduTcm2FarEndErrorSeconds,
			ommp401OduTcm2FarEndBackgroundBlockErrors,
			ommp401OduTcm2FarEndSevereErrorSeconds,
			ommp401OduTcm2FarEndUnavailableSeconds,
			ommp401OduTcm2FarEndErrorFreePeriod,
			ommp401OduTcm2FarEndErroredPeriod,
			ommp401OduTcm2FarEndConsecutiveSevereErrorSecond,
			ommp401OduTcm2FarEndNonConsecutiveSevereErrorSecond,
			ommp401OduTcm2FarEndPathAvailabilityStatus,
			ommp401OduTcm2FarEndBackgroundBlockErrorRatio,
			ommp401OduTcm2FarEndSevereErrorSecondsErrorRatio,
			ommp401OduTcm3ErrorFreeSeconds,
			ommp401OduTcm3ErrorSeconds,
			ommp401OduTcm3BackgroundBlockErrors,
			ommp401OduTcm3SevereErrorSeconds,
			ommp401OduTcm3UnavailableSeconds,
			ommp401OduTcm3ErrorFreePeriod,
			ommp401OduTcm3ErroredPeriod,
			ommp401OduTcm3ConsecutiveSevereErrorSecond,
			ommp401OduTcm3NonConsecutiveSevereErrorSecond,
			ommp401OduTcm3PathAvailabilityStatus,
			ommp401OduTcm3BackgroundBlockErrorRatio,
			ommp401OduTcm3SevereErrorSecondsErrorRatio,
			ommp401OduTcm3FarEndErrorFreeSeconds,
			ommp401OduTcm3FarEndErrorSeconds,
			ommp401OduTcm3FarEndBackgroundBlockErrors,
			ommp401OduTcm3FarEndSevereErrorSeconds,
			ommp401OduTcm3FarEndUnavailableSeconds,
			ommp401OduTcm3FarEndErrorFreePeriod,
			ommp401OduTcm3FarEndErroredPeriod,
			ommp401OduTcm3FarEndConsecutiveSevereErrorSecond,
			ommp401OduTcm3FarEndNonConsecutiveSevereErrorSecond,
			ommp401OduTcm3FarEndPathAvailabilityStatus,
			ommp401OduTcm3FarEndBackgroundBlockErrorRatio,
			ommp401OduTcm3FarEndSevereErrorSecondsErrorRatio,
			ommp401OduTcm4ErrorFreeSeconds,
			ommp401OduTcm4ErrorSeconds,
			ommp401OduTcm4BackgroundBlockErrors,
			ommp401OduTcm4SevereErrorSeconds,
			ommp401OduTcm4UnavailableSeconds,
			ommp401OduTcm4ErrorFreePeriod,
			ommp401OduTcm4ErroredPeriod,
			ommp401OduTcm4ConsecutiveSevereErrorSecond,
			ommp401OduTcm4NonConsecutiveSevereErrorSecond,
			ommp401OduTcm4PathAvailabilityStatus,
			ommp401OduTcm4BackgroundBlockErrorRatio,
			ommp401OduTcm4SevereErrorSecondsErrorRatio,
			ommp401OduTcm4FarEndErrorFreeSeconds,
			ommp401OduTcm4FarEndErrorSeconds,
			ommp401OduTcm4FarEndBackgroundBlockErrors,
			ommp401OduTcm4FarEndSevereErrorSeconds,
			ommp401OduTcm4FarEndUnavailableSeconds,
			ommp401OduTcm4FarEndErrorFreePeriod,
			ommp401OduTcm4FarEndErroredPeriod,
			ommp401OduTcm4FarEndConsecutiveSevereErrorSecond,
			ommp401OduTcm4FarEndNonConsecutiveSevereErrorSecond,
			ommp401OduTcm4FarEndPathAvailabilityStatus,
			ommp401OduTcm4FarEndBackgroundBlockErrorRatio,
			ommp401OduTcm4FarEndSevereErrorSecondsErrorRatio,
			ommp401OduTcm5ErrorFreeSeconds,
			ommp401OduTcm5ErrorSeconds,
			ommp401OduTcm5BackgroundBlockErrors,
			ommp401OduTcm5SevereErrorSeconds,
			ommp401OduTcm5UnavailableSeconds,
			ommp401OduTcm5ErrorFreePeriod,
			ommp401OduTcm5ErroredPeriod,
			ommp401OduTcm5ConsecutiveSevereErrorSecond,
			ommp401OduTcm5NonConsecutiveSevereErrorSecond,
			ommp401OduTcm5PathAvailabilityStatus,
			ommp401OduTcm5BackgroundBlockErrorRatio,
			ommp401OduTcm5SevereErrorSecondsErrorRatio,
			ommp401OduTcm5FarEndErrorFreeSeconds,
			ommp401OduTcm5FarEndErrorSeconds,
			ommp401OduTcm5FarEndBackgroundBlockErrors,
			ommp401OduTcm5FarEndSevereErrorSeconds,
			ommp401OduTcm5FarEndUnavailableSeconds,
			ommp401OduTcm5FarEndErrorFreePeriod,
			ommp401OduTcm5FarEndErroredPeriod,
			ommp401OduTcm5FarEndConsecutiveSevereErrorSecond,
			ommp401OduTcm5FarEndNonConsecutiveSevereErrorSecond,
			ommp401OduTcm5FarEndPathAvailabilityStatus,
			ommp401OduTcm5FarEndBackgroundBlockErrorRatio,
			ommp401OduTcm5FarEndSevereErrorSecondsErrorRatio,
			ommp401OduTcm6ErrorFreeSeconds,
			ommp401OduTcm6ErrorSeconds,
			ommp401OduTcm6BackgroundBlockErrors,
			ommp401OduTcm6SevereErrorSeconds,
			ommp401OduTcm6UnavailableSeconds,
			ommp401OduTcm6ErrorFreePeriod,
			ommp401OduTcm6ErroredPeriod,
			ommp401OduTcm6ConsecutiveSevereErrorSecond,
			ommp401OduTcm6NonConsecutiveSevereErrorSecond,
			ommp401OduTcm6PathAvailabilityStatus,
			ommp401OduTcm6BackgroundBlockErrorRatio,
			ommp401OduTcm6SevereErrorSecondsErrorRatio,
			ommp401OduTcm6FarEndErrorFreeSeconds,
			ommp401OduTcm6FarEndErrorSeconds,
			ommp401OduTcm6FarEndBackgroundBlockErrors,
			ommp401OduTcm6FarEndSevereErrorSeconds,
			ommp401OduTcm6FarEndUnavailableSeconds,
			ommp401OduTcm6FarEndErrorFreePeriod,
			ommp401OduTcm6FarEndErroredPeriod,
			ommp401OduTcm6FarEndConsecutiveSevereErrorSecond,
			ommp401OduTcm6FarEndNonConsecutiveSevereErrorSecond,
			ommp401OduTcm6FarEndPathAvailabilityStatus,
			ommp401OduTcm6FarEndBackgroundBlockErrorRatio,
			ommp401OduTcm6FarEndSevereErrorSecondsErrorRatio,
			ommp401EthernetMacTerminatedFramesTransmitted,
			ommp401EthernetMacTerminatedFramesReceived,
			ommp401EthernetMacTerminatedPauseFramesTransmitted,
			ommp401EthernetMacTerminatedPauseFramesReceived,
			ommp401EthernetMacTerminatedUnicastFramesTransmitted,
			ommp401EthernetMacTerminatedUnicastFramesReceived,
			ommp401EthernetMacTerminatedMulticastFramesTransmitted,
			ommp401EthernetMacTerminatedMulticastFramesReceived,
			ommp401EthernetMacTerminatedBroadcastFramesTransmitted,
			ommp401EthernetMacTerminatedBroadcastFramesReceived,
			ommp401EthernetMacTerminatedUnderSizeFramesTransmitted,
			ommp401EthernetMacTerminatedUnderSizeFramesReceived,
			ommp401EthernetMacTerminatedOverSizeFramesTransmitted,
			ommp401EthernetMacTerminatedOverSizeFramesReceived,
			ommp401EthernetMacTerminatedFragmentFramesTransmitted,
			ommp401EthernetMacTerminatedFragmentFramesReceived,
			ommp401EthernetMacTerminatedFrameCheckSequenceErrorsTransmitted,
			ommp401EthernetMacTerminatedFrameCheckSequenceErrorsReceived,
			ommp401EthernetMacTerminatedBytesTransmitted,
			ommp401EthernetMacTerminatedBytesReceived,
			ommp401EthernetMacTerminatedJabberFramesTransmitted,
			ommp401EthernetMacTerminatedJabberFramesReceived,
			ommp401EthernetMacTerminated64BytesFramesTransmitted,
			ommp401EthernetMacTerminated64BytesFramesReceived,
			ommp401EthernetMacTerminated65to127BytesFramesTransmitted,
			ommp401EthernetMacTerminated65to127BytesFramesReceived,
			ommp401EthernetMacTerminated128to255BytesFramesTransmitted,
			ommp401EthernetMacTerminated128to255BytesFramesReceived,
			ommp401EthernetMacTerminated256to511BytesFramesTransmitted,
			ommp401EthernetMacTerminated256to511BytesFramesReceived,
			ommp401EthernetMacTerminated512to1023BytesFramesTransmitted,
			ommp401EthernetMacTerminated512to1023BytesFramesReceived,
			ommp401EthernetMacTerminated1024to1518BytesFramesTransmitted,
			ommp401EthernetMacTerminated1024to1518BytesFramesReceived,
			ommp401EthernetMacTerminated1519toMaxBytesFramesTransmitted,
			ommp401EthernetMacTerminated1519toMaxBytesFramesReceived,
			ommp401EthernetMacTerminatedJumboFramesTransmitted,
			ommp401EthernetMacTerminatedJumboFramesReceived,
			ommp401LineOtnFecUncorrectedWords,
			ommp401LineOtnFecCorrectedBits,
			ommp401LineOtnFecZerosCorrectedBits,
			ommp401LineOtnFecOnesCorrectedBits,
			ommp401LineOtuBitInterleavedParityErrors,
			ommp401LineOtuIncomingAlignmentErrorSeconds,
			ommp401LineOtuBackwardErrorIndicationErrorCount,
			ommp401LineOtuBackwardIncomingAlignmentErrorSeconds,
			ommp401LineOtuErrorFreeSeconds,
			ommp401LineOtuErrorSeconds,
			ommp401LineOtuBackgroundBlockErrors,
			ommp401LineOtuSevereErrorSeconds,
			ommp401LineOtuUnavailableSeconds,
			ommp401LineOtuErrorSecondsErrorRatio,
			ommp401LineOtuErrorFreePeriod,
			ommp401LineOtuErroredPeriod,
			ommp401LineOtuConsecutiveSevereErrorSecond,
			ommp401LineOtuNonConsecutiveSevereErrorSecond,
			ommp401LineOtuPathAvailabilityStatus,
			ommp401LineOtuBackgroundBlockErrorRatio,
			ommp401LineOtuSevereErrorSecondsErrorRatio,
			ommp401LineOtuFarEndErrorFreeSeconds,
			ommp401LineOtuFarEndBackgroundBlockErrors,
			ommp401LineOtuFarEndSevereErrorSeconds,
			ommp401LineOtuFarEndUnavailableSeconds,
			ommp401LineOtuFarEndErrorSecondsErrorRatio,
			ommp401LineOtuFarEndErrorSeconds,
			ommp401LineOtuFarEndBackgroundBlockErrorRatio,
			ommp401LineOtuFarEndSevereErrorSecondsErrorRatio,
			ommp401LineOtuErrorRatio,
			ommp401LineOtuFarEndErrorFreePeriod,
			ommp401LineOtuFarEndErroredPeriod,
			ommp401LineOtuFarEndConsecutiveSevereErrorSecond,
			ommp401LineOtuFarEndNonConsecutiveSevereErrorSecond,
			ommp401LineOtuFarEndPathAvailabilityStatus,
			ommp401LineOtuFramesReceived,
			ommp401LineOtuBitErrorRate,
			ommp401LineOduBitInterleavedParityErrors,
			ommp401LineOduTcm1BitInterleavedParityErrors,
			ommp401LineOduTcm2BitInterleavedParityErrors,
			ommp401LineOduTcm3BitInterleavedParityErrors,
			ommp401LineOduTcm4BitInterleavedParityErrors,
			ommp401LineOduTcm5BitInterleavedParityErrors,
			ommp401LineOduTcm6BitInterleavedParityErrors,
			ommp401LineOduTcm1IncomingAlignmentErrorSeconds,
			ommp401LineOduBackwardErrorIndicationErrorCount,
			ommp401LineOduTcm1BackwardErrorIndicationErrorCount,
			ommp401LineOduTcm2BackwardErrorIndicationErrorCount,
			ommp401LineOduTcm3BackwardErrorIndicationErrorCount,
			ommp401LineOduTcm4BackwardErrorIndicationErrorCount,
			ommp401LineOduTcm5BackwardErrorIndicationErrorCount,
			ommp401LineOduTcm6BackwardErrorIndicationErrorCount,
			ommp401LineOduTcm1BackwardIncomingAlignmentErrorSeconds,
			ommp401LineOduDelayMeasurement,
			ommp401LineOduErrorFreeSeconds,
			ommp401LineOduErrorSeconds,
			ommp401LineOduBackgroundBlockErrors,
			ommp401LineOduSevereErrorSeconds,
			ommp401LineOduUnavailableSeconds,
			ommp401LineOduErrorFreePeriod,
			ommp401LineOduErroredPeriod,
			ommp401LineOduConsecutiveSevereErrorSecond,
			ommp401LineOduNonConsecutiveSevereErrorSecond,
			ommp401LineOduPathAvailabilityStatus,
			ommp401LineOduFarEndErrorFreePeriod,
			ommp401LineOduFarEndErroredPeriod,
			ommp401LineOduFarEndConsecutiveSevereErrorSecond,
			ommp401LineOduFarEndNonConsecutiveSevereErrorSecond,
			ommp401LineOduFarEndPathAvailabilityStatus,
			ommp401LineOduFramesReceived,
			ommp401LineOduErrorSecondsErrorRatio,
			ommp401LineOduBackgroundBlockErrorRatio,
			ommp401LineOduSevereErrorSecondsErrorRatio,
			ommp401LineOduFarEndErrorFreeSeconds,
			ommp401LineOduFarEndErrorSeconds,
			ommp401LineOduFarEndBackgroundBlockErrors,
			ommp401LineOduFarEndSevereErrorSeconds,
			ommp401LineOduFarEndUnavailableSeconds,
			ommp401LineOduFarEndErrorSecondsErrorRatio,
			ommp401LineOduFarEndBackgroundBlockErrorRatio,
			ommp401LineOduFarEndSevereErrorSecondsErrorRatio,
			ommp401LineOtnMeasurementPeriod,
			ommp401LineOduTcm1ErrorFreeSeconds,
			ommp401LineOduTcm1ErrorSeconds,
			ommp401LineOduTcm1BackgroundBlockErrors,
			ommp401LineOduTcm1SevereErrorSeconds,
			ommp401LineOduTcm1UnavailableSeconds,
			ommp401LineOduTcm1ErrorFreePeriod,
			ommp401LineOduTcm1ErroredPeriod,
			ommp401LineOduTcm1ConsecutiveSevereErrorSecond,
			ommp401LineOduTcm1NonConsecutiveSevereErrorSecond,
			ommp401LineOduTcm1PathAvailabilityStatus,
			ommp401LineOduTcm1BackgroundBlockErrorRatio,
			ommp401LineOduTcm1SevereErrorSecondsErrorRatio,
			ommp401LineOduTcm1FarEndErrorFreeSeconds,
			ommp401LineOduTcm1FarEndErrorSeconds,
			ommp401LineOduTcm1FarEndBackgroundBlockErrors,
			ommp401LineOduTcm1FarEndSevereErrorSeconds,
			ommp401LineOduTcm1FarEndUnavailableSeconds,
			ommp401LineOduTcm1FarEndErrorFreePeriod,
			ommp401LineOduTcm1FarEndErroredPeriod,
			ommp401LineOduTcm1FarEndConsecutiveSevereErrorSecond,
			ommp401LineOduTcm1FarEndNonConsecutiveSevereErrorSecond,
			ommp401LineOduTcm1FarEndPathAvailabilityStatus,
			ommp401LineOduTcm1FarEndBackgroundBlockErrorRatio,
			ommp401LineOduTcm1FarEndSevereErrorSecondsErrorRatio,
			ommp401LineOduTcm2ErrorFreeSeconds,
			ommp401LineOduTcm2ErrorSeconds,
			ommp401LineOduTcm2BackgroundBlockErrors,
			ommp401LineOduTcm2SevereErrorSeconds,
			ommp401LineOduTcm2UnavailableSeconds,
			ommp401LineOduTcm2ErrorFreePeriod,
			ommp401LineOduTcm2ErroredPeriod,
			ommp401LineOduTcm2ConsecutiveSevereErrorSecond,
			ommp401LineOduTcm2NonConsecutiveSevereErrorSecond,
			ommp401LineOduTcm2PathAvailabilityStatus,
			ommp401LineOduTcm2BackgroundBlockErrorRatio,
			ommp401LineOduTcm2SevereErrorSecondsErrorRatio,
			ommp401LineOduTcm2FarEndErrorFreeSeconds,
			ommp401LineOduTcm2FarEndErrorSeconds,
			ommp401LineOduTcm2FarEndBackgroundBlockErrors,
			ommp401LineOduTcm2FarEndSevereErrorSeconds,
			ommp401LineOduTcm2FarEndUnavailableSeconds,
			ommp401LineOduTcm2FarEndErrorFreePeriod,
			ommp401LineOduTcm2FarEndErroredPeriod,
			ommp401LineOduTcm2FarEndConsecutiveSevereErrorSecond,
			ommp401LineOduTcm2FarEndNonConsecutiveSevereErrorSecond,
			ommp401LineOduTcm2FarEndPathAvailabilityStatus,
			ommp401LineOduTcm2FarEndBackgroundBlockErrorRatio,
			ommp401LineOduTcm2FarEndSevereErrorSecondsErrorRatio,
			ommp401LineOduTcm3ErrorFreeSeconds,
			ommp401LineOduTcm3ErrorSeconds,
			ommp401LineOduTcm3BackgroundBlockErrors,
			ommp401LineOduTcm3SevereErrorSeconds,
			ommp401LineOduTcm3UnavailableSeconds,
			ommp401LineOduTcm3ErrorFreePeriod,
			ommp401LineOduTcm3ErroredPeriod,
			ommp401LineOduTcm3ConsecutiveSevereErrorSecond,
			ommp401LineOduTcm3NonConsecutiveSevereErrorSecond,
			ommp401LineOduTcm3PathAvailabilityStatus,
			ommp401LineOduTcm3BackgroundBlockErrorRatio,
			ommp401LineOduTcm3SevereErrorSecondsErrorRatio,
			ommp401LineOduTcm3FarEndErrorFreeSeconds,
			ommp401LineOduTcm3FarEndErrorSeconds,
			ommp401LineOduTcm3FarEndBackgroundBlockErrors,
			ommp401LineOduTcm3FarEndSevereErrorSeconds,
			ommp401LineOduTcm3FarEndUnavailableSeconds,
			ommp401LineOduTcm3FarEndErrorFreePeriod,
			ommp401LineOduTcm3FarEndErroredPeriod,
			ommp401LineOduTcm3FarEndConsecutiveSevereErrorSecond,
			ommp401LineOduTcm3FarEndNonConsecutiveSevereErrorSecond,
			ommp401LineOduTcm3FarEndPathAvailabilityStatus,
			ommp401LineOduTcm3FarEndBackgroundBlockErrorRatio,
			ommp401LineOduTcm3FarEndSevereErrorSecondsErrorRatio,
			ommp401LineOduTcm4ErrorFreeSeconds,
			ommp401LineOduTcm4ErrorSeconds,
			ommp401LineOduTcm4BackgroundBlockErrors,
			ommp401LineOduTcm4SevereErrorSeconds,
			ommp401LineOduTcm4UnavailableSeconds,
			ommp401LineOduTcm4ErrorFreePeriod,
			ommp401LineOduTcm4ErroredPeriod,
			ommp401LineOduTcm4ConsecutiveSevereErrorSecond,
			ommp401LineOduTcm4NonConsecutiveSevereErrorSecond,
			ommp401LineOduTcm4PathAvailabilityStatus,
			ommp401LineOduTcm4BackgroundBlockErrorRatio,
			ommp401LineOduTcm4SevereErrorSecondsErrorRatio,
			ommp401LineOduTcm4FarEndErrorFreeSeconds,
			ommp401LineOduTcm4FarEndErrorSeconds,
			ommp401LineOduTcm4FarEndBackgroundBlockErrors,
			ommp401LineOduTcm4FarEndSevereErrorSeconds,
			ommp401LineOduTcm4FarEndUnavailableSeconds,
			ommp401LineOduTcm4FarEndErrorFreePeriod,
			ommp401LineOduTcm4FarEndErroredPeriod,
			ommp401LineOduTcm4FarEndConsecutiveSevereErrorSecond,
			ommp401LineOduTcm4FarEndNonConsecutiveSevereErrorSecond,
			ommp401LineOduTcm4FarEndPathAvailabilityStatus,
			ommp401LineOduTcm4FarEndBackgroundBlockErrorRatio,
			ommp401LineOduTcm4FarEndSevereErrorSecondsErrorRatio,
			ommp401LineOduTcm5ErrorFreeSeconds,
			ommp401LineOduTcm5ErrorSeconds,
			ommp401LineOduTcm5BackgroundBlockErrors,
			ommp401LineOduTcm5SevereErrorSeconds,
			ommp401LineOduTcm5UnavailableSeconds,
			ommp401LineOduTcm5ErrorFreePeriod,
			ommp401LineOduTcm5ErroredPeriod,
			ommp401LineOduTcm5ConsecutiveSevereErrorSecond,
			ommp401LineOduTcm5NonConsecutiveSevereErrorSecond,
			ommp401LineOduTcm5PathAvailabilityStatus,
			ommp401LineOduTcm5BackgroundBlockErrorRatio,
			ommp401LineOduTcm5SevereErrorSecondsErrorRatio,
			ommp401LineOduTcm5FarEndErrorFreeSeconds,
			ommp401LineOduTcm5FarEndErrorSeconds,
			ommp401LineOduTcm5FarEndBackgroundBlockErrors,
			ommp401LineOduTcm5FarEndSevereErrorSeconds,
			ommp401LineOduTcm5FarEndUnavailableSeconds,
			ommp401LineOduTcm5FarEndErrorFreePeriod,
			ommp401LineOduTcm5FarEndErroredPeriod,
			ommp401LineOduTcm5FarEndConsecutiveSevereErrorSecond,
			ommp401LineOduTcm5FarEndNonConsecutiveSevereErrorSecond,
			ommp401LineOduTcm5FarEndPathAvailabilityStatus,
			ommp401LineOduTcm5FarEndBackgroundBlockErrorRatio,
			ommp401LineOduTcm5FarEndSevereErrorSecondsErrorRatio,
			ommp401LineOduTcm6ErrorFreeSeconds,
			ommp401LineOduTcm6ErrorSeconds,
			ommp401LineOduTcm6BackgroundBlockErrors,
			ommp401LineOduTcm6SevereErrorSeconds,
			ommp401LineOduTcm6UnavailableSeconds,
			ommp401LineOduTcm6ErrorFreePeriod,
			ommp401LineOduTcm6ErroredPeriod,
			ommp401LineOduTcm6ConsecutiveSevereErrorSecond,
			ommp401LineOduTcm6NonConsecutiveSevereErrorSecond,
			ommp401LineOduTcm6PathAvailabilityStatus,
			ommp401LineOduTcm6BackgroundBlockErrorRatio,
			ommp401LineOduTcm6SevereErrorSecondsErrorRatio,
			ommp401LineOduTcm6FarEndErrorFreeSeconds,
			ommp401LineOduTcm6FarEndErrorSeconds,
			ommp401LineOduTcm6FarEndBackgroundBlockErrors,
			ommp401LineOduTcm6FarEndSevereErrorSeconds,
			ommp401LineOduTcm6FarEndUnavailableSeconds,
			ommp401LineOduTcm6FarEndErrorFreePeriod,
			ommp401LineOduTcm6FarEndErroredPeriod,
			ommp401LineOduTcm6FarEndConsecutiveSevereErrorSecond,
			ommp401LineOduTcm6FarEndNonConsecutiveSevereErrorSecond,
			ommp401LineOduTcm6FarEndPathAvailabilityStatus,
			ommp401LineOduTcm6FarEndBackgroundBlockErrorRatio,
			ommp401LineOduTcm6FarEndSevereErrorSecondsErrorRatio,
			ommp401PerformanceTableRowStatus
		}
    STATUS  current
    DESCRIPTION
            "A collection of objects from RFC 1213 made current by this MIB module."
    ::= { utlrnd 2 }

	
END

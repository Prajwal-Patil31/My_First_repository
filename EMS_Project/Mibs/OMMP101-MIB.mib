--*****************************************************************************
--			MIB FILE FOR THE OMMP101 CARD
--*****************************************************************************

OMMP101-MIB DEFINITIONS ::= BEGIN
 
          IMPORTS
        	
		RowStatus      			FROM STANDARD-MIB
			
		DisplayString  			FROM RFC1213-MIB       
    	
    		OBJECT-IDENTITY,
    		NOTIFICATION-TYPE,
    		MODULE-IDENTITY,
    		Integer32,
    		Unsigned32,
    		IpAddress,
    		TimeTicks			FROM SNMPv2-SMI
	 
	 	OBJECT-TYPE    			FROM RFC-1212
	 		
		MODULE-COMPLIANCE,
		OBJECT-GROUP,
		NOTIFICATION-GROUP		FROM SNMPv2-CONF
	
		node,
		rack,
		subRack,
		slot				FROM SCC-MIB
    
		enterprises			FROM RFC1155-SMI
	;

 

	utl   MODULE-IDENTITY
            LAST-UPDATED    	"1807130630Z"
            ORGANIZATION    	"United Telecoms Limited, Bangalore-560048."
            CONTACT-INFO    	"Website: http://www.utlindia.com."                                           
            DESCRIPTION     	"MIB module for UTL 40/80 channel DWDM."
            REVISION 	    	"1807130630Z"
            DESCRIPTION    	"MIB module for OMMP101 Card."
            ::= { enterprises 18036 }

	utlrnd  OBJECT-IDENTITY
            STATUS  current
            DESCRIPTION "UTL Research and Development."
            ::= { utl 1 }

	dwdm 	OBJECT IDENTIFIER				::=	{ utlrnd 1 }
	indus 	OBJECT IDENTIFIER				::=	{ dwdm 1 }
	ommp101 	OBJECT IDENTIFIER 			::=	{ indus 88 }

	ommp101CardGeneralDetails OBJECT IDENTIFIER		::=	{ ommp101 1 }
	ommp101Configuration OBJECT IDENTIFIER 		::=	{ ommp101 2 }
	ommp101Alarm OBJECT IDENTIFIER 			::=	{ ommp101 3 }
	ommp101Performance OBJECT IDENTIFIER 		::=	{ ommp101 4 }
	ommp101Diagnostics OBJECT IDENTIFIER 		::=	{ ommp101 5 }

	ommp101AlarmQuery OBJECT IDENTIFIER			::=	{ ommp101Alarm 1 }
	ommp101AlarmNotification OBJECT IDENTIFIER		::=	{ ommp101Alarm 2 }

--*****************************************************************************
--				CARD GENERAL DETAILS
--*****************************************************************************

	ommp101CardGeneralDetailsTable OBJECT-TYPE
		SYNTAX  SEQUENCE OF Ommp101CardGeneralDetailsEntry 
		MAX-ACCESS  not-accessible
		STATUS  current
		DESCRIPTION
                     "Contains card general details' queries for the OMMP101 card"
		::= { ommp101CardGeneralDetails 1 }

	ommp101CardGeneralDetailsEntry  OBJECT-TYPE
		SYNTAX  Ommp101CardGeneralDetailsEntry 
		MAX-ACCESS  not-accessible
		STATUS  current
		DESCRIPTION 
              	""
		INDEX   { node, rack, subRack, slot, ommp101InterfaceNumber }
		::= { ommp101CardGeneralDetailsTable 1 }

	Ommp101CardGeneralDetailsEntry  ::= 
		SEQUENCE {
				ommp101InterfaceNumber					INTEGER,
				ommp101EepromCardId					        INTEGER,
				ommp101EepromCardName					DisplayString,
				ommp101EepromPartCode					DisplayString,
				ommp101EepromCardSerialNumber				DisplayString,
				ommp101EepromHardwareExternalReleaseVersion		        DisplayString,
				ommp101SoftwareExternalReleaseVersion		        DisplayString,
				ommp101EepromHardwareInternalReleaseVersion		        DisplayString,
				ommp101SoftwareInternalReleaseVersion		        DisplayString,
				ommp101EepromCardUidNumber			                DisplayString,
				ommp101EepromCardEui48Number				        DisplayString,
				ommp101EepromCardEui64Number				        DisplayString,
				ommp101CardInstallationDate				        DisplayString,
				ommp101CardCommissionDate				        DisplayString,
				ommp101CardRunningTime					DisplayString,
				ommp101CardRestartCount					INTEGER,
				ommp101Cfp2ReadyForOperation				        INTEGER,
				ommp101Cfp2VendorName					        DisplayString,
				ommp101Cfp2VendorIeeeId					DisplayString,
				ommp101Cfp2PartNumber					        DisplayString,
				ommp101Cfp2SerialNumber					DisplayString,
				ommp101Cfp2ManufacturingDate				        DisplayString,
				ommp101Cfp2HardwareVersionNumber			 DisplayString,
				ommp101Cfp2FirmwareVersionNumber			 DisplayString,
				ommp101Cfp2MediaType					 DisplayString,
				ommp101NumberOfNetworkLanesInCfp2			 INTEGER,
				ommp101NumberOfHostLanesInCfp2				 INTEGER,
				ommp101Cfp2ModuleId					 DisplayString,
				ommp101Cfp2PowerClass					 INTEGER,
				ommp101Cfp2ProductCodeValue				 INTEGER,
				ommp101Cfp2WavelengthTunabilitySupported			INTEGER,
				ommp101TunableCfp2LaserFirstFrequency			        DisplayString,
				ommp101TunableCfp2LaserLastFrequency			        DisplayString,
				ommp101Cfp2ConnectorType					DisplayString,
				ommp101Cfp2SignalEncodingTypeSupported			DisplayString,
				ommp101Cfp2MaximumBitrateSupported			        DisplayString,
				ommp101Cfp2MaximumCaseTemperatureSupported		        INTEGER,
				ommp101Cfp2MinimumCaseTemperatureSupported		        DisplayString,
				ommp101Cfp2ActiveWavelengthControlSupported			INTEGER,
				ommp101Cfp2TransmitterIsCooledOrUncooled			INTEGER,
				ommp101SfpPlusEepromPage						INTEGER,
				ommp101CheckCodeOfSfpPlusEepromPage				INTEGER,
				ommp101ExtendedCheckCodeOfSfpPlusEepromPage			INTEGER,
				ommp101SfpPlusVendorName						DisplayString,
				ommp101SfpPlusVendorIeeeId					DisplayString,
				ommp101SfpPlusPartNumber						DisplayString,
				ommp101SfpPlusSerialNumber					DisplayString,
				ommp101SfpPlusRevisionNumber					DisplayString,
				ommp101SfpPlusManufacturingDate					DisplayString,
				ommp101FixedSfpPlusLaserWavelength				DisplayString,
				ommp101SfpPlusConnectorType					DisplayString,
				ommp101SfpPlusLinkLength						DisplayString,
				ommp101SfpPlusSignalEncodingTypeSupported			INTEGER,
				ommp101SfpPlusTransceiverCodesSupported				DisplayString,
				ommp101SfpPlusMaximumBitrateSupported				DisplayString,
				ommp101SfpPlusNominalBitrateSupported				DisplayString,
				ommp101SfpPlusMinimumBitrateSupported				DisplayString,
				ommp101CardGeneralDetailsTableRowStatus			RowStatus
			 }
	

	ommp101InterfaceNumber OBJECT-TYPE
		SYNTAX  INTEGER
		MAX-ACCESS  not-accessible
		STATUS  current
		DESCRIPTION
			"Interface number represents the port number.
			InterfaceNumber to port mapping is as follows:
			1 - CLIENT-1,
			2 - CLIENT-2,
			3 - CLIENT-3,
			4 - CLIENT-4,
			5 - CLIENT-5,
			6 - CLIENT-6,
			7 - CLIENT-7,
			8 - CLIENT-8,
			9 - CLIENT-9,
			10 - CLIENT-10,
			11 - LINE PORT
			-----------------------------
			Values of the demultiplexing properties can be accessed
			with respect to slice number.  In such cases the
			InterfaceNumber will represent the slice number.
			1 - Slice-1
			2 - Slice-2
			3 - Slice-3
			4 - Slice-4
			-----------------------------
			For properties which do not apply on any interface,
			the interface number must be passed as 0
			-----------------------------"
		::= { ommp101CardGeneralDetailsEntry 1 }
	
	ommp101EepromCardId OBJECT-TYPE		 
		SYNTAX  INTEGER
		MAX-ACCESS  read-only
		STATUS current
		DESCRIPTION
			"Tells the card ID of the OMMP101 card, present in the EEPROM
			-----------------------------
			ommp101InterfaceNumber: 0
			-----------------------------"
		::= { ommp101CardGeneralDetailsEntry 2 }

	ommp101EepromCardName OBJECT-TYPE		 
		SYNTAX  DisplayString
		MAX-ACCESS  read-only
		STATUS current
		DESCRIPTION
			"Tells the card name of the OMMP101 card, present in the EEPROM
			-----------------------------
			ommp101InterfaceNumber: 0
			-----------------------------"
		::= { ommp101CardGeneralDetailsEntry 3 }

	ommp101EepromPartCode OBJECT-TYPE		 
		SYNTAX  DisplayString
		MAX-ACCESS  read-only
		STATUS current
		DESCRIPTION
			"Tells the part code of the OMMP101 card, present in the EEPROM
			-----------------------------
			ommp101InterfaceNumber: 0
			-----------------------------"
		::= { ommp101CardGeneralDetailsEntry 4 }

	ommp101EepromCardSerialNumber OBJECT-TYPE		 
		SYNTAX  DisplayString
		MAX-ACCESS  read-write
		STATUS current
		DESCRIPTION
			"This property get / set the information about 
			OMMP101 Card's Serial Number.
			-----------------------------
			ommp101InterfaceNumber: 0
			-----------------------------
			Values:
			eg: 123456
			-----------------------------"
		::= { ommp101CardGeneralDetailsEntry 5 }

	ommp101EepromHardwareExternalReleaseVersion OBJECT-TYPE		 
		SYNTAX  DisplayString
		MAX-ACCESS  read-only
		STATUS current
		DESCRIPTION
			"Gets the Card's Hardware External Release Version. 
			This detail will be displayed to the customer.
			This version will increment only if there are significant
			architectural changes in the product
			-----------------------------
			ommp101InterfaceNumber: 0
			-----------------------------
			Value:
			eg: 0.1
			-----------------------------"
		::= { ommp101CardGeneralDetailsEntry 6 }

	ommp101SoftwareExternalReleaseVersion OBJECT-TYPE		 
		SYNTAX  DisplayString
		MAX-ACCESS  read-only
		STATUS current
		DESCRIPTION
			"Gets the Card's Software External Release Version. 
			This detail will be displayed to the customer.
			This version will increment only if there are
			significant architectural changes in the product
			-----------------------------
			ommp101InterfaceNumber: 0
			-----------------------------
			Value:
			eg: 0.1
			-----------------------------"
		::= { ommp101CardGeneralDetailsEntry 7 }

	ommp101EepromHardwareInternalReleaseVersion OBJECT-TYPE		 
		SYNTAX  DisplayString
		MAX-ACCESS  read-only
		STATUS current
		DESCRIPTION
			"Gets the Card's Hardware Internal Release Version.
			This detail is used for development purposes only.
			It differs from the external hardware version.
			-----------------------------
			ommp101InterfaceNumber: 0
			-----------------------------
			Value:
			eg: 4.1
			-----------------------------"
		::= { ommp101CardGeneralDetailsEntry 8 }

	ommp101SoftwareInternalReleaseVersion OBJECT-TYPE		 
		SYNTAX  DisplayString
		MAX-ACCESS  read-only
		STATUS current
		DESCRIPTION
			"Gets the Card's Software Internal Release Version.
			This detail is used for development purposes only.
			It differs from the external software version.
		      	-----------------------------
			ommp101InterfaceNumber: 0
			-----------------------------
			Value:
			eg: 5.1
			-----------------------------"
		::= { ommp101CardGeneralDetailsEntry 9 }

	ommp101EepromCardUidNumber OBJECT-TYPE		 
		SYNTAX  DisplayString
		MAX-ACCESS  read-only
		STATUS current
		DESCRIPTION
			"Tells the Card Unique IDentifier. It is a 4 byte
			address used to uniquely identify a card.
			----------------------------
			ommp101InterfaceNumber: 0
			------------------------------
			Value:
		      	eg: 12345678
			-----------------------------"
		::= { ommp101CardGeneralDetailsEntry 10 }

	ommp101EepromCardEui48Number OBJECT-TYPE		 
		SYNTAX  DisplayString
		MAX-ACCESS  read-only
		STATUS current
		DESCRIPTION
			"Tells the Card EUI-48 Number. It is a 6 byte address
			used to uniquely identify a card.
			-----------------------------
			ommp101InterfaceNumber: 0
			-----------------------------
			Value:
		      	eg: 0004A3123456
			-----------------------------"
		::= { ommp101CardGeneralDetailsEntry 11 }

	ommp101EepromCardEui64Number OBJECT-TYPE		 
		SYNTAX  DisplayString
		MAX-ACCESS  read-only
		STATUS current
		DESCRIPTION
			"Tells the Card EUI-64 Number. It is a 8 byte address
			used to uniquely identify a card.
			-----------------------------
			ommp101InterfaceNumber: 0
			-----------------------------
			Value:
		      	eg: 0004A31234567890
			-----------------------------"
		::= { ommp101CardGeneralDetailsEntry 12 }

	ommp101CardInstallationDate OBJECT-TYPE		 
		SYNTAX  DisplayString
		MAX-ACCESS  read-write
		STATUS current
		DESCRIPTION
			"Gets the card's installation date in
			dd/mm/yyyy format
			-----------------------------
			ommp101InterfaceNumber: 0
			-----------------------------
			Value:
		      	eg: 12/03/2016
			-----------------------------"
		::= { ommp101CardGeneralDetailsEntry 13 }

	ommp101CardCommissionDate OBJECT-TYPE		 
		SYNTAX  DisplayString
		MAX-ACCESS  read-write
		STATUS current
		DESCRIPTION
			"Gets the card's commission date in
			dd/mm/yyyy format
			-----------------------------
			ommp101InterfaceNumber: 0
			-----------------------------
			Value:
		      	eg: 20/03/2016
			-----------------------------"
		::= { ommp101CardGeneralDetailsEntry 14 }

	ommp101CardRunningTime OBJECT-TYPE		 
		SYNTAX  DisplayString
		MAX-ACCESS  read-only
		STATUS current
		DESCRIPTION
			"Get the duration of time for which the card is
			operational/running
			-----------------------------
			ommp101InterfaceNumber: 0
			-----------------------------
			Values:
		      	eg: 4d:3h:2m:1s
			-----------------------------"
		::= { ommp101CardGeneralDetailsEntry 15 }

	ommp101CardRestartCount OBJECT-TYPE		 
		SYNTAX  INTEGER
		MAX-ACCESS  read-only
		STATUS current
		DESCRIPTION
			"Get the number of times the card has been soft reset.
			This value will get reset to 0 on factory reset.
			-----------------------------
			ommp101InterfaceNumber: 0
			-----------------------------
			Values:
		      	eg: 10
			-----------------------------"
		::= { ommp101CardGeneralDetailsEntry 16 }

	ommp101Cfp2ReadyForOperation OBJECT-TYPE		 
		SYNTAX  INTEGER
		MAX-ACCESS  read-only
		STATUS current
		DESCRIPTION
			"Module not ready indicates that the CFP2
			has detected a condition that tells
			transmit or receive data is invalid.
			It shall consist of logical OR of the
			following signals:
			> Transmit Signal Conditioner Loss of Lock
			> Transmitter Laser Fault
			> Receiver Signal Conditioner Loss of Lock
			(Ref: INF-8077 2.4.1)
			-----------------------------
			ommp101InterfaceNumber:
			11 - LINE PORT
			-----------------------------
			Values:		
			1 - CFP2 is ready for operation 
			0 - CFP2 is not ready for operation
			-----------------------------"
		::= { ommp101CardGeneralDetailsEntry 17 }

	ommp101Cfp2VendorName OBJECT-TYPE		 
		SYNTAX  DisplayString
		MAX-ACCESS  read-only
		STATUS current
		DESCRIPTION
			"This property provides Vendor Name for given CFP2. 
			The vendor name shall be the full name of the 
			corporation, a commonly accepted abbreviation of 
			the name of the corporation, the SCSI company code
			for the corporation, or the stock exchange code for
			the corporation.
			-----------------------------
			ommp101InterfaceNumber:
			11 - LINE PORT
			-----------------------------
			Values:			
			eg: WTD
			-----------------------------"
		::= { ommp101CardGeneralDetailsEntry 18 }

	ommp101Cfp2VendorIeeeId OBJECT-TYPE		 
		SYNTAX  DisplayString
		MAX-ACCESS  read-only
		STATUS current
		DESCRIPTION
			"This property defines the IEEE company Identifier for
			the vendor of CFP2. A value of all zero in the 3-byte
			field indicates that the Vendor OUI is unspecified.
			-----------------------------
			ommp101InterfaceNumber:
			11 - LINE PORT
			-----------------------------
			Values:			
			eg: 010
			-----------------------------"
		::= { ommp101CardGeneralDetailsEntry 19 }

	ommp101Cfp2PartNumber OBJECT-TYPE		 
		SYNTAX  DisplayString
		MAX-ACCESS  read-only
		STATUS current
		DESCRIPTION
			"This property defines the vendor part number or
			product name of the CFP2. A value of all zero
			indicates that the vendor Part Number is unspecified.
			-----------------------------
			ommp101InterfaceNumber:
			11 - LINE PORT
			-----------------------------
			Values:			
			eg: FTRX-1811-2D2
			-----------------------------"
		::= { ommp101CardGeneralDetailsEntry 20 }

	ommp101Cfp2SerialNumber OBJECT-TYPE		 
		SYNTAX  DisplayString
		MAX-ACCESS  read-only
		STATUS current
		DESCRIPTION
			"This property provides vendor serial number defining
			the vendors serial number for the CFP2. A value of all
			zero in the 16-byte field indicates that the vendor
			serial number is unspecified.
			-----------------------------
			ommp101InterfaceNumber:
			11 - LINE PORT
			-----------------------------
			Values:			
			eg: KBG02CU
			-----------------------------"
		::= { ommp101CardGeneralDetailsEntry 21 }

	ommp101Cfp2ManufacturingDate OBJECT-TYPE		 
		SYNTAX  DisplayString
		MAX-ACCESS  read-only
		STATUS current
		DESCRIPTION
			"This property defines the manufacturing date for 
			CFP2. A value of 8-byte field in ASCII which represents
			year, month and date of each two bytes. 
			Extra two bytes may be blank
			-----------------------------
			ommp101InterfaceNumber:
			11 - LINE PORT
			-----------------------------
			Values:			
			eg: 160224
			-----------------------------"
		::= { ommp101CardGeneralDetailsEntry 22 }

	ommp101Cfp2HardwareVersionNumber OBJECT-TYPE		 
		SYNTAX  DisplayString
		MAX-ACCESS  read-only
		STATUS current
		DESCRIPTION
			"This property defines the hardware version number for 
			CFP2. A value of 2-byte field which represents
			hardware version number in x.y format. 
			-----------------------------
			ommp101InterfaceNumber:
			11 - LINE PORT
			-----------------------------
			Values:			
			eg: 1.1
			-----------------------------"
		::= { ommp101CardGeneralDetailsEntry 23 }

	ommp101Cfp2FirmwareVersionNumber OBJECT-TYPE		 
		SYNTAX  DisplayString
		MAX-ACCESS  read-only
		STATUS current
		DESCRIPTION
			"This property defines the Firmware version number for 
			CFP2. A value of 2-byte field which represents
			firmware version number in x.y format. 
			-----------------------------
			ommp101InterfaceNumber:
			11 - LINE PORT
			-----------------------------
			Values:			
			eg: 1.1
			-----------------------------"
		::= { ommp101CardGeneralDetailsEntry 24 }

	ommp101Cfp2MediaType OBJECT-TYPE		 
		SYNTAX  DisplayString
		MAX-ACCESS  read-only
		STATUS current
		DESCRIPTION
			"This property defines the Media type for 
			CFP2. A value of 2-Bit field which represents
			media type number. 
			-----------------------------
			ommp101InterfaceNumber:
			11 - LINE PORT
			-----------------------------
			Values:			
			eg: 1
			-----------------------------"
		::= { ommp101CardGeneralDetailsEntry 25 }

	ommp101NumberOfNetworkLanesInCfp2 OBJECT-TYPE		 
		SYNTAX  INTEGER
		MAX-ACCESS  read-only
		STATUS current
		DESCRIPTION
			"This property defines the Number of Network Lanes for 
			CFP2. A value of 4-Bits field which represents
			Number of Network Lanes. 
			-----------------------------
			ommp101InterfaceNumber:
			11 - LINE PORT
			-----------------------------
			Values:			
			eg: 1
			-----------------------------"
		::= { ommp101CardGeneralDetailsEntry 26 }

	ommp101NumberOfHostLanesInCfp2 OBJECT-TYPE		 
		SYNTAX  INTEGER
		MAX-ACCESS  read-only
		STATUS current
		DESCRIPTION
			"This property defines the Number of Network Host for 
			CFP2. A value of 4-Bits field which represents
			Number of Host Lanes.
			-----------------------------
			ommp101InterfaceNumber:
			11 - LINE PORT
			-----------------------------
			Values:			
			eg: 1
			-----------------------------"
		::= { ommp101CardGeneralDetailsEntry 27 }

	ommp101Cfp2ModuleId OBJECT-TYPE		 
		SYNTAX  DisplayString
		MAX-ACCESS  read-only
		STATUS current
		DESCRIPTION
			"This property defines the Module ID for 
			CFP2. A value of 1-Byte field which represents
			Module identifier.
			-----------------------------
			ommp101InterfaceNumber:
			11 - LINE PORT
			-----------------------------
			Values:			
			eg: CFP2-DCO
			-----------------------------"
		::= { ommp101CardGeneralDetailsEntry 28 }

	ommp101Cfp2PowerClass OBJECT-TYPE		 
		SYNTAX  INTEGER
		MAX-ACCESS  read-only
		STATUS current
		DESCRIPTION
			"This property defines the Power Class for 
			CFP2. A value of 2-Bits field which represents
			Power class.
			-----------------------------
			ommp101InterfaceNumber:
			11 - LINE PORT
			-----------------------------
			Values:			
			eg: 1
			-----------------------------"
		::= { ommp101CardGeneralDetailsEntry 29 }

	ommp101Cfp2ProductCodeValue OBJECT-TYPE		 
		SYNTAX  INTEGER
		MAX-ACCESS  read-only
		STATUS current
		DESCRIPTION
			"This property defines the Product code value for 
			CFP2. A value of 7-Bits field which represents
			Product code value.
			-----------------------------
			ommp101InterfaceNumber:
			11 - LINE PORT
			-----------------------------
			Values:			
			eg: 50h
			-----------------------------"
		::= { ommp101CardGeneralDetailsEntry 30 }

	ommp101Cfp2WavelengthTunabilitySupported OBJECT-TYPE		 
		SYNTAX  INTEGER
		MAX-ACCESS  read-only
		STATUS current
		DESCRIPTION
			"This property provides information whether the CFP2
			supports wavelength tunability or not.
			-----------------------------
			ommp101InterfaceNumber:
			11 - LINE PORT
			-----------------------------
			Values:			
			1 - CFP2 supports wavelength tunability
			0 - CFP2 does not supports wavelength tunability
			-----------------------------"
		::= { ommp101CardGeneralDetailsEntry 31 }

	ommp101TunableCfp2LaserFirstFrequency OBJECT-TYPE		 
		SYNTAX  DisplayString
		MAX-ACCESS  read-only
		STATUS current
		DESCRIPTION
			"This property defines the first LASER frequency of CFP2.
			The two byte value is specified in units of THz.
			-----------------------------
			ommp101InterfaceNumber:
			11 - LINE PORT
			-----------------------------
			Values:			
			eg: 1529.45
			-----------------------------"
		::= { ommp101CardGeneralDetailsEntry 32 }

	ommp101TunableCfp2LaserLastFrequency OBJECT-TYPE		 
		SYNTAX  DisplayString
		MAX-ACCESS  read-only
		STATUS current
		DESCRIPTION
			"This property defines the last laser frequency of CFP2.
		 	 The two byte value is specified in units of THz.
			-----------------------------
			ommp101InterfaceNumber:
			11 - LINE PORT
			-----------------------------
			Values:			
			eg: 1563.45
			-----------------------------"
		::= { ommp101CardGeneralDetailsEntry 33 }

	ommp101Cfp2ConnectorType OBJECT-TYPE		 
		SYNTAX  DisplayString
		MAX-ACCESS  read-only
		STATUS current
		DESCRIPTION
			"This property provides information of the CFP2
			connector, value indicates the external connector
			provided on the CFP2.
			-----------------------------
			ommp101InterfaceNumber:
			11 - LINE PORT
			-----------------------------
			Values:
			00h 	Unknown or unspecified
			01h 	SC
			02h 	Fibre Channel Style 1 copper connector
			03h 	Fibre Channel Style 2 copper connector
			04h 	BNC/TNC
			05h 	Fibre Channel coaxial headers
			06h 	FiberJack
			07h 	LC
			08h 	MT-RJ
			09h 	MU
			0Ah 	SG
			0Bh 	Optical pigtail
			0C-1Fh 	Reserved
			20h 	HSSDC II
			21h 	Copper Pigtail
			22h-7Fh Reserved
			80-FFh 	Vendor specific
			-----------------------------"
		::= { ommp101CardGeneralDetailsEntry 35 }

	ommp101Cfp2SignalEncodingTypeSupported OBJECT-TYPE		 
		SYNTAX  DisplayString
		MAX-ACCESS  read-only
		STATUS current
		DESCRIPTION
			"This property indicates the serial encoding mechanisms
			that are supported by the CFP2.
			-----------------------------
			ommp101InterfaceNumber:
			11 - LINE PORT
			-----------------------------
			Values:16QAM:
			-----------------------------"
		::= { ommp101CardGeneralDetailsEntry 36 }

	ommp101Cfp2MaximumBitrateSupported OBJECT-TYPE		 
		SYNTAX  DisplayString
		MAX-ACCESS  read-only
		STATUS current
		DESCRIPTION
			"This property provides maximum bit rate(Gbps) value
			supported by CFP2
			-----------------------------
			ommp101InterfaceNumber:
			11 - LINE PORT
			-----------------------------
			Values: 28
			-----------------------------"
		::= { ommp101CardGeneralDetailsEntry 37 }

	ommp101Cfp2MaximumCaseTemperatureSupported OBJECT-TYPE		 
		SYNTAX  INTEGER
		MAX-ACCESS  read-only
		STATUS current
		DESCRIPTION
			"This property provides the maximum case temperature
			(degree celcius) supported by CFP2.
			-----------------------------
			ommp101InterfaceNumber:
			11 - LINE PORT
			-----------------------------
			Values:
			eg: 70
			-----------------------------"
		::= { ommp101CardGeneralDetailsEntry 38 }

	ommp101Cfp2MinimumCaseTemperatureSupported OBJECT-TYPE		 
		SYNTAX  DisplayString
		MAX-ACCESS  read-only
		STATUS current
		DESCRIPTION
			"This property provides the minimum case temperature
			(degree celcius) supported by CFP2.
			-----------------------------
			ommp101InterfaceNumber:
			11 - LINE PORT
			-----------------------------
			Values:
			eg: 70
			-----------------------------"
		::= { ommp101CardGeneralDetailsEntry 39 }

	ommp101Cfp2ActiveWavelengthControlSupported OBJECT-TYPE		 
		SYNTAX  INTEGER
		MAX-ACCESS  read-only
		STATUS current
		DESCRIPTION
			"This property provides whether the CFP2 wavelength 
			controlling state is active or not
			-----------------------------
			ommp101InterfaceNumber:
			11 - LINE PORT
			-----------------------------
			Values:
			1 - Active
			0 - Inactive
			-----------------------------"
		::= { ommp101CardGeneralDetailsEntry 40 }

	ommp101Cfp2TransmitterIsCooledOrUncooled OBJECT-TYPE		 
		SYNTAX  INTEGER
		MAX-ACCESS  read-only
		STATUS current
		DESCRIPTION
			"This property provide information on which type of
			diode used in transmitter of the CFP2
			-----------------------------
			ommp101InterfaceNumber:
			11 - LINE PORT
			-----------------------------
			Values:
			1 - Cooling circuit supported for CFP2 transmitter. 
			0 - Cooling circuit not supported for CFP2 transmitter.
			-----------------------------"
		::= { ommp101CardGeneralDetailsEntry 41 }

	ommp101SfpPlusEepromPage OBJECT-TYPE		 
		SYNTAX  INTEGER
		MAX-ACCESS  read-write
		STATUS current
		DESCRIPTION
			"This property sets/gets the SFP PLUS EEPROM page, 
			the value represents the SFP PLUS EEPROM page number.
			-----------------------------
			ommp101InterfaceNumber:
			1 to 10 - CLIENT-1 to CLIENT-10
			-----------------------------
			Values:			
			eg: 1(EEPROM Page number)
			-----------------------------"
		::= { ommp101CardGeneralDetailsEntry 42 }

	ommp101CheckCodeOfSfpPlusEepromPage OBJECT-TYPE		 
		SYNTAX  INTEGER
		MAX-ACCESS  read-only
		STATUS current
		DESCRIPTION
			"This property provides the SFP PLUS
			check code(checksum) value for bytes 128 to 190
			present in SFP PLUS EEPROM Page number 1. 
			-----------------------------
			ommp101InterfaceNumber:
			1 to 10 - CLIENT-1 to CLIENT-10
			-----------------------------
			Values:			
			eg: 1(EEPROM Page number)
			-----------------------------"
		::= { ommp101CardGeneralDetailsEntry 43 }

	ommp101ExtendedCheckCodeOfSfpPlusEepromPage OBJECT-TYPE		 
		SYNTAX  INTEGER
		MAX-ACCESS  read-only
		STATUS current
		DESCRIPTION
			"This property provides the SFP PLUS
			extended check code(checksum) value for bytes 192 to 222
			present in SFP PLUS EEPROM Page number 1. 
			-----------------------------
			ommp101InterfaceNumber:
			1 to 10 - CLIENT-1 to CLIENT-10
			-----------------------------
			Values:			
			eg: 1(EEPROM Page number)
			-----------------------------"
		::= { ommp101CardGeneralDetailsEntry 44 }

	ommp101SfpPlusVendorName OBJECT-TYPE		 
		SYNTAX  DisplayString
		MAX-ACCESS  read-only
		STATUS current
		DESCRIPTION
			"This property provides Vendor Name for given SFP PLUS. 
			The vendor name shall be the full name of the 
			corporation, a commonly accepted abbreviation of 
			the name of the corporation, the SCSI company code
			for the corporation, or the stock exchange code for
			the corporation.
			-----------------------------
			ommp101InterfaceNumber:
			1 to 10 - CLIENT-1 to CLIENT-10
			-----------------------------
			Values:			
			eg: Gigalight
			-----------------------------"

		::= { ommp101CardGeneralDetailsEntry 45 }

	ommp101SfpPlusVendorIeeeId OBJECT-TYPE		 
		SYNTAX  DisplayString
		MAX-ACCESS  read-only
		STATUS current
		DESCRIPTION
			"This property defines the IEEE company Identifier for
			the vendor of SFP PLUS. A value of all zero in the 3-byte
			field indicates that the Vendor OUI is unspecified.
			-----------------------------
			ommp101InterfaceNumber:
			1 to 10 - CLIENT-1 to CLIENT-10
			-----------------------------
			Values:			
			eg: 010
			-----------------------------"
		::= { ommp101CardGeneralDetailsEntry 46 }

	ommp101SfpPlusPartNumber OBJECT-TYPE		 
		SYNTAX  DisplayString
		MAX-ACCESS  read-only
		STATUS current
		DESCRIPTION
			"This property defines the vendor part number or
			product name of the SFP PLUS. A value of all zero
			indicates that the vendor Part Number is unspecified.
			-----------------------------
			ommp101InterfaceNumber:
			1 to 10 - CLIENT-1 to CLIENT-10
			-----------------------------
			Values:			
			eg: WXTR15101000427
			-----------------------------"
		::= { ommp101CardGeneralDetailsEntry 47 }

	ommp101SfpPlusSerialNumber OBJECT-TYPE		 
		SYNTAX  DisplayString
		MAX-ACCESS  read-only
		STATUS current
		DESCRIPTION
			"This property provides vendor serial number defining
			the vendor’s serial number for the SFP PLUS. A value of all
			zero in the 16-byte field indicates that the vendor
			serial number is unspecified.
			-----------------------------
			ommp101InterfaceNumber:
			1 to 10 - CLIENT-1 to CLIENT-10
			-----------------------------
			Values:			
			eg: WXTRRPGEAS1
			-----------------------------"
		::= { ommp101CardGeneralDetailsEntry 48 }

	ommp101SfpPlusRevisionNumber OBJECT-TYPE		 
		SYNTAX  DisplayString
		MAX-ACCESS  read-only
		STATUS current
		DESCRIPTION
			"The vendor revision number defining the vendor’s
			product revision number. A value of all zero indicates
			that the vendor revision number is unspecified
			-----------------------------
			ommp101InterfaceNumber:
			1 to 10 - CLIENT-1 to CLIENT-10
			-----------------------------
			Values:			
			eg: RT
			-----------------------------"
		::= { ommp101CardGeneralDetailsEntry 49 }

	ommp101SfpPlusManufacturingDate OBJECT-TYPE		 
		SYNTAX  DisplayString
		MAX-ACCESS  read-only
		STATUS current
		DESCRIPTION
			"This property defines the manufacturing date for 
			SFP PLUS. A value of 8-byte field in ASCII which represents
			year, month and date of each two bytes. 
			Extra two bytes may be blank
			-----------------------------
			ommp101InterfaceNumber:
			1 to 10 - CLIENT-1 to CLIENT-10
			-----------------------------
			Values:			
			eg: 160224
			-----------------------------"
		::= { ommp101CardGeneralDetailsEntry 50 }

	ommp101FixedSfpPlusLaserWavelength OBJECT-TYPE		 
		SYNTAX  DisplayString
		MAX-ACCESS  read-only
		STATUS current
		DESCRIPTION
			"This property provides transmitter LASER wavelength(nm)
			of the SFP PLUS
			-----------------------------
			ommp101InterfaceNumber:
			1 to 10 - CLIENT-1 to CLIENT-10
			-----------------------------
			Values:			
			eg: 1310.0
			-----------------------------"
		::= { ommp101CardGeneralDetailsEntry 51 }

	ommp101SfpPlusConnectorType OBJECT-TYPE		 
		SYNTAX  DisplayString
		MAX-ACCESS  read-only
		STATUS current
		DESCRIPTION
			"This property provides information of the SFP PLUS
			connector, value indicates the external connector
			provided on the SFP PLUS.
			-----------------------------
			ommp101InterfaceNumber:
			1 to 10 - CLIENT-1 to CLIENT-10
			-----------------------------
			Values:

			00h 	Unknown or unspecified
			01h 	SC (Subscriber Connector)
			02h 	Fibre Channel Style 1 copper connector
			03h 	Fibre Channel Style 2 copper connector
			04h 	BNC/TNC (Bayonet/Threaded Neill-Concelman)
			05h 	Fibre Channel coax headers
			06h 	Fiber Jack
			07h 	LC (Lucent Connector)
			08h 	MT-RJ (Mechanical Transfer - Registered Jack)
			09h 	MU (Multiple Optical)
			0Ah 	SG
			0Bh 	Optical Pigtail
			0Ch 	MPO 1x12 (Multifiber Parallel Optic)
			0Dh 	MPO 2x16
			0E-1Fh 	Reserved
			20h 	HSSDC II (High Speed Serial Data Connector)
			21h 	Copper pigtail
			22h 	RJ45 (Registered Jack)
			23h 	No separable connector
			24h 	MXC 2x16
			25h-7Fh Reserved
			80h-FFh Vendor specific
			-----------------------------"
		::= { ommp101CardGeneralDetailsEntry 52 }

	ommp101SfpPlusLinkLength OBJECT-TYPE		 
		SYNTAX  DisplayString
		MAX-ACCESS  read-only
		STATUS current
		DESCRIPTION
			"This property provides link length suported by the SFP PLUS
			-----------------------------
			ommp101InterfaceNumber:
			1 to 10 - CLIENT-1 to CLIENT-10
			-----------------------------
			Values:
			eg: 80.00
			-----------------------------"
		::= { ommp101CardGeneralDetailsEntry 53 }

	ommp101SfpPlusSignalEncodingTypeSupported OBJECT-TYPE		 
		SYNTAX  INTEGER
		MAX-ACCESS  read-only
		STATUS current
		DESCRIPTION
			"This property indicates the serial encoding mechanisms
			that are supported by the SFP PLUS.
			-----------------------------
			ommp101InterfaceNumber:
			1 to 10 - CLIENT-1 to CLIENT-10
			-----------------------------
			Values:
			1 - 64B/66B
			2 - 8B10B
			3 - SONET Scrambled
			4 - NRZ
			5 - RZ
			-----------------------------"
		::= { ommp101CardGeneralDetailsEntry 54 }

	ommp101SfpPlusTransceiverCodesSupported OBJECT-TYPE		 
		SYNTAX  DisplayString
		MAX-ACCESS  read-only
		STATUS current
		DESCRIPTION
			"The identifier value specifies which transceiver
			codes are supported by the SFP PLUS
			-----------------------------
			ommp101InterfaceNumber:
			1 to 10 - CLIENT-1 to CLIENT-10
			-----------------------------
			Values:

			Return value 8-Byte represetation:
				  			 Byte-1	 Byte-2	 Byte-3	 Byte-4	 Byte-5  Byte-6  Byte-7	Byte-8
			100-M5-SN-I and 100-M6-SN-I	 0x00	 0x00   0x00	 0x00	 0x20    0x40    0x0C   0x01
			200-SM-LC-L and 100-SM-LC-L	 0x00	 0x00	 0x00	 0x00	 0x12	 0x00    0x01	0x05
			400-M5-SN-I and 400-M6-SN-I	 0x00	 0x00	 0x00	 0x00	 0x20    0x40    0x0C   0x15
			800-M5-SN-I and 800-M6-SN-I	 0x00	 0x00	 0x00	 0x00	 0x20    0x40    0x0C   0x54
			400-SM-LC-M	 		 0x00	 0x00	 0x00	 0x00	 0x0A    0x00    0x01   0x15
			400-SM-LC-L	 		 0x00	 0x00	 0x00	 0x00	 0x12    0x00    0x01   0x15
			200-SM-LL-V and 100-SM-LL-V	 0x00	 0x00	 0x00	 0x00	 0x80    0x10    0x01   0x05
			1000BASE-T	 		 0x00	 0x00	 0x00	 0x08    0x00    0x00    0x00   0x00
			1000BASE-SX	 		 0x00	 0x00	 0x00	 0x01    0x00    0x00    0x00   0x00
			1000BASE-LX	 		 0x00	 0x00	 0x00	 0x02    0x00    0x00    0x00   0x00
			1000BASE-LX10	 		 0x00	 0x00	 0x00	 0x02    0x00    0x00    0x00   0x00
			10GBASE-SR	 		 0x10h	 0x00	 0x00    0x00	 0x00	 0x00    0x00	0x00
			10GBASE-LR	 		 0x20h	 0x00	 0x00    0x00	 0x00	 0x00    0x00	0x00
			OC3/STM1 SR-1	 		 0x00	 0x00	 0x01h   0x00	 0x00	 0x00    0x00	0x00
			OC12/STM4 LR-1	 		 0x00	 0x10h	 0x40h   0x00	 0x00	 0x00    0x00	0x00
			OC48/STM16 LR-2	 		 0x00	 0x0Ch	 0x00    0x00	 0x00	 0x00    0x00	0x00
			10GE Passive copper cable	 0x00	 0x00	 0x00    0x00	 0x00	 0x04h   0x00	0x00
			10GE Active cable		 0x00	 0x00	 0x00    0x00	 0x00	 0x08h   0x00	0x00
			8/4/2G Passive copper cable	 0x00	 0x00	 0x00    0x00	 0x00	 0x04h   0x00	0x54h
			8/4/2G Active cable		 0x00	 0x00	 0x00    0x00	 0x00	 0x08h   0x00	0x54h
			-----------------------------"
		::= { ommp101CardGeneralDetailsEntry 55 }

	ommp101SfpPlusMaximumBitrateSupported OBJECT-TYPE		 
		SYNTAX  DisplayString
		MAX-ACCESS  read-only
		STATUS current
		DESCRIPTION
			"This property provides maximum bit rate value(Gbps)
			supported by the SFP PLUS
			-----------------------------
			ommp101InterfaceNumber:
			1 to 10 - CLIENT-1 to CLIENT-10
			-----------------------------
			Values: 2.7
			-----------------------------"
		::= { ommp101CardGeneralDetailsEntry 56 }

	ommp101SfpPlusNominalBitrateSupported OBJECT-TYPE		 
		SYNTAX  DisplayString
		MAX-ACCESS  read-only
		STATUS current
		DESCRIPTION
			"This property provides maximum bit rate value(Gbps)
			supported by the SFP PLUS
			-----------------------------
			ommp101InterfaceNumber:
			1 to 10 - CLIENT-1 to CLIENT-10
			-----------------------------
			Values: 2.5
			-----------------------------"
		::= { ommp101CardGeneralDetailsEntry 57 }

	ommp101SfpPlusMinimumBitrateSupported OBJECT-TYPE		 
		SYNTAX  DisplayString
		MAX-ACCESS  read-only
		STATUS current
		DESCRIPTION
			"This property provides minimum bit rate value(Gbps)
			supported by the SFP PLUS
			-----------------------------
			ommp101InterfaceNumber:
			1 to 10 - CLIENT-1 to CLIENT-10
			-----------------------------
			Values: 2.3
			-----------------------------"
		::= { ommp101CardGeneralDetailsEntry 58 }

	ommp101CardGeneralDetailsTableRowStatus OBJECT-TYPE
              SYNTAX      RowStatus
              MAX-ACCESS  read-write
              STATUS      current
              DESCRIPTION
			"*****************************
			This is MIB realted property,
			NOT to be considered as a card property
			*****************************"
              ::= { ommp101CardGeneralDetailsEntry 59 }

--*****************************************************************************
--				   CONFIGURATION
--*****************************************************************************

	ommp101ConfigurationTable OBJECT-TYPE
		SYNTAX  SEQUENCE OF Ommp101ConfigurationEntry 
		MAX-ACCESS  not-accessible
		STATUS  current
		DESCRIPTION
		      "Contains configuration queries of the OMMP101 card"
		::= { ommp101Configuration 1 }

	ommp101ConfigurationEntry  OBJECT-TYPE
              SYNTAX  Ommp101ConfigurationEntry 
              MAX-ACCESS  not-accessible
              STATUS  current
              DESCRIPTION 
              	""
		INDEX   { node, rack, subRack, slot, ommp101InterfaceNumber }
		::= { ommp101ConfigurationTable 1 }
	
	Ommp101ConfigurationEntry  ::= 
		SEQUENCE {
				ommp101CardSoftwareUpgrade					DisplayString,
				ommp101CardSignalMonitorState				INTEGER,
				ommp101CardOpticalMonitorState				INTEGER,
				ommp101CardSoftReset						INTEGER,
				ommp101CardFactoryReset					INTEGER,
				ommp101SyncSystemTimeWithNtpServer				DisplayString,
				ommp101SyncRtcWithNtpServer						DisplayString,
				ommp101SyncRtcWithSystemTime						DisplayString,
				ommp101UpdateGivenTimeIntoSystem					DisplayString,
				ommp101UpdateGivenTimeIntoRtc					DisplayString,
				ommp101SystemTimeAndRtcTime						DisplayString,
				ommp101TrafficConfiguration					INTEGER,
				ommp101LoopbackState						INTEGER,
				ommp101PortSignalMonitorState				INTEGER,
				ommp101PortOpticalMonitorState				INTEGER,
				ommp101ClearSignalPerformance				INTEGER,
				ommp101AlsState						INTEGER,
				ommp101AlsPulseRepetitionTime				INTEGER,
				ommp101OtuFecConfiguration					INTEGER,
				ommp101OtuSignalFailThreshold				INTEGER,
				ommp101OtuSignalDegradeThreshold				INTEGER,
				ommp101OtuSapiTransmitTraceMessage				DisplayString,
				ommp101OtuDapiTransmitTraceMessage				DisplayString,
				ommp101OtuOperatorSpecificTransmitTraceMessage		DisplayString,
				ommp101OtuSapiExpectedTraceMessage				DisplayString,
				ommp101OtuDapiExpectedTraceMessage				DisplayString,
				ommp101OtuOperatorSpecificExpectedTraceMessage		DisplayString,
				ommp101OduSignalFailThreshold				INTEGER,
				ommp101OduSignalDegradeThreshold				INTEGER,
				ommp101OduSapiTransmitTraceMessage				DisplayString,
				ommp101OduDapiTransmitTraceMessage				DisplayString,
				ommp101OduOperatorSpecificTransmitTraceMessage		DisplayString,
				ommp101OduSapiExpectedTraceMessage				DisplayString,
				ommp101OduDapiExpectedTraceMessage				DisplayString,
				ommp101OduOperatorSpecificExpectedTraceMessage		DisplayString,
				ommp101SdhMsB2ExcessiveErrorThreshold			INTEGER,
				ommp101SdhMsB2SignalDegradeThreshold				INTEGER,
				ommp101TunableCfp2LaserWavelength				INTEGER,
				ommp101TunableCfp2LaserChannelNumber				INTEGER,
				ommp101Cfp2LaserState						INTEGER,
				ommp101Cfp2Reset						INTEGER,
				ommp101Cfp2PowerDownMode					INTEGER,
				ommp101Cfp2HighTemperatureAlarmThreshold			DisplayString,
				ommp101Cfp2LowTemperatureAlarmThreshold			DisplayString,
				ommp101Cfp2HighTemperatureWarningThreshold			DisplayString,
				ommp101Cfp2LowTemperatureWarningThreshold			DisplayString,
				ommp101Cfp2InputHighPowerAlarmThreshold			DisplayString,
				ommp101Cfp2InputLowPowerAlarmThreshold			DisplayString,
				ommp101Cfp2InputHighPowerWarningThreshold			DisplayString,
				ommp101Cfp2InputLowPowerWarningThreshold			DisplayString,
				ommp101Cfp2OutputHighPowerAlarmThreshold			DisplayString,
				ommp101Cfp2OutputLowPowerAlarmThreshold			DisplayString,
				ommp101Cfp2OutputHighPowerWarningThreshold			DisplayString,
				ommp101Cfp2OutputLowPowerWarningThreshold			DisplayString,
				ommp101Cfp2HighSupplyVoltageAlarmThreshold			DisplayString,
				ommp101Cfp2LowSupplyVoltageAlarmThreshold			DisplayString,
				ommp101Cfp2HighSupplyVoltageWarningThreshold			DisplayString,
				ommp101Cfp2LowSupplyVoltageWarningThreshold			DisplayString,
				ommp101SfpPlusLaserState						INTEGER,
				ommp101SfpPlusHighTemperatureAlarmThreshold			DisplayString,
				ommp101SfpPlusLowTemperatureAlarmThreshold			DisplayString,
				ommp101SfpPlusHighTemperatureWarningThreshold			DisplayString,
				ommp101SfpPlusLowTemperatureWarningThreshold			DisplayString,
				ommp101SfpPlusHighBiasCurrentAlarmThreshold			DisplayString,
				ommp101SfpPlusLowBiasCurrentAlarmThreshold			DisplayString,
				ommp101SfpPlusHighBiasCurrentWarningThreshold			DisplayString,
				ommp101SfpPlusLowBiasCurrentWarningThreshold			DisplayString,
				ommp101SfpPlusInputHighPowerAlarmThreshold			DisplayString,
				ommp101SfpPlusInputLowPowerAlarmThreshold			DisplayString,
				ommp101SfpPlusInputHighPowerWarningThreshold			DisplayString,
				ommp101SfpPlusInputLowPowerWarningThreshold			DisplayString,
				ommp101SfpPlusOutputHighPowerAlarmThreshold			DisplayString,
				ommp101SfpPlusOutputLowPowerAlarmThreshold			DisplayString,
				ommp101SfpPlusOutputHighPowerWarningThreshold			DisplayString,
				ommp101SfpPlusOutputLowPowerWarningThreshold			DisplayString,
				ommp101SfpPlusHighSupplyVoltageAlarmThreshold			DisplayString,
				ommp101SfpPlusLowSupplyVoltageAlarmThreshold			DisplayString,
				ommp101SfpPlusHighSupplyVoltageWarningThreshold			DisplayString,
				ommp101SfpPlusLowSupplyVoltageWarningThreshold			DisplayString,
				ommp101Cfp2InputPowerFailureAlarmInhibit			INTEGER,
				ommp101Cfp2OutputPowerFailureAlarmInhibit			INTEGER,
				ommp101Cfp2HighTemperatureAlarmInhibit			INTEGER,
				ommp101Cfp2LowTemperatureAlarmInhibit				INTEGER,
				ommp101Cfp2HighTemperatureWarningInhibit			INTEGER,
				ommp101Cfp2LowTemperatureWarningInhibit			INTEGER,
				ommp101Cfp2InputHighPowerAlarmInhibit				INTEGER,
				ommp101Cfp2InputLowPowerAlarmInhibit				INTEGER,
				ommp101Cfp2InputHighPowerWarningInhibit			INTEGER,
				ommp101Cfp2InputLowPowerWarningInhibit			INTEGER,
				ommp101Cfp2OutputHighPowerAlarmInhibit			INTEGER,
				ommp101Cfp2OutputLowPowerAlarmInhibit				INTEGER,
				ommp101Cfp2OutputHighPowerWarningInhibit			INTEGER,
				ommp101Cfp2OutputLowPowerWarningInhibit			INTEGER,
				ommp101Cfp2HighSupplyVoltageAlarmInhibit			INTEGER,
				ommp101Cfp2LowSupplyVoltageAlarmInhibit			INTEGER,
				ommp101Cfp2HighSupplyVoltageWarningInhibit			INTEGER,
				ommp101Cfp2LowSupplyVoltageWarningInhibit			INTEGER,
				ommp101Cfp2PresenceAbsenceNotificationInhibit			INTEGER,
				ommp101SfpPlusInputPowerFailureAlarmInhibit			INTEGER,
				ommp101SfpPlusOutputPowerFailureAlarmInhibit			INTEGER,
				ommp101SfpPlusHighTemperatureAlarmInhibit			INTEGER,
				ommp101SfpPlusLowTemperatureAlarmInhibit				INTEGER,
				ommp101SfpPlusHighTemperatureWarningInhibit			INTEGER,
				ommp101SfpPlusLowTemperatureWarningInhibit			INTEGER,
				ommp101SfpPlusHighBiasCurrentAlarmInhibit			INTEGER,
				ommp101SfpPlusLowBiasCurrentAlarmInhibit				INTEGER,
				ommp101SfpPlusHighBiasCurrentWarningInhibit			INTEGER,
				ommp101SfpPlusLowBiasCurrentWarningInhibit			INTEGER,
				ommp101SfpPlusInputHighPowerAlarmInhibit				INTEGER,
				ommp101SfpPlusInputLowPowerAlarmInhibit				INTEGER,
				ommp101SfpPlusInputHighPowerWarningInhibit			INTEGER,
				ommp101SfpPlusInputLowPowerWarningInhibit			INTEGER,
				ommp101SfpPlusOutputHighPowerAlarmInhibit			INTEGER,
				ommp101SfpPlusOutputLowPowerAlarmInhibit				INTEGER,
				ommp101SfpPlusOutputHighPowerWarningInhibit			INTEGER,
				ommp101SfpPlusOutputLowPowerWarningInhibit			INTEGER,
				ommp101SfpPlusHighSupplyVoltageAlarmInhibit			INTEGER,
				ommp101SfpPlusLowSupplyVoltageAlarmInhibit			INTEGER,
				ommp101SfpPlusHighSupplyVoltageWarningInhibit			INTEGER,
				ommp101SfpPlusLowSupplyVoltageWarningInhibit			INTEGER,
				ommp101SfpPlusPresenceAbsenceNotificationInhibit			INTEGER,
				ommp101SfpPlusTransmitFaultPresenceAlarmInhibit			INTEGER,
				ommp101OtuLossOfSignalAlarmInhibit				INTEGER,
				ommp101OtuLossOfFrameAlarmInhibit				INTEGER,
				ommp101OtuOutOfFrameAlarmInhibit				INTEGER,
				ommp101OtuLossOfMultiFrameAlarmInhibit			INTEGER,
				ommp101OtuOutOfMultiFrameAlarmInhibit			INTEGER,
				ommp101OtuSignalFailAlarmInhibit				INTEGER,
				ommp101OtuSignalDegradeAlarmInhibit				INTEGER,
				ommp101OtuAlarmIndicationSignalAlarmInhibit			INTEGER,
				ommp101OtuIncomingAlignmentErrorAlarmInhibit			INTEGER,
				ommp101OtuBackwardIncomingAlignmentErrorAlarmInhibit		INTEGER,
				ommp101OtuBackwardDefectIndicationAlarmInhibit		INTEGER,
				ommp101OduSignalFailAlarmInhibit				INTEGER,
				ommp101OduSignalDegradeAlarmInhibit				INTEGER,
				ommp101OduAlarmIndicationSignalAlarmInhibit			INTEGER,
				ommp101OduTcm1IncomingAlignmentErrorAlarmInhibit		INTEGER,
				ommp101OduTcm2IncomingAlignmentErrorAlarmInhibit		INTEGER,
				ommp101OduTcm3IncomingAlignmentErrorAlarmInhibit		INTEGER,
				ommp101OduTcm4IncomingAlignmentErrorAlarmInhibit		INTEGER,
				ommp101OduTcm5IncomingAlignmentErrorAlarmInhibit		INTEGER,
				ommp101OduTcm6IncomingAlignmentErrorAlarmInhibit		INTEGER,
				ommp101OduLockedDefectAlarmInhibit				INTEGER,
				ommp101OduOpenConnectionIndicationAlarmInhibit		INTEGER,
				ommp101OduBackwardDefectIndicationAlarmInhibit		INTEGER,
				ommp101OduTcm1BackwardIncomingAlignmentErrorAlarmInhibit	INTEGER,
				ommp101OduTcm2BackwardIncomingAlignmentErrorAlarmInhibit	INTEGER,
				ommp101OduTcm3BackwardIncomingAlignmentErrorAlarmInhibit	INTEGER,
				ommp101OduTcm4BackwardIncomingAlignmentErrorAlarmInhibit	INTEGER,
				ommp101OduTcm5BackwardIncomingAlignmentErrorAlarmInhibit	INTEGER,
				ommp101OduTcm6BackwardIncomingAlignmentErrorAlarmInhibit	INTEGER,
				ommp101OduLossOfFrameLossOfMultiframeAlarmInhibit		INTEGER,
				ommp101OpuPayloadMismatchAlarmInhibit			INTEGER,
				ommp101SdhLossOfSignalAlarmInhibit				INTEGER,
				ommp101SdhOutOfFrameAlarmInhibit				INTEGER,
				ommp101SdhLossOfFrameAlarmInhibit				INTEGER,
				ommp101SdhRsTraceIdentifierMismatchAlarmInhibit		INTEGER,
				ommp101SdhMsAlarmIndicationSignalAlarmInhibit		INTEGER,
				ommp101SdhMsRemoteDefectIndicationAlarmInhibit		INTEGER,
				ommp101EthernetLossOfSignalAlarmInhibit			INTEGER,
				ommp101EthernetLinkFailureAlarmInhibit			INTEGER,
				ommp101EthernetHighBerAlarmInhibit				INTEGER,
				ommp101EthernetLocalFaultAlarmInhibit			INTEGER,
				ommp101EthernetRemoteFaultAlarmInhibit			INTEGER,
				ommp101Cfp2InputPowerFailureAlarmSeverity			DisplayString,
				ommp101Cfp2OutputPowerFailureAlarmSeverity			DisplayString,
				ommp101Cfp2HighTemperatureAlarmSeverity			DisplayString,
				ommp101Cfp2LowTemperatureAlarmSeverity			DisplayString,
				ommp101Cfp2HighTemperatureWarningSeverity			DisplayString,
				ommp101Cfp2LowTemperatureWarningSeverity			DisplayString,
				ommp101Cfp2InputHighPowerAlarmSeverity			DisplayString,
				ommp101Cfp2InputLowPowerAlarmSeverity				DisplayString,
				ommp101Cfp2InputHighPowerWarningSeverity			DisplayString,
				ommp101Cfp2InputLowPowerWarningSeverity			DisplayString,
				ommp101Cfp2OutputHighPowerAlarmSeverity			DisplayString,
				ommp101Cfp2OutputLowPowerAlarmSeverity			DisplayString,
				ommp101Cfp2OutputHighPowerWarningSeverity			DisplayString,
				ommp101Cfp2OutputLowPowerWarningSeverity			DisplayString,
				ommp101Cfp2HighSupplyVoltageAlarmSeverity			DisplayString,
				ommp101Cfp2LowSupplyVoltageAlarmSeverity			DisplayString,
				ommp101Cfp2HighSupplyVoltageWarningSeverity			DisplayString,
				ommp101Cfp2LowSupplyVoltageWarningSeverity			DisplayString,
				ommp101Cfp2PresenceAbsenceNotificationSeverity		DisplayString,
				ommp101SfpPlusInputPowerFailureAlarmSeverity			DisplayString,
				ommp101SfpPlusOutputPowerFailureAlarmSeverity			DisplayString,
				ommp101SfpPlusHighTemperatureAlarmSeverity			DisplayString,
				ommp101SfpPlusLowTemperatureAlarmSeverity			DisplayString,
				ommp101SfpPlusHighTemperatureWarningSeverity			DisplayString,
				ommp101SfpPlusLowTemperatureWarningSeverity			DisplayString,
				ommp101SfpPlusHighBiasCurrentAlarmSeverity			DisplayString,
				ommp101SfpPlusLowBiasCurrentAlarmSeverity			DisplayString,
				ommp101SfpPlusHighBiasCurrentWarningSeverity			DisplayString,
				ommp101SfpPlusLowBiasCurrentWarningSeverity			DisplayString,
				ommp101SfpPlusInputHighPowerAlarmSeverity			DisplayString,
				ommp101SfpPlusInputLowPowerAlarmSeverity				DisplayString,
				ommp101SfpPlusInputHighPowerWarningSeverity			DisplayString,
				ommp101SfpPlusInputLowPowerWarningSeverity			DisplayString,
				ommp101SfpPlusOutputHighPowerAlarmSeverity			DisplayString,
				ommp101SfpPlusOutputLowPowerAlarmSeverity			DisplayString,
				ommp101SfpPlusOutputHighPowerWarningSeverity			DisplayString,
				ommp101SfpPlusOutputLowPowerWarningSeverity			DisplayString,
				ommp101SfpPlusHighSupplyVoltageAlarmSeverity			DisplayString,
				ommp101SfpPlusLowSupplyVoltageAlarmSeverity			DisplayString,
				ommp101SfpPlusHighSupplyVoltageWarningSeverity			DisplayString,
				ommp101SfpPlusLowSupplyVoltageWarningSeverity			DisplayString,
				ommp101SfpPlusPresenceAbsenceNotificationSeverity		DisplayString,
				ommp101SfpPlusTransmitFaultPresenceAlarmSeverity			DisplayString,
				ommp101OtuLossOfSignalAlarmSeverity				DisplayString,
				ommp101OtuLossOfFrameAlarmSeverity				DisplayString,
				ommp101OtuOutOfFrameAlarmSeverity				DisplayString,
				ommp101OtuLossOfMultiFrameAlarmSeverity			DisplayString,
				ommp101OtuOutOfMultiFrameAlarmSeverity			DisplayString,
				ommp101OtuSignalFailAlarmSeverity				DisplayString,
				ommp101OtuSignalDegradeAlarmSeverity				DisplayString,
				ommp101OtuAlarmIndicationSignalAlarmSeverity			DisplayString,
				ommp101OtuIncomingAlignmentErrorAlarmSeverity		DisplayString,
				ommp101OtuBackwardIncomingAlignmentErrorAlarmSeverity	DisplayString,
				ommp101OtuBackwardDefectIndicationAlarmSeverity		DisplayString,
				ommp101OduSignalFailAlarmSeverity				DisplayString,
				ommp101OduSignalDegradeAlarmSeverity				DisplayString,
				ommp101OduAlarmIndicationSignalAlarmSeverity			DisplayString,
				ommp101OduTcm1IncomingAlignmentErrorAlarmSeverity		DisplayString,
				ommp101OduTcm2IncomingAlignmentErrorAlarmSeverity		DisplayString,
				ommp101OduTcm3IncomingAlignmentErrorAlarmSeverity		DisplayString,
				ommp101OduTcm4IncomingAlignmentErrorAlarmSeverity		DisplayString,
				ommp101OduTcm5IncomingAlignmentErrorAlarmSeverity		DisplayString,
				ommp101OduTcm6IncomingAlignmentErrorAlarmSeverity		DisplayString,
				ommp101OduLockedDefectAlarmSeverity				DisplayString,
				ommp101OduOpenConnectionIndicationAlarmSeverity		DisplayString,
				ommp101OduBackwardDefectIndicationAlarmSeverity		DisplayString,
				ommp101OduTcm1BackwardIncomingAlignmentErrorAlarmSeverity	DisplayString,
				ommp101OduTcm2BackwardIncomingAlignmentErrorAlarmSeverity	DisplayString,
				ommp101OduTcm3BackwardIncomingAlignmentErrorAlarmSeverity	DisplayString,
				ommp101OduTcm4BackwardIncomingAlignmentErrorAlarmSeverity	DisplayString,
				ommp101OduTcm5BackwardIncomingAlignmentErrorAlarmSeverity	DisplayString,
				ommp101OduTcm6BackwardIncomingAlignmentErrorAlarmSeverity	DisplayString,
				ommp101OduLossOfFrameLossOfMultiframeAlarmSeverity		DisplayString,
				ommp101OpuPayloadMismatchAlarmSeverity			DisplayString,
				ommp101SdhLossOfSignalAlarmSeverity				DisplayString,
				ommp101SdhOutOfFrameAlarmSeverity				DisplayString,
				ommp101SdhLossOfFrameAlarmSeverity				DisplayString,
				ommp101SdhRsTraceIdentifierMismatchAlarmSeverity		DisplayString,
				ommp101SdhMsAlarmIndicationSignalAlarmSeverity		DisplayString,
				ommp101SdhMsRemoteDefectIndicationAlarmSeverity		DisplayString,
				ommp101EthernetLossOfSignalAlarmSeverity			DisplayString,
				ommp101EthernetLinkFailureAlarmSeverity			DisplayString,
				ommp101EthernetHighBerAlarmSeverity				DisplayString,
				ommp101EthernetLocalFaultAlarmSeverity			DisplayString,
				ommp101EthernetRemoteFaultAlarmSeverity			DisplayString,
				ommp101TunableCfp2WavelengthGridSpacing			INTEGER,
				ommp101OduLockedDefectAlarmInsertion				INTEGER,
				ommp101OduOpenConnectionIndicationAlarmInsertion		INTEGER,
				ommp101OtuTraceIdentifierMismatchAlarmInhibit		INTEGER,
				ommp101OduTraceIdentifierMismatchAlarmInhibit		INTEGER,
				ommp101OtuTraceIdentifierMismatchAlarmSeverity		DisplayString,
				ommp101OduTraceIdentifierMismatchAlarmSeverity		DisplayString,
				ommp101EthernetLossOfAlignmentAlarmInhibit		INTEGER,
				ommp101EthernetLossOfBlockLockAlarmInhibit		INTEGER,
				ommp101EthernetNotAlignedInPcsAlarmInhibit		INTEGER,
				ommp101EthernetLossOfAlignmentAlarmSeverity		DisplayString,
				ommp101EthernetLossOfBlockLockAlarmSeverity		DisplayString,
				ommp101EthernetNotAlignedInPcsAlarmSeverity		DisplayString,				
				ommp101ConfigurationTableRowStatus				RowStatus
			 }
	

	ommp101CardSoftwareUpgrade OBJECT-TYPE		 
		SYNTAX  DisplayString
		MAX-ACCESS  read-write
		STATUS current
		DESCRIPTION
			"Valid only as SET command.
			This property upgrades the software of the OMMP101 card
			It takes the path of the software release as
			a value
			-----------------------------
			ommp101InterfaceNumber: 0
			-----------------------------
			Values:
			eg: /root/home/rel-2.0.0.tar.gz
			-----------------------------"
		::= { ommp101ConfigurationEntry 1 }

	ommp101CardSignalMonitorState OBJECT-TYPE		 
		SYNTAX  INTEGER
		MAX-ACCESS  read-write
		STATUS current
		DESCRIPTION
			"This property sets or gets the card's signal
			monitoring state. Disabling card signal monitoring 
			will not provide any signal alarms and performances
			information to the user.
			-----------------------------
			ommp101InterfaceNumber: 0
			-----------------------------
			Values:
			1 - Card Signal Monitoring is enabled
			0 - Card Signal Monitoring is disabled
			-----------------------------"
		::= { ommp101ConfigurationEntry 2 }

	ommp101CardOpticalMonitorState OBJECT-TYPE		 
		SYNTAX  INTEGER
		MAX-ACCESS  read-write
		STATUS current
		DESCRIPTION
			"This property sets or gets the card's optical
			monitoring state. Disabling card signal monitoring 
			will not provide any signal alarms and performances
			information to the user.
			-----------------------------
			ommp101InterfaceNumber: 0
			-----------------------------
			Values:
			1 - Card Optical Monitoring is enabled
			0 - Card Optical Monitoring is disabled
			-----------------------------"
		::= { ommp101ConfigurationEntry 3 }

	ommp101CardSoftReset OBJECT-TYPE		 
		SYNTAX  INTEGER
		MAX-ACCESS  read-write
		STATUS current
		DESCRIPTION
			"Valid only as a SET command.
			Reboots the Card, Reconfigures the Card 
			i.e All Configuration Parameter	like Laser State,
			Traffic configuration, Loopback, FEC, optical and 
			signal thresholds, switching mode,
			user choice of line path, auto-negotiation, 
			TTI messages will be restored to previous state
			-----------------------------
			ommp101InterfaceNumber: 0
			-----------------------------
			Values:
			Dont care, any value
			eg: 0
			-----------------------------"
		::= { ommp101ConfigurationEntry 4 }

	ommp101CardFactoryReset OBJECT-TYPE		 
		SYNTAX  INTEGER
		MAX-ACCESS  read-write
		STATUS current
		DESCRIPTION
			"Valid only as a SET command.
			Sets the Card To Factory Default State
			i.e All User Configuration Parameters like Laser State,
			Traffic configuration, Loopback, FEC, optical and 
			signal thresholds, switching mode,
			user choice of line path, auto-negotiation, TTI messages
			will be set to default state
			-----------------------------
			ommp101InterfaceNumber: 0
			-----------------------------
			Values:
			Dont care, any value
			eg: 0
			-----------------------------"
		::= { ommp101ConfigurationEntry 5 }

	ommp101SyncSystemTimeWithNtpServer OBJECT-TYPE		 
		SYNTAX  DisplayString
		MAX-ACCESS read-write
		STATUS current
		DESCRIPTION
			" when we want to manually sync the time value
			present in linux kernel with the NTP server
			we can use this OID. We can provide NTP server
			ip address as a value to this OID and the time
			will be synced to that ilarticular server. 
			If we are not providing NTP server IP address 
			then the system will be synced with the NTP server 
			which is already been registered with card. 
			If both are absent then error message will be returned
			-----------------------------
			Interface : 0
			-----------------------------
			If we want to provide NTP server IP address then
			Value should be a valid IP address as shown below
			: 192.168.21.25
			
			If we don't want to provide NTP server address then no
			need to pass any value. 
			---------------------------"
		::= { ommp101ConfigurationEntry 6 }

	ommp101SyncRtcWithNtpServer OBJECT-TYPE		 
		SYNTAX  DisplayString
		MAX-ACCESS  read-write
		STATUS current
		DESCRIPTION
			" when we want to manually sync the time value
			present in RTC with the NTP server
			we can use this OID. We can provide NTP server
			ip address as a value to this OID and the time
			will be synced to that particular server. 
			If we are not providing NTP server IP address 
			then the system will be synced with the NTP server 
			which is already been registered with card. 
			If both are absent then error message will be returned.
			-----------------------------
			Interface : 0
			-----------------------------
			If we want to provide NTP server IP address then
			Value should be a valid IP address as shown below
			: 192.168.21.25
			
			If we don't want to provide NTP server address, then no
			need to ilass any value. 
			---------------------------"
		::= { ommp101ConfigurationEntry 7 }

	ommp101SyncRtcWithSystemTime OBJECT-TYPE		 
		SYNTAX  DisplayString
		MAX-ACCESS  read-write
		STATUS current
		DESCRIPTION
			" when we want to manually sync the time value
			present in RTC with the time value in linux kernel
			we can use this OID. With this set operation, 
			the time available with linux kernel will be updated
			into RTC. It is not required to provide any value for 
			this operation"
		::= { ommp101ConfigurationEntry 8 }

	ommp101UpdateGivenTimeIntoSystem OBJECT-TYPE		 
		SYNTAX  DisplayString
		MAX-ACCESS  read-write
		STATUS current
		DESCRIPTION
			" when we want to manually update system time
			with the user provided time, we can use this OID.
			With OID we need to provide time value which we
			want to update in the system.
			-----------------------------
			Interface : 0
			-----------------------------
			Value should be of given format:
			YYYY-MM-DD H:M:S
			
			Example: 2017-10-31 15:20:44
			---------------------------"
		::= { ommp101ConfigurationEntry 9 }

	ommp101UpdateGivenTimeIntoRtc OBJECT-TYPE		 
		SYNTAX  DisplayString
		MAX-ACCESS  read-write
		STATUS current
		DESCRIPTION
			" when we want to manually update RTC time
			with the user provided time, we can use this OID.
			With OID we need to provide time value which we
			want to update in RTC.
			-----------------------------
			Interface : 0
			-----------------------------
			Value should be of given format:
			YYYY-MM-DD H:M:S
			
			Example: 2017-10-31 15:20:44
			---------------------------"
		::= { ommp101ConfigurationEntry 10 }

	ommp101SystemTimeAndRtcTime OBJECT-TYPE		 
		SYNTAX  DisplayString
		MAX-ACCESS read-only
		STATUS current
		DESCRIPTION
			" get the system time and time value present in RTC.
			-----------------------------
			Interface : 0
			-----------------------------"
		::= { ommp101ConfigurationEntry 11 }

	ommp101TrafficConfiguration OBJECT-TYPE		 
		SYNTAX  INTEGER
		MAX-ACCESS  read-write
		STATUS current
		DESCRIPTION
			"Set or get Traffic configuration for all ports
			-----------------------------
			ommp101InterfaceNumber:
			1 to 10 - CLIENT-1 to CLIENT-10
			-----------------------------
			Value: 
			00 - Un-configure 
			01 - STM64
			02 - LAN10G
			03 - OTU2
			04 - OTU4
			-----------------------------"
		::= { ommp101ConfigurationEntry 12 }

	ommp101LoopbackState OBJECT-TYPE		 
		SYNTAX  INTEGER
		MAX-ACCESS  read-write
		STATUS current
		DESCRIPTION
			"Set or get the loopback state for the
			requested port
			-----------------------------
			ommp101InterfaceNumber:
			1 to 10 - CLIENT-1 to CLIENT-10
			11 - LINE PORT
			-----------------------------
			Values: 
			00 - No Loopback   
			01 - Near End Loopback
			02 - Far End Loopback
			-----------------------------"
		::= { ommp101ConfigurationEntry 13 }

	ommp101PortSignalMonitorState OBJECT-TYPE		 
		SYNTAX  INTEGER
		MAX-ACCESS  read-write
		STATUS current
		DESCRIPTION
			"This property sets or gets the port's signal
			monitoring state. Disabling port signal monitoring 
			will not provide any signal alarms and performances
			information to the user.
			-----------------------------
			ommp101InterfaceNumber:
			1 to 10 - CLIENT-1 to CLIENT-10
			11 - LINE PORT
			-----------------------------
			Values:
			1 - Port Signal Monitoring is enabled
			0 - Port Signal Monitoring is disabled
			-----------------------------"
		::= { ommp101ConfigurationEntry 14 }

	ommp101PortOpticalMonitorState OBJECT-TYPE		 
		SYNTAX  INTEGER
		MAX-ACCESS  read-write
		STATUS current
		DESCRIPTION
			"This property sets or gets the port's optical
			monitoring state. Disabling port optical monitoring 
			will not provide any optical alarms and performances
			information to the user.
			-----------------------------
			ommp101InterfaceNumber:
			1 to 10 - CLIENT-1 to CLIENT-10
			11 - LINE PORT
			-----------------------------
			Values:
			1 - Port Optical Monitoring is enabled
			0 - Port Optical Monitoring is disabled
			-----------------------------"
		::= { ommp101ConfigurationEntry 15 }

	ommp101ClearSignalPerformance OBJECT-TYPE		 
		SYNTAX  INTEGER
		MAX-ACCESS  read-write
		STATUS current
		DESCRIPTION
			"Valid only as a SET command.
			Clears signal performance for the requested port
			-----------------------------
			ommp101InterfaceNumber:
			1 to 10 - CLIENT-1 to CLIENT-10
			11 - LINE PORT
			-----------------------------
			Values:
			Dont care, any value
			eg: 0
			-----------------------------"
		::= { ommp101ConfigurationEntry 16 }

	ommp101AlsState OBJECT-TYPE		 
		SYNTAX  INTEGER
		MAX-ACCESS  read-write
		STATUS current
		DESCRIPTION
			"Set the Automatic Laser Switching(ALS) mode for
			for requested port. Based on the RX LOS state of the
			port, the transmit LASER state will be controlled
			according to the algorithm defined for ALS in
			ITUT 664 Standard
			-----------------------------
			ommp101InterfaceNumber:
			1 to 10 - CLIENT-1 to CLIENT-10
			11 - LINE PORT
			-----------------------------
			Values: 
			1 - Enable ALS state
			0 - Disable ALS state
			-----------------------------" 
		::= { ommp101ConfigurationEntry 17 }

	ommp101AlsPulseRepetitionTime OBJECT-TYPE		 
		SYNTAX  INTEGER
		MAX-ACCESS  read-write
		STATUS current
		DESCRIPTION
			"Pulse repetition time is the time for automatic 
			restart of CFP2 LASER once the ALS algorithm starts.
			-----------------------------
			ommp101InterfaceNumber:
			1 to 10 - CLIENT-1 to CLIENT-10
			11 - LINE PORT
			-----------------------------
			Values: 
			100 seconds to 300 seconds
			-----------------------------"
		::= { ommp101ConfigurationEntry 18 }

	ommp101OtuFecConfiguration OBJECT-TYPE		 
		SYNTAX  INTEGER
		MAX-ACCESS  read-write
		STATUS current
		DESCRIPTION
			"Set or Get FEC type for requested port configured with
			 OTU2 traffic.  
			-----------------------------
			ommp101InterfaceNumber:
			1 to 10 - CLIENT-1 to CLIENT-10
			11 - LINE PORT
			-----------------------------
			Values: 
			00 - Zero FEC 
			01 - Reed-Solomon GFEC
			-----------------------------"
		::= { ommp101ConfigurationEntry 19 }

	ommp101OtuSignalFailThreshold OBJECT-TYPE		 
		SYNTAX  INTEGER
		MAX-ACCESS  read-write
		STATUS current
		DESCRIPTION
			"Set or Get SM Signal Failure 
			Threshold value for the requested port configured with 
			OTU2/OTU4 traffic.
			-----------------------------
			ommp101InterfaceNumber:
			1 to 10 - CLIENT-1 to CLIENT-10
			11 - LINE PORT
			-----------------------------
			Values: 
			03 - 1.E -03
			04 - 1.E -04
			05 - 1.E -05
			-----------------------------" 
		::= { ommp101ConfigurationEntry 20 }

	ommp101OtuSignalDegradeThreshold OBJECT-TYPE		 
		SYNTAX  INTEGER
		MAX-ACCESS  read-write
		STATUS current
		DESCRIPTION
			"Set or Get SM Signal Degrade 
			Threshold value for the requested port configured with 
			OTU2/OTU4 traffic.
			-----------------------------
			ommp101InterfaceNumber:
			1 to 10 - CLIENT-1 to CLIENT-10
			11 - LINE PORT
			-----------------------------
			Values:
			06 - 1.E -06
			07 - 1.E -07
			08 - 1.E -08
			09 - 1.E -09
			10 - 1.E -10(for line only)
			-----------------------------"
		::= { ommp101ConfigurationEntry 21 }

	ommp101OtuSapiTransmitTraceMessage OBJECT-TYPE		 
		SYNTAX  DisplayString
		MAX-ACCESS  read-write
		STATUS current
		DESCRIPTION
			"Set or get the 15 characters SAPI Transmit TTI message
			which is put into the outgoing OTU2 frame. 
			-----------------------------
			ommp101InterfaceNumber:
			1 to 10 - CLIENT-1 to CLIENT-10
			11 - LINE PORT
			-----------------------------
			Values:
			eg: 123451234512345
			-----------------------------" 
		::= { ommp101ConfigurationEntry 22 }

	ommp101OtuDapiTransmitTraceMessage OBJECT-TYPE		 
		SYNTAX  DisplayString
		MAX-ACCESS  read-write
		STATUS current
		DESCRIPTION
			"Set or get the 15 characters DAPI Transmit TTI message
			which is put into the outgoing OTU2 frame. 
			-----------------------------
			ommp101InterfaceNumber:
			1 to 10 - CLIENT-1 to CLIENT-10
			11 - LINE PORT
			-----------------------------
			Values:
			eg: 123451234512345
			-----------------------------" 
		::= { ommp101ConfigurationEntry 23 }

	ommp101OtuOperatorSpecificTransmitTraceMessage OBJECT-TYPE		 
		SYNTAX  DisplayString
		MAX-ACCESS  read-write
		STATUS current
		DESCRIPTION
			"Set or get the 32 characters Operator Specific Transmit
			TTI message which is put into the outgoing OTU2
			frame. 
			-----------------------------
			ommp101InterfaceNumber:
			1 to 10 - CLIENT-1 to CLIENT-10
			11 - LINE PORT
			-----------------------------
			Values:
			eg: 12345123451234512345123451234500
			-----------------------------" 
		::= { ommp101ConfigurationEntry 24 }

	ommp101OtuSapiExpectedTraceMessage OBJECT-TYPE		 
		SYNTAX  DisplayString
		MAX-ACCESS  read-write
		STATUS current
		DESCRIPTION
			"15 characters SM SAPI Expected TTI message - Message
			set here is used for comparison with the message present
			in SM SAPI field of the incoming OTU2 frames.
			-----------------------------
			ommp101InterfaceNumber:
			1 to 10 - CLIENT-1 to CLIENT-10
			11 - LINE PORT
			-----------------------------
			Values:
			eg: 123451234512345
			-----------------------------" 
		::= { ommp101ConfigurationEntry 25 }

	ommp101OtuDapiExpectedTraceMessage OBJECT-TYPE		 
		SYNTAX  DisplayString
		MAX-ACCESS  read-write
		STATUS current
		DESCRIPTION
			"15 characters SM DAPI Expected TTI message - Message
			set here is used for comparison with the message present
			in SM DAPI field of the incoming OTU2 frames.
			-----------------------------
			ommp101InterfaceNumber:
			1 to 10 - CLIENT-1 to CLIENT-10
			11 - LINE PORT
			-----------------------------
			Values:
			eg: 123451234512345
			-----------------------------" 
		::= { ommp101ConfigurationEntry 26 }

	ommp101OtuOperatorSpecificExpectedTraceMessage OBJECT-TYPE		 
		SYNTAX  DisplayString
		MAX-ACCESS  read-write
		STATUS current
		DESCRIPTION
			"32 characters SM Operator Specific Expected TTI 
			message - Message set here is used for comparison with 
			the message present in SM Operator Specific field of 
			the incoming OTU2 frames.
			-----------------------------
			ommp101InterfaceNumber:
			1 to 10 - CLIENT-1 to CLIENT-10
			11 - LINE PORT
			-----------------------------
			Values:
			eg: 12345123451234512345123451234500
			-----------------------------" 
		::= { ommp101ConfigurationEntry 27 }

	ommp101OduSignalFailThreshold OBJECT-TYPE		 
		SYNTAX  INTEGER
		MAX-ACCESS  read-write
		STATUS current
		DESCRIPTION
			"Set or Get PM Signal Failure 
			Threshold value for the requested port configured with 
			OTU2/OTU4 traffic.
			-----------------------------
			ommp101InterfaceNumber:
			1 to 10 - CLIENT-1 to CLIENT-10
			11 - LINE PORT
			-----------------------------
			Values: 
			03 - 1.E -03
			04 - 1.E -04
			05 - 1.E -05
			-----------------------------" 
		::= { ommp101ConfigurationEntry 28 }

	ommp101OduSignalDegradeThreshold OBJECT-TYPE		 
		SYNTAX  INTEGER
		MAX-ACCESS  read-write
		STATUS current
		DESCRIPTION
			"Set or Get PM Signal Degrade 
			Threshold value for the requested port configured with 
			OTU2/OTU4 traffic.
			-----------------------------
			ommp101InterfaceNumber:
			1 to 10 - CLIENT-1 to CLIENT-10
			11 - LINE PORT
			-----------------------------
			Values: 
			06 - 1.E -06
			07 - 1.E -07
			08 - 1.E -08
			09 - 1.E -09
			10 - 1.E -10(for line only)
			-----------------------------" 
		::= { ommp101ConfigurationEntry 29 }

	ommp101OduSapiTransmitTraceMessage OBJECT-TYPE
		SYNTAX  DisplayString
		MAX-ACCESS  read-write
		STATUS current
		DESCRIPTION
			"Set or get the 15 characters SAPI Transmit TTI message
			which is put into the outgoing OTU2
			frame at the PM level. 
			-----------------------------
			ommp101InterfaceNumber:
			1 to 10 - CLIENT-1 to CLIENT-10
			11 - LINE PORT
			-----------------------------
			Values:
			eg: 123451234512345
			-----------------------------" 
		::= { ommp101ConfigurationEntry 30 }

	ommp101OduDapiTransmitTraceMessage OBJECT-TYPE		 
		SYNTAX  DisplayString
		MAX-ACCESS  read-write
		STATUS current
		DESCRIPTION
			"Set or get the 15 characters DAPI Transmit TTI message
			which is put into the outgoing OTU2
			frame at the PM level. 
			-----------------------------
			ommp101InterfaceNumber:
			1 to 10 - CLIENT-1 to CLIENT-10
			11 - LINE PORT
			-----------------------------
			Values:
			eg: 123451234512345
			-----------------------------" 
		::= { ommp101ConfigurationEntry 31 }

	ommp101OduOperatorSpecificTransmitTraceMessage OBJECT-TYPE		 
		SYNTAX  DisplayString
		MAX-ACCESS  read-write
		STATUS current
		DESCRIPTION
			"Set or get the 32 characters Operator Specific Transmit
			TTI message which is put into the outgoing OTU2
			frame at the PM level. 
			-----------------------------
			ommp101InterfaceNumber:
			1 to 10 - CLIENT-1 to CLIENT-10
			11 - LINE PORT
			-----------------------------
			Values:
			eg: 12345123451234512345123451234500
			-----------------------------" 
		::= { ommp101ConfigurationEntry 32 }

	ommp101OduSapiExpectedTraceMessage OBJECT-TYPE		 
		SYNTAX  DisplayString
		MAX-ACCESS  read-write
		STATUS current
		DESCRIPTION
			"15 characters PM SAPI Expected TTI message - Message
			set here is used for comparison with the message present
			in PM SAPI field of the incoming OTU2 frames.
			-----------------------------
			ommp101InterfaceNumber:
			1 to 10 - CLIENT-1 to CLIENT-10
			11 - LINE PORT
			-----------------------------
			Values:
			eg: 123451234512345
			-----------------------------" 
		::= { ommp101ConfigurationEntry 33 }

	ommp101OduDapiExpectedTraceMessage OBJECT-TYPE		 
		SYNTAX  DisplayString
		MAX-ACCESS  read-write
		STATUS current
		DESCRIPTION
			"15 characters PM DAPI Expected TTI message - Message
			set here is used for comparison with the message present
			in PM DAPI field of the incoming OTU2 frames.
			-----------------------------
			ommp101InterfaceNumber:
			1 to 10 - CLIENT-1 to CLIENT-10
			11 - LINE PORT
			-----------------------------
			Values:
			eg: 123451234512345
			-----------------------------" 
		::= { ommp101ConfigurationEntry 34 }

	ommp101OduOperatorSpecificExpectedTraceMessage OBJECT-TYPE		 
		SYNTAX  DisplayString
		MAX-ACCESS  read-write
		STATUS current
		DESCRIPTION
			"32 characters PM Operator Specific Expected TTI 
			message - Message set here is used for comparison with 
			the message present in PM DAPI field of the incoming
			OTU2/OTU4 frames.
			-----------------------------
			ommp101InterfaceNumber:
			1 to 10 - CLIENT-1 to CLIENT-10
			11 - LINE PORT
			-----------------------------
			Values:
			eg: 12345123451234512345123451234500
			-----------------------------" 
		::= { ommp101ConfigurationEntry 35 }

	ommp101SdhMsB2ExcessiveErrorThreshold OBJECT-TYPE		 
		SYNTAX  INTEGER
		MAX-ACCESS  read-write
		STATUS current
		DESCRIPTION
			"Set or Get B2 Signal Failure Threshold value for the 
			requested port configured with STM-16 traffic.
			-----------------------------
			ommp101InterfaceNumber:
			1 to 10 - CLIENT-1 to CLIENT-10
			-----------------------------
			Values:
			03 - 1.E -03
			04 - 1.E -04
			05 - 1.E -05
			-----------------------------"
		::= { ommp101ConfigurationEntry 36 }

	ommp101SdhMsB2SignalDegradeThreshold OBJECT-TYPE		 
		SYNTAX  INTEGER
		MAX-ACCESS  read-write
		STATUS current
		DESCRIPTION
			"Set or Get B2 Signal Degrade Threshold value for the 
			requested port configured with STM-16 traffic.
			-----------------------------
			ommp101InterfaceNumber:
			1 to 10 - CLIENT-1 to CLIENT-10
			-----------------------------
			Values:
			06 - 1.E -06
			07 - 1.E -07
			08 - 1.E -08
			09 - 1.E -09
			10 - 1.E -10
			11 - 1.E -11
			-----------------------------"
		::= { ommp101ConfigurationEntry 37 }

	ommp101TunableCfp2LaserWavelength OBJECT-TYPE		 
		SYNTAX  INTEGER
		MAX-ACCESS  read-write
		STATUS current
		DESCRIPTION
			"Get the CFP2 wavelength for the requested port 
			-----------------------------
			ommp101InterfaceNumber:
			11 - LINE PORT
			-----------------------------
			Values:
			eg: 30607
			-----------------------------"
		::= { ommp101ConfigurationEntry 38 }

	ommp101TunableCfp2LaserChannelNumber OBJECT-TYPE		 
		SYNTAX  INTEGER
		MAX-ACCESS  read-write
		STATUS current
		DESCRIPTION
			"Set or Get the CFP2 Channel Number for the the requested
			port
			-----------------------------
			ommp101InterfaceNumber:
			11 - LINE PORT
			-----------------------------
			Values:
			eg: 10
			-----------------------------"
		::= { ommp101ConfigurationEntry 39 }

	ommp101Cfp2LaserState OBJECT-TYPE		 
		SYNTAX  INTEGER
		MAX-ACCESS  read-write
		STATUS current
		DESCRIPTION
			"Set or Get the CFP2 LASER state for the the requested
			port
			-----------------------------
			ommp101InterfaceNumber:
			11 - LINE PORT
			-----------------------------
			Values: 
			00 - Laser OFF
			01 - Laser ON
			-----------------------------"
		::= { ommp101ConfigurationEntry 40 }

	ommp101Cfp2Reset OBJECT-TYPE		 
		SYNTAX  INTEGER
		MAX-ACCESS  read-write
		STATUS current
		DESCRIPTION
			"Valid only as a SET command.
			Resets the CFP2.
			-----------------------------
			ommp101InterfaceNumber:
			11 - LINE PORT
			-----------------------------
			Values: 
			Dont care, any value
			eg: 0
			-----------------------------"
		::= { ommp101ConfigurationEntry 41 }

	ommp101Cfp2PowerDownMode OBJECT-TYPE		 
		SYNTAX  INTEGER
		MAX-ACCESS  read-write
		STATUS current
		DESCRIPTION
			"Valid only as a SET command.
			Sets the CFP2 in the Power Down mode i.e. low power 
			consumption mode.
			-----------------------------
			ommp101InterfaceNumber:
			11 - LINE PORT
			-----------------------------
			Values: 
			01 - power down CFP2
			-----------------------------"
		::= { ommp101ConfigurationEntry 42 }

	ommp101Cfp2HighTemperatureAlarmThreshold OBJECT-TYPE		 
		SYNTAX  DisplayString
		MAX-ACCESS  read-write
		STATUS current
		DESCRIPTION
			"Set or Get High Temperature Alarm Threshold
			(in degree celsius) for the requested port
			-----------------------------
			ommp101InterfaceNumber:
			11 - LINE PORT
			-----------------------------
			Values: 
			eg: 65 
			-----------------------------" 
		::= { ommp101ConfigurationEntry 43 }

	ommp101Cfp2LowTemperatureAlarmThreshold OBJECT-TYPE		 
		SYNTAX  DisplayString
		MAX-ACCESS  read-write
		STATUS current
		DESCRIPTION
			"Set or Get Low Temperature Alarm Threshold
			(in degree celsius) for the requested port
			-----------------------------
			ommp101InterfaceNumber:
			11 - LINE PORT
			-----------------------------
			Values: 
			eg: 5 
			-----------------------------" 
		::= { ommp101ConfigurationEntry 44 }

	ommp101Cfp2HighTemperatureWarningThreshold OBJECT-TYPE		 
		SYNTAX  DisplayString
		MAX-ACCESS  read-write
		STATUS current
		DESCRIPTION
			"Set or Get High Temperature Warning Threshold
			(in degree celsius) for the requested port
			-----------------------------
			ommp101InterfaceNumber:
			11 - LINE PORT
			-----------------------------
			Values: 
			eg: 60 
			-----------------------------"
		::= { ommp101ConfigurationEntry 45 }
		
	ommp101Cfp2LowTemperatureWarningThreshold OBJECT-TYPE		 
		SYNTAX  DisplayString
		MAX-ACCESS  read-write
		STATUS current
		DESCRIPTION
			"Set or Get Low Temperature Warning Threshold
			(in degree celsius) for the requested port
			-----------------------------
			ommp101InterfaceNumber:
			11 - LINE PORT
			-----------------------------
			Values: 
			eg: 10 
			-----------------------------"
		::= { ommp101ConfigurationEntry 46 }

	ommp101Cfp2InputHighPowerAlarmThreshold OBJECT-TYPE		 
		SYNTAX  DisplayString
		MAX-ACCESS  read-write
		STATUS current
		DESCRIPTION
			"Set or Get Input High Power Alarm Threshold
			(in dbm) for the requested port
			-----------------------------
			ommp101InterfaceNumber:
			11 - LINE PORT
			-----------------------------
			Values:
			eg: -9.1
			-----------------------------"
		::= { ommp101ConfigurationEntry 47 }

	ommp101Cfp2InputLowPowerAlarmThreshold OBJECT-TYPE		 
		SYNTAX  DisplayString
		MAX-ACCESS  read-write
		STATUS current
		DESCRIPTION
			"Set or Get Input Low Power Alarm Threshold
			(in dbm) for the requested port
			-----------------------------
			ommp101InterfaceNumber:
			11 - LINE PORT
			-----------------------------
			Values:
			eg: -35.6
			-----------------------------"
		::= { ommp101ConfigurationEntry 48 }

	ommp101Cfp2InputHighPowerWarningThreshold OBJECT-TYPE		 
		SYNTAX  DisplayString
		MAX-ACCESS  read-write
		STATUS current
		DESCRIPTION
			"Set or Get Input High Power Warning Threshold
			(in dbm) for the requested port
			-----------------------------
			ommp101InterfaceNumber:
			11 - LINE PORT
			-----------------------------
			Values:
			eg: -11.2
			-----------------------------"
		::= { ommp101ConfigurationEntry 49 }

	ommp101Cfp2InputLowPowerWarningThreshold OBJECT-TYPE		 
		SYNTAX  DisplayString
		MAX-ACCESS  read-write
		STATUS current
		DESCRIPTION
			"Set or Get Input Low Power Warning Threshold
			(in dbm) for the requested port
			-----------------------------
			ommp101InterfaceNumber:
			11 - LINE PORT
			-----------------------------
			Values:
			eg: -31.3
			-----------------------------"
		::= { ommp101ConfigurationEntry 50 }

	ommp101Cfp2OutputHighPowerAlarmThreshold OBJECT-TYPE		 
		SYNTAX  DisplayString
		MAX-ACCESS  read-write
		STATUS current
		DESCRIPTION
			"Set or Get Output High Power Alarm Threshold
			(in dbm) for the requested port
			-----------------------------
			ommp101InterfaceNumber:
			11 - LINE PORT
			-----------------------------
			Values:
			eg: +2.0
			-----------------------------"
		::= { ommp101ConfigurationEntry 51 }

	ommp101Cfp2OutputLowPowerAlarmThreshold OBJECT-TYPE		 
		SYNTAX  DisplayString
		MAX-ACCESS  read-write
		STATUS current
		DESCRIPTION
			"Set or Get Output Low Power Alarm Threshold
			(in dbm) for the requested port
			-----------------------------
			ommp101InterfaceNumber:
			11 - LINE PORT
			-----------------------------
			Values:
			eg: -3.5
			-----------------------------"
		::= { ommp101ConfigurationEntry 52 }

	ommp101Cfp2OutputHighPowerWarningThreshold OBJECT-TYPE		 
		SYNTAX  DisplayString
		MAX-ACCESS  read-write
		STATUS current
		DESCRIPTION
			"Set or Get Output High Power Warning Threshold
			(in dbm) for the requested port
			-----------------------------
			ommp101InterfaceNumber:
			11 - LINE PORT
			-----------------------------
			Values:
			eg: +1.3
			-----------------------------"
		::= { ommp101ConfigurationEntry 53 }

	ommp101Cfp2OutputLowPowerWarningThreshold OBJECT-TYPE		 
		SYNTAX  DisplayString
		MAX-ACCESS  read-write
		STATUS current
		DESCRIPTION
			"Set or Get Output Low Power Warning Threshold
			(in dbm) for the requested port
			-----------------------------
			ommp101InterfaceNumber:
			11 - LINE PORT
			-----------------------------
			Values:
			eg: -2.5
			-----------------------------"
		::= { ommp101ConfigurationEntry 54 }

	ommp101Cfp2HighSupplyVoltageAlarmThreshold OBJECT-TYPE		 
		SYNTAX  DisplayString
		MAX-ACCESS  read-write
		STATUS current
		DESCRIPTION
			"Set or Get High Supply Voltage Alarm Threshold
			(in volts) for the requested port
			-----------------------------
			ommp101InterfaceNumber:
			11 - LINE PORT
			-----------------------------
			Values:
			eg: +3.3
			-----------------------------"
		::= { ommp101ConfigurationEntry 55 }

	ommp101Cfp2LowSupplyVoltageAlarmThreshold OBJECT-TYPE		 
		SYNTAX  DisplayString
		MAX-ACCESS  read-write
		STATUS current
		DESCRIPTION
			"Set or Get Low Supply Voltage Alarm Threshold
			(in volts) for the requested port
			-----------------------------
			ommp101InterfaceNumber:
			11 - LINE PORT
			-----------------------------
			Values:
			eg: +3.0
			-----------------------------"
		::= { ommp101ConfigurationEntry 56 }

	ommp101Cfp2HighSupplyVoltageWarningThreshold OBJECT-TYPE		 
		SYNTAX  DisplayString
		MAX-ACCESS  read-write
		STATUS current
		DESCRIPTION
			"Set or Get High Supply Voltage Warning Threshold
			(in volts) for the requested port
			-----------------------------
			ommp101InterfaceNumber:
			11 - LINE PORT
			-----------------------------
			Values:
			eg: +3.2
			-----------------------------"
		::= { ommp101ConfigurationEntry 57 }

	ommp101Cfp2LowSupplyVoltageWarningThreshold OBJECT-TYPE		 
		SYNTAX  DisplayString
		MAX-ACCESS  read-write
		STATUS current
		DESCRIPTION
			"Set or Get Low Supply Voltage Warning Threshold
			(in volts) for the requested port
			-----------------------------
			ommp101InterfaceNumber:
			11 - LINE PORT
			-----------------------------
			Values:
			eg: +3.1
			-----------------------------"
		::= { ommp101ConfigurationEntry 58 }

	ommp101SfpPlusLaserState OBJECT-TYPE		 
		SYNTAX  INTEGER
		MAX-ACCESS  read-write
		STATUS current
		DESCRIPTION
			"Set or Get the SFP PLUS LASER state for the the requested
			port
			-----------------------------
			ommp101InterfaceNumber:
			1 to 10 - CLIENT-1 to CLIENT-10
			-----------------------------
			Values: 
			01 - Laser ON
			00 - Laser OFF
			-----------------------------" 
		::= { ommp101ConfigurationEntry 59 }

	ommp101SfpPlusHighTemperatureAlarmThreshold OBJECT-TYPE		 
		SYNTAX  DisplayString
		MAX-ACCESS  read-write
		STATUS current
		DESCRIPTION
			"Set or Get High Temperature Alarm Threshold
			(in degree celsius) for the requested port
			-----------------------------
			ommp101InterfaceNumber:
			1 to 10 - CLIENT-1 to CLIENT-10
			-----------------------------
			Values: 
			eg: 65 
			-----------------------------" 
		::= { ommp101ConfigurationEntry 60 }

	ommp101SfpPlusLowTemperatureAlarmThreshold OBJECT-TYPE		 
		SYNTAX  DisplayString
		MAX-ACCESS  read-write
		STATUS current
		DESCRIPTION
			"Set or Get Low Temperature Alarm Threshold
			(in degree celsius) for the requested port
			-----------------------------
			ommp101InterfaceNumber:
			1 to 10 - CLIENT-1 to CLIENT-10
			-----------------------------
			Values: 
			eg: 5 
			-----------------------------" 
		::= { ommp101ConfigurationEntry 61 }

	ommp101SfpPlusHighTemperatureWarningThreshold OBJECT-TYPE		 
		SYNTAX  DisplayString
		MAX-ACCESS  read-write
		STATUS current
		DESCRIPTION
			"Set or Get High Temperature Warning Threshold
			(in degree celsius) for the requested port
			-----------------------------
			ommp101InterfaceNumber:
			1 to 10 - CLIENT-1 to CLIENT-10
			-----------------------------
			Values: 
			eg: 60 
			-----------------------------"
		::= { ommp101ConfigurationEntry 62 }

	ommp101SfpPlusLowTemperatureWarningThreshold OBJECT-TYPE		 
		SYNTAX  DisplayString
		MAX-ACCESS  read-write
		STATUS current
		DESCRIPTION
			"Set or Get Low Temperature Warning Threshold
			(in degree celsius) for the requested port
			-----------------------------
			ommp101InterfaceNumber:
			1 to 10 - CLIENT-1 to CLIENT-10
			-----------------------------
			Values: 
			eg: 10 
			-----------------------------"
		::= { ommp101ConfigurationEntry 63 }

	ommp101SfpPlusHighBiasCurrentAlarmThreshold OBJECT-TYPE		 
		SYNTAX  DisplayString
		MAX-ACCESS  read-write
		STATUS current
		DESCRIPTION
			"Set or Get High Bias Current Alarm Threshold
			(in milli ampere) for the requested port
			-----------------------------
			ommp101InterfaceNumber:
			1 to 10 - CLIENT-1 to CLIENT-10
			-----------------------------
			Values:
			eg: 35.6
			-----------------------------"
		::= { ommp101ConfigurationEntry 64 }

	ommp101SfpPlusLowBiasCurrentAlarmThreshold OBJECT-TYPE		 
		SYNTAX  DisplayString
		MAX-ACCESS  read-write
		STATUS current
		DESCRIPTION
			"Set or Get Low Bias Current Alarm Threshold
			(in milli ampere) for the requested port
			-----------------------------
			ommp101InterfaceNumber:
			1 to 10 - CLIENT-1 to CLIENT-10
			-----------------------------
			Values:
			eg: 31.1
			-----------------------------"
		::= { ommp101ConfigurationEntry 65 }

	ommp101SfpPlusHighBiasCurrentWarningThreshold OBJECT-TYPE		 
		SYNTAX  DisplayString
		MAX-ACCESS  read-write
		STATUS current
		DESCRIPTION
			"Set or Get High Bias Current Warning Threshold
			(in milli ampere) for the requested port
			-----------------------------
			ommp101InterfaceNumber:
			1 to 10 - CLIENT-1 to CLIENT-10
			-----------------------------
			Values:
			eg: 34.5
			-----------------------------"
		::= { ommp101ConfigurationEntry 66 }

	ommp101SfpPlusLowBiasCurrentWarningThreshold OBJECT-TYPE		 
		SYNTAX  DisplayString
		MAX-ACCESS  read-write
		STATUS current
		DESCRIPTION
			"Set or Get Low Bias Current Alarm Threshold
			(in milli ampere) for the requested port
			-----------------------------
			ommp101InterfaceNumber:
			1 to 10 - CLIENT-1 to CLIENT-10
			-----------------------------
			Values:
			eg: 32.8
			-----------------------------"
		::= { ommp101ConfigurationEntry 67 }

	ommp101SfpPlusInputHighPowerAlarmThreshold OBJECT-TYPE		 
		SYNTAX  DisplayString
		MAX-ACCESS  read-write
		STATUS current
		DESCRIPTION
			"Set or Get Input High Power Alarm Threshold
			(in dbm) for the requested port
			-----------------------------
			ommp101InterfaceNumber:
			1 to 10 - CLIENT-1 to CLIENT-10
			-----------------------------
			Values:
			eg: -9.1
			-----------------------------"
		::= { ommp101ConfigurationEntry 68 }

	ommp101SfpPlusInputLowPowerAlarmThreshold OBJECT-TYPE		 
		SYNTAX  DisplayString
		MAX-ACCESS  read-write
		STATUS current
		DESCRIPTION
			"Set or Get Input Low Power Alarm Threshold
			(in dbm) for the requested port
			-----------------------------
			ommp101InterfaceNumber:
			1 to 10 - CLIENT-1 to CLIENT-10
			-----------------------------
			Values:
			eg: -35.6
			-----------------------------"
		::= { ommp101ConfigurationEntry 69 }

	ommp101SfpPlusInputHighPowerWarningThreshold OBJECT-TYPE		 
		SYNTAX  DisplayString
		MAX-ACCESS  read-write
		STATUS current
		DESCRIPTION
			"Set or Get Input High Power Warning Threshold
			(in dbm) for the requested port
			-----------------------------
			ommp101InterfaceNumber:
			1 to 10 - CLIENT-1 to CLIENT-10
			-----------------------------
			Values:
			eg: -11.2
			-----------------------------"
		::= { ommp101ConfigurationEntry 70 }

	ommp101SfpPlusInputLowPowerWarningThreshold OBJECT-TYPE		 
		SYNTAX  DisplayString
		MAX-ACCESS  read-write
		STATUS current
		DESCRIPTION
			"Set or Get Input Low Power Warning Threshold
			(in dbm) for the requested port
			-----------------------------
			ommp101InterfaceNumber:
			1 to 10 - CLIENT-1 to CLIENT-10
			-----------------------------
			Values:
			eg: -31.3
			-----------------------------"
		::= { ommp101ConfigurationEntry 71 }

	ommp101SfpPlusOutputHighPowerAlarmThreshold OBJECT-TYPE		 
		SYNTAX  DisplayString
		MAX-ACCESS  read-write
		STATUS current
		DESCRIPTION
			"Set or Get Output High Power Alarm Threshold
			(in dbm) for the requested port
			-----------------------------
			ommp101InterfaceNumber:
			1 to 10 - CLIENT-1 to CLIENT-10
			-----------------------------
			Values:
			eg: +2.0
			-----------------------------"
		::= { ommp101ConfigurationEntry 72 }

	ommp101SfpPlusOutputLowPowerAlarmThreshold OBJECT-TYPE		 
		SYNTAX  DisplayString
		MAX-ACCESS  read-write
		STATUS current
		DESCRIPTION
			"Set or Get Output Low Power Alarm Threshold
			(in dbm) for the requested port
			-----------------------------
			ommp101InterfaceNumber:
			1 to 10 - CLIENT-1 to CLIENT-10
			-----------------------------
			Values:
			eg: -3.5
			-----------------------------"
		::= { ommp101ConfigurationEntry 73 }

	ommp101SfpPlusOutputHighPowerWarningThreshold OBJECT-TYPE		 
		SYNTAX  DisplayString
		MAX-ACCESS  read-write
		STATUS current
		DESCRIPTION
			"Set or Get Output High Power Warning Threshold
			(in dbm) for the requested port
			-----------------------------
			ommp101InterfaceNumber:
			1 to 10 - CLIENT-1 to CLIENT-10
			-----------------------------
			Values:
			eg: +1.3
			-----------------------------"
		::= { ommp101ConfigurationEntry 74 }

	ommp101SfpPlusOutputLowPowerWarningThreshold OBJECT-TYPE		 
		SYNTAX  DisplayString
		MAX-ACCESS  read-write
		STATUS current
		DESCRIPTION
			"Set or Get Output Low Power Warning Threshold
			(in dbm) for the requested port
			-----------------------------
			ommp101InterfaceNumber:
			1 to 10 - CLIENT-1 to CLIENT-10
			-----------------------------
			Values:
			eg: -2.5
			-----------------------------"
		::= { ommp101ConfigurationEntry 75 }

	ommp101SfpPlusHighSupplyVoltageAlarmThreshold OBJECT-TYPE		 
		SYNTAX  DisplayString
		MAX-ACCESS  read-write
		STATUS current
		DESCRIPTION
			"Set or Get High Supply Voltage Alarm Threshold
			(in volts) for the requested port
			-----------------------------
			ommp101InterfaceNumber:
			1 to 10 - CLIENT-1 to CLIENT-10
			-----------------------------
			Values:
			eg: +3.3
			-----------------------------"
		::= { ommp101ConfigurationEntry 76 }

	ommp101SfpPlusLowSupplyVoltageAlarmThreshold OBJECT-TYPE		 
		SYNTAX  DisplayString
		MAX-ACCESS  read-write
		STATUS current
		DESCRIPTION
			"Set or Get Low Supply Voltage Alarm Threshold
			(in volts) for the requested port
			-----------------------------
			ommp101InterfaceNumber:
			1 to 10 - CLIENT-1 to CLIENT-10
			-----------------------------
			Values:
			eg: +3.0
			-----------------------------"
		::= { ommp101ConfigurationEntry 77 }

	ommp101SfpPlusHighSupplyVoltageWarningThreshold OBJECT-TYPE		 
		SYNTAX  DisplayString
		MAX-ACCESS  read-write
		STATUS current
		DESCRIPTION
			"Set or Get High Supply Voltage Warning Threshold
			(in volts) for the requested port
			-----------------------------
			ommp101InterfaceNumber:
			1 to 10 - CLIENT-1 to CLIENT-10
			-----------------------------
			Values:
			eg: +3.2
			-----------------------------"
		::= { ommp101ConfigurationEntry 78 }

	ommp101SfpPlusLowSupplyVoltageWarningThreshold OBJECT-TYPE		 
		SYNTAX  DisplayString
		MAX-ACCESS  read-write
		STATUS current
		DESCRIPTION
			"Set or Get Low Supply Voltage Warning Threshold
			(in volts) for the requested port
			-----------------------------
			ommp101InterfaceNumber:
			1 to 10 - CLIENT-1 to CLIENT-10
			-----------------------------
			Values:
			eg: +3.1
			-----------------------------"
		::= { ommp101ConfigurationEntry 79 }

	ommp101Cfp2InputPowerFailureAlarmInhibit  OBJECT-TYPE		 
		SYNTAX  INTEGER
		MAX-ACCESS  read-write
		STATUS  current
		DESCRIPTION
			"Inhibits OMMP101 CFP2 Input Power Failure Alarm
			for the requested port
			-----------------------------
			ommp101InterfaceNumber:
			11 - LINE PORT
			-----------------------------
			Value:
			1 - Inhibit
			0 - Do Not Inhibit
			-----------------------------"
	::= { ommp101ConfigurationEntry 80 }

	ommp101Cfp2OutputPowerFailureAlarmInhibit  OBJECT-TYPE		 
		SYNTAX  INTEGER
		MAX-ACCESS  read-write
		STATUS  current
		DESCRIPTION
			"Inhibits OMMP101 CFP2 Output Power Failure Alarm
			for the requested port
			-----------------------------
			ommp101InterfaceNumber:
			11 - LINE PORT
			-----------------------------
			Value:
			1 - Inhibit
			0 - Do Not Inhibit
			-----------------------------"
	::= { ommp101ConfigurationEntry 81 }

	ommp101Cfp2HighTemperatureAlarmInhibit  OBJECT-TYPE		 
		SYNTAX  INTEGER
		MAX-ACCESS  read-write
		STATUS  current
		DESCRIPTION
			"Inhibits OMMP101 CFP2 High Temperature Alarm
			for the requested port
			-----------------------------
			ommp101InterfaceNumber:
			11 - LINE PORT
			-----------------------------
			Value:
			1 - Inhibit
			0 - Do Not Inhibit
			-----------------------------"
	::= { ommp101ConfigurationEntry 82 }

	ommp101Cfp2LowTemperatureAlarmInhibit  OBJECT-TYPE		 
		SYNTAX  INTEGER
		MAX-ACCESS  read-write
		STATUS  current
		DESCRIPTION
			"Inhibits OMMP101 CFP2 Low Temperature Alarm
			for the requested port
			-----------------------------
			ommp101InterfaceNumber:
			11 - LINE PORT
			-----------------------------
			Value:
			1 - Inhibit
			0 - Do Not Inhibit
			-----------------------------"
	::= { ommp101ConfigurationEntry 83 }

	ommp101Cfp2HighTemperatureWarningInhibit  OBJECT-TYPE		 
		SYNTAX  INTEGER
		MAX-ACCESS  read-write
		STATUS  current
		DESCRIPTION
			"Inhibits OMMP101 CFP2 High Temperature Warning
			for the requested port
			-----------------------------
			ommp101InterfaceNumber:
			11 - LINE PORT
			-----------------------------
			Value:
			1 - Inhibit
			0 - Do Not Inhibit
			-----------------------------"
	::= { ommp101ConfigurationEntry 84 }

	ommp101Cfp2LowTemperatureWarningInhibit  OBJECT-TYPE		 
		SYNTAX  INTEGER
		MAX-ACCESS  read-write
		STATUS  current
		DESCRIPTION
			"Inhibits OMMP101 CFP2 Low Temperature Warning
			for the requested port
			-----------------------------
			ommp101InterfaceNumber:
			11 - LINE PORT
			-----------------------------
			Value:
			1 - Inhibit
			0 - Do Not Inhibit
			-----------------------------"
	::= { ommp101ConfigurationEntry 85 }

	ommp101Cfp2InputHighPowerAlarmInhibit  OBJECT-TYPE		 
		SYNTAX  INTEGER
		MAX-ACCESS  read-write
		STATUS  current
		DESCRIPTION
			"Inhibits OMMP101 CFP2 Input High Power Alarm
			for the requested port
			-----------------------------
			ommp101InterfaceNumber:
			11 - LINE PORT
			-----------------------------
			Value:
			1 - Inhibit
			0 - Do Not Inhibit
			-----------------------------"
	::= { ommp101ConfigurationEntry 86 }

	ommp101Cfp2InputLowPowerAlarmInhibit  OBJECT-TYPE		 
		SYNTAX  INTEGER
		MAX-ACCESS  read-write
		STATUS  current
		DESCRIPTION
			"Inhibits OMMP101 CFP2 Input Low Power Alarm
			for the requested port
			-----------------------------
			ommp101InterfaceNumber:
			11 - LINE PORT
			-----------------------------
			Value:
			1 - Inhibit
			0 - Do Not Inhibit
			-----------------------------"
	::= { ommp101ConfigurationEntry 87 }

	ommp101Cfp2InputHighPowerWarningInhibit  OBJECT-TYPE		 
		SYNTAX  INTEGER
		MAX-ACCESS  read-write
		STATUS  current
		DESCRIPTION
			"Inhibits OMMP101 CFP2 Input High Power Warning
			for the requested port
			-----------------------------
			ommp101InterfaceNumber:
			11 - LINE PORT
			-----------------------------
			Value:
			1 - Inhibit
			0 - Do Not Inhibit
			-----------------------------"
	::= { ommp101ConfigurationEntry 88 }

	ommp101Cfp2InputLowPowerWarningInhibit  OBJECT-TYPE		 
		SYNTAX  INTEGER
		MAX-ACCESS  read-write
		STATUS  current
		DESCRIPTION
			"Inhibits OMMP101 CFP2 Input Low Power Warning
			for the requested port
			-----------------------------
			ommp101InterfaceNumber:
			11 - LINE PORT
			-----------------------------
			Value:
			1 - Inhibit
			0 - Do Not Inhibit
			-----------------------------"
	::= { ommp101ConfigurationEntry 89 }

	ommp101Cfp2OutputHighPowerAlarmInhibit OBJECT-TYPE		 
		SYNTAX  INTEGER
		MAX-ACCESS  read-write
		STATUS  current
		DESCRIPTION
			"Inhibits OMMP101 CFP2 Output High Power Alarm
			for the requested port
			-----------------------------
			ommp101InterfaceNumber:
			11 - LINE PORT
			-----------------------------
			Value:
			1 - Inhibit
			0 - Do Not Inhibit
			-----------------------------"
	::= { ommp101ConfigurationEntry 90 }

	ommp101Cfp2OutputLowPowerAlarmInhibit OBJECT-TYPE		 
		SYNTAX  INTEGER
		MAX-ACCESS  read-write
		STATUS  current
		DESCRIPTION
			"Inhibits OMMP101 CFP2 Output Low Power Alarm
			for the requested port
			-----------------------------
			ommp101InterfaceNumber:
			11 - LINE PORT
			-----------------------------
			Value:
			1 - Inhibit
			0 - Do Not Inhibit
			-----------------------------"
	::= { ommp101ConfigurationEntry 91 }

	ommp101Cfp2OutputHighPowerWarningInhibit OBJECT-TYPE		 
		SYNTAX  INTEGER
		MAX-ACCESS  read-write
		STATUS  current
		DESCRIPTION
			"Inhibits OMMP101 CFP2 Output High Power Warning
			for the requested port
			-----------------------------
			ommp101InterfaceNumber:
			11 - LINE PORT
			-----------------------------
			Value:
			1 - Inhibit
			0 - Do Not Inhibit
			-----------------------------"
	::= { ommp101ConfigurationEntry 92 }

	ommp101Cfp2OutputLowPowerWarningInhibit OBJECT-TYPE		 
		SYNTAX  INTEGER
		MAX-ACCESS  read-write
		STATUS  current
		DESCRIPTION
			"Inhibits OMMP101 CFP2 Output Low Power Warning
			for the requested port
			-----------------------------
			ommp101InterfaceNumber:
			11 - LINE PORT
			-----------------------------
			Value:
			1 - Inhibit
			0 - Do Not Inhibit
			-----------------------------"
	::= { ommp101ConfigurationEntry 93 }

	ommp101Cfp2HighSupplyVoltageAlarmInhibit OBJECT-TYPE		 
		SYNTAX  INTEGER
		MAX-ACCESS  read-write
		STATUS  current
		DESCRIPTION
			"Inhibits OMMP101 CFP2 High Supply Voltage Alarm
			for the requested port
			-----------------------------
			ommp101InterfaceNumber:
			11 - LINE PORT
			-----------------------------
			Value:
			1 - Inhibit
			0 - Do Not Inhibit
			-----------------------------"
	::= { ommp101ConfigurationEntry 94 }

	ommp101Cfp2LowSupplyVoltageAlarmInhibit OBJECT-TYPE		 
		SYNTAX  INTEGER
		MAX-ACCESS  read-write
		STATUS  current
		DESCRIPTION
			"Inhibits OMMP101 CFP2 Low Supply Voltage Alarm
			for the requested port
			-----------------------------
			ommp101InterfaceNumber:
			11 - LINE PORT
			-----------------------------
			Value:
			1 - Inhibit
			0 - Do Not Inhibit
			-----------------------------"
	::= { ommp101ConfigurationEntry 95 }

	ommp101Cfp2HighSupplyVoltageWarningInhibit OBJECT-TYPE		 
		SYNTAX  INTEGER
		MAX-ACCESS  read-write
		STATUS  current
		DESCRIPTION
			"Inhibits OMMP101 CFP2 High Supply Voltage Warning
			for the requested port
			-----------------------------
			ommp101InterfaceNumber:
			11 - LINE PORT
			-----------------------------
			Value:
			1 - Inhibit
			0 - Do Not Inhibit
			-----------------------------"
	::= { ommp101ConfigurationEntry 96 }

	ommp101Cfp2LowSupplyVoltageWarningInhibit OBJECT-TYPE		 
		SYNTAX  INTEGER
		MAX-ACCESS  read-write
		STATUS  current
		DESCRIPTION
			"Inhibits OMMP101 CFP2 Low Supply Voltage Warning
			for the requested port
			-----------------------------
			ommp101InterfaceNumber:
			11 - LINE PORT
			-----------------------------
			Value:
			1 - Inhibit
			0 - Do Not Inhibit
			-----------------------------"
	::= { ommp101ConfigurationEntry 97 }

	ommp101Cfp2PresenceAbsenceNotificationInhibit OBJECT-TYPE		 
		SYNTAX  INTEGER
		MAX-ACCESS  read-write
		STATUS  current
		DESCRIPTION
			"Inhibits OMMP101 CFP2 Presence Absence Notification
			for the requested port
			-----------------------------
			ommp101InterfaceNumber:
			11 - LINE PORT
			-----------------------------
			Value:
			1 - Inhibit
			0 - Do Not Inhibit
			-----------------------------"
	::= { ommp101ConfigurationEntry 98 }

	ommp101SfpPlusInputPowerFailureAlarmInhibit OBJECT-TYPE		 
		SYNTAX  INTEGER
		MAX-ACCESS  read-write
		STATUS  current
		DESCRIPTION
			"Inhibits OMMP101 SFP PLUS Input Power Failure Alarm
			for the requested port
			-----------------------------
			ommp101InterfaceNumber:
			1 to 10 - CLIENT-1 to CLIENT-10
			-----------------------------
			Value:
			1 - Inhibit
			0 - Do Not Inhibit
			-----------------------------"
	::= { ommp101ConfigurationEntry 99 }

	ommp101SfpPlusOutputPowerFailureAlarmInhibit OBJECT-TYPE		 
		SYNTAX  INTEGER
		MAX-ACCESS  read-write
		STATUS  current
		DESCRIPTION
			"Inhibits OMMP101 SFP PLUS Output Power Failure Alarm
			for the requested port
			-----------------------------
			ommp101InterfaceNumber:
			1 to 10 - CLIENT-1 to CLIENT-10
			-----------------------------
			Value:
			1 - Inhibit
			0 - Do Not Inhibit
			-----------------------------"
	::= { ommp101ConfigurationEntry 100 }

	ommp101SfpPlusHighTemperatureAlarmInhibit OBJECT-TYPE		 
		SYNTAX  INTEGER
		MAX-ACCESS  read-write
		STATUS  current
		DESCRIPTION
			"Inhibits OMMP101 SFP PLUS High Temperature Alarm
			for the requested port
			-----------------------------
			ommp101InterfaceNumber:
			1 to 10 - CLIENT-1 to CLIENT-10
			-----------------------------
			Value:
			1 - Inhibit
			0 - Do Not Inhibit
			-----------------------------"
	::= { ommp101ConfigurationEntry 101 }

	ommp101SfpPlusLowTemperatureAlarmInhibit OBJECT-TYPE		 
		SYNTAX  INTEGER
		MAX-ACCESS  read-write
		STATUS  current
		DESCRIPTION
			"Inhibits OMMP101 SFP PLUS Low Temperature Alarm
			for the requested port
			-----------------------------
			ommp101InterfaceNumber:
			1 to 10 - CLIENT-1 to CLIENT-10
			-----------------------------
			Value:
			1 - Inhibit
			0 - Do Not Inhibit
			-----------------------------"
	::= { ommp101ConfigurationEntry 102 }

	ommp101SfpPlusHighTemperatureWarningInhibit OBJECT-TYPE		 
		SYNTAX  INTEGER
		MAX-ACCESS  read-write
		STATUS  current
		DESCRIPTION
			"Inhibits OMMP101 SFP PLUS High Temperature Warning
			for the requested port
			-----------------------------
			ommp101InterfaceNumber:
			1 to 10 - CLIENT-1 to CLIENT-10
			-----------------------------
			Value:
			1 - Inhibit
			0 - Do Not Inhibit
			-----------------------------"
	::= { ommp101ConfigurationEntry 103 }

	ommp101SfpPlusLowTemperatureWarningInhibit OBJECT-TYPE		 
		SYNTAX  INTEGER
		MAX-ACCESS  read-write
		STATUS  current
		DESCRIPTION
			"Inhibits OMMP101 SFP PLUS Low Temperature Warning
			for the requested port
			-----------------------------
			ommp101InterfaceNumber:
			1 to 10 - CLIENT-1 to CLIENT-10
			-----------------------------
			Value:
			1 - Inhibit
			0 - Do Not Inhibit
			-----------------------------"
	::= { ommp101ConfigurationEntry 104 }

	ommp101SfpPlusHighBiasCurrentAlarmInhibit OBJECT-TYPE		 
		SYNTAX  INTEGER
		MAX-ACCESS  read-write
		STATUS  current
		DESCRIPTION
			"Inhibits OMMP101 SFP PLUS High Bias Current Alarm
			for the requested port
			-----------------------------
			ommp101InterfaceNumber:
			1 to 10 - CLIENT-1 to CLIENT-10
			-----------------------------
			Value:
			1 - Inhibit
			0 - Do Not Inhibit
			-----------------------------"
	::= { ommp101ConfigurationEntry 105 }

	ommp101SfpPlusLowBiasCurrentAlarmInhibit OBJECT-TYPE		 
		SYNTAX  INTEGER
		MAX-ACCESS  read-write
		STATUS  current
		DESCRIPTION
			"Inhibits OMMP101 SFP PLUS Low Bias Current Alarm
			for the requested port
			-----------------------------
			ommp101InterfaceNumber:
			1 to 10 - CLIENT-1 to CLIENT-10
			-----------------------------
			Value:
			1 - Inhibit
			0 - Do Not Inhibit
			-----------------------------"
	::= { ommp101ConfigurationEntry 106 }

	ommp101SfpPlusHighBiasCurrentWarningInhibit OBJECT-TYPE		 
		SYNTAX  INTEGER
		MAX-ACCESS  read-write
		STATUS  current
		DESCRIPTION
			"Inhibits OMMP101 SFP PLUS High Bias Current Warning
			for the requested port
			-----------------------------
			ommp101InterfaceNumber:
			1 to 10 - CLIENT-1 to CLIENT-10
			-----------------------------
			Value:
			1 - Inhibit
			0 - Do Not Inhibit
			-----------------------------"
	::= { ommp101ConfigurationEntry 107 }

	ommp101SfpPlusLowBiasCurrentWarningInhibit OBJECT-TYPE		 
		SYNTAX  INTEGER
		MAX-ACCESS  read-write
		STATUS  current
		DESCRIPTION
			"Inhibits OMMP101 SFP PLUS Low Bias Current Warning
			for the requested port
			-----------------------------
			ommp101InterfaceNumber:
			1 to 10 - CLIENT-1 to CLIENT-10
			-----------------------------
			Value:
			1 - Inhibit
			0 - Do Not Inhibit
			-----------------------------"
	::= { ommp101ConfigurationEntry 108 }

	ommp101SfpPlusInputHighPowerAlarmInhibit OBJECT-TYPE		 
		SYNTAX  INTEGER
		MAX-ACCESS  read-write
		STATUS  current
		DESCRIPTION
			"Inhibits OMMP101 SFP PLUS Input High Power Alarm
			for the requested port
			-----------------------------
			ommp101InterfaceNumber:
			1 to 10 - CLIENT-1 to CLIENT-10
			-----------------------------
			Value:
			1 - Inhibit
			0 - Do Not Inhibit
			-----------------------------"
	::= { ommp101ConfigurationEntry 109 }

	ommp101SfpPlusInputLowPowerAlarmInhibit OBJECT-TYPE
		SYNTAX  INTEGER
		MAX-ACCESS  read-write
		STATUS  current
		DESCRIPTION
			"Inhibits OMMP101 SFP PLUS Input Low Power Alarm
			for the requested port
			-----------------------------
			ommp101InterfaceNumber:
			1 to 10 - CLIENT-1 to CLIENT-10
			-----------------------------
			Value:
			1 - Inhibit
			0 - Do Not Inhibit
			-----------------------------"
	::= { ommp101ConfigurationEntry 110 }

	ommp101SfpPlusInputHighPowerWarningInhibit OBJECT-TYPE		 
		SYNTAX  INTEGER
		MAX-ACCESS  read-write
		STATUS  current
		DESCRIPTION
			"Inhibits OMMP101 SFP PLUS Input High Power Warning
			for the requested port
			-----------------------------
			ommp101InterfaceNumber:
			1 to 10 - CLIENT-1 to CLIENT-10
			-----------------------------
			Value:
			1 - Inhibit
			0 - Do Not Inhibit
			-----------------------------"
	::= { ommp101ConfigurationEntry 111 }

	ommp101SfpPlusInputLowPowerWarningInhibit OBJECT-TYPE		 
		SYNTAX  INTEGER
		MAX-ACCESS  read-write
		STATUS  current
		DESCRIPTION
			"Inhibits OMMP101 SFP PLUS Input Low Power Warning
			for the requested port
			-----------------------------
			ommp101InterfaceNumber:
			1 to 10 - CLIENT-1 to CLIENT-10
			-----------------------------
			Value:
			1 - Inhibit
			0 - Do Not Inhibit
			-----------------------------"
	::= { ommp101ConfigurationEntry 112 }

	ommp101SfpPlusOutputHighPowerAlarmInhibit OBJECT-TYPE		 
		SYNTAX  INTEGER
		MAX-ACCESS  read-write
		STATUS  current
		DESCRIPTION
			"Inhibits OMMP101 SFP PLUS Output High Power Alarm
			for the requested port
			-----------------------------
			ommp101InterfaceNumber:
			1 to 10 - CLIENT-1 to CLIENT-10
			-----------------------------
			Value:
			1 - Inhibit
			0 - Do Not Inhibit
			-----------------------------"
	::= { ommp101ConfigurationEntry 113 }

	ommp101SfpPlusOutputLowPowerAlarmInhibit OBJECT-TYPE		 
		SYNTAX  INTEGER
		MAX-ACCESS  read-write
		STATUS  current
		DESCRIPTION
			"Inhibits OMMP101 SFP PLUS Output Low Power Alarm
			for the requested port
			-----------------------------
			ommp101InterfaceNumber:
			1 to 10 - CLIENT-1 to CLIENT-10
			-----------------------------
			Value:
			1 - Inhibit
			0 - Do Not Inhibit
			-----------------------------"
	::= { ommp101ConfigurationEntry 114 }

	ommp101SfpPlusOutputHighPowerWarningInhibit OBJECT-TYPE		 
		SYNTAX  INTEGER
		MAX-ACCESS  read-write
		STATUS  current
		DESCRIPTION
			"Inhibits OMMP101 SFP PLUS Output High Power Warning
			for the requested port
			-----------------------------
			ommp101InterfaceNumber:
			1 to 10 - CLIENT-1 to CLIENT-10
			-----------------------------
			Value:
			1 - Inhibit
			0 - Do Not Inhibit
			-----------------------------"
	::= { ommp101ConfigurationEntry 115 }

	ommp101SfpPlusOutputLowPowerWarningInhibit OBJECT-TYPE		 
		SYNTAX  INTEGER
		MAX-ACCESS  read-write
		STATUS  current
		DESCRIPTION
			"Inhibits OMMP101 SFP PLUS Output Low Power Warning
			for the requested port
			-----------------------------
			ommp101InterfaceNumber:
			1 to 10 - CLIENT-1 to CLIENT-10
			-----------------------------
			Value:
			1 - Inhibit
			0 - Do Not Inhibit
			-----------------------------"
	::= { ommp101ConfigurationEntry 116 }

	ommp101SfpPlusHighSupplyVoltageAlarmInhibit OBJECT-TYPE		 
		SYNTAX  INTEGER
		MAX-ACCESS  read-write
		STATUS  current
		DESCRIPTION
			"Inhibits OMMP101 SFP PLUS High Supply Voltage Alarm
			for the requested port
			-----------------------------
			ommp101InterfaceNumber:
			1 to 10 - CLIENT-1 to CLIENT-10
			-----------------------------
			Value:
			1 - Inhibit
			0 - Do Not Inhibit
			-----------------------------"
	::= { ommp101ConfigurationEntry 117 }

	ommp101SfpPlusLowSupplyVoltageAlarmInhibit OBJECT-TYPE		 
		SYNTAX  INTEGER
		MAX-ACCESS  read-write
		STATUS  current
		DESCRIPTION
			"Inhibits OMMP101 SFP PLUS Low Supply Voltage Alarm
			for the requested port
			-----------------------------
			ommp101InterfaceNumber:
			1 to 10 - CLIENT-1 to CLIENT-10
			-----------------------------
			Value:
			1 - Inhibit
			0 - Do Not Inhibit
			-----------------------------"
	::= { ommp101ConfigurationEntry 118 }

	ommp101SfpPlusHighSupplyVoltageWarningInhibit OBJECT-TYPE		 
		SYNTAX  INTEGER
		MAX-ACCESS  read-write
		STATUS  current
		DESCRIPTION
			"Inhibits OMMP101 SFP PLUS High Supply Voltage Warning
			for the requested port
			-----------------------------
			ommp101InterfaceNumber:
			1 to 10 - CLIENT-1 to CLIENT-10
			-----------------------------
			Value:
			1 - Inhibit
			0 - Do Not Inhibit
			-----------------------------"
	::= { ommp101ConfigurationEntry 119 }

	ommp101SfpPlusLowSupplyVoltageWarningInhibit OBJECT-TYPE		 
		SYNTAX  INTEGER
		MAX-ACCESS  read-write
		STATUS  current
		DESCRIPTION
			"Inhibits OMMP101 SFP PLUS Low Supply Voltage Warning
			for the requested port
			-----------------------------
			ommp101InterfaceNumber:
			1 to 10 - CLIENT-1 to CLIENT-10
			-----------------------------
			Value:
			1 - Inhibit
			0 - Do Not Inhibit
			-----------------------------"
	::= { ommp101ConfigurationEntry 120 }

	ommp101SfpPlusPresenceAbsenceNotificationInhibit OBJECT-TYPE		 
		SYNTAX  INTEGER
		MAX-ACCESS  read-write
		STATUS  current
		DESCRIPTION
			"Inhibits OMMP101 SFP PLUS Presence Absence Notification
			for the requested port
			-----------------------------
			ommp101InterfaceNumber:
			1 to 10 - CLIENT-1 to CLIENT-10
			-----------------------------
			Value:
			1 - Inhibit
			0 - Do Not Inhibit
			-----------------------------"
	::= { ommp101ConfigurationEntry 121 }

	ommp101SfpPlusTransmitFaultPresenceAlarmInhibit OBJECT-TYPE		 
		SYNTAX  INTEGER
		MAX-ACCESS  read-write
		STATUS  current
		DESCRIPTION
			"Inhibits OMMP101 SFP PLUS Transmit Fault Presence Alarm
			for the requested port
			-----------------------------
			ommp101InterfaceNumber:
			1 to 10 - CLIENT-1 to CLIENT-10
			-----------------------------
			Value:
			1 - Inhibit
			0 - Do Not Inhibit
			-----------------------------"
	::= { ommp101ConfigurationEntry 122 }

	ommp101OtuLossOfSignalAlarmInhibit OBJECT-TYPE		 
		SYNTAX  INTEGER
		MAX-ACCESS  read-write
		STATUS  current
		DESCRIPTION
			"Inhibits OMMP101 OTU Loss Of Signal Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 123 }

	ommp101OtuLossOfFrameAlarmInhibit OBJECT-TYPE		 
		SYNTAX  INTEGER
		MAX-ACCESS  read-write
		STATUS  current
		DESCRIPTION
			"Inhibits OMMP101 OTU Loss Of Frame Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 124 }

	ommp101OtuOutOfFrameAlarmInhibit OBJECT-TYPE		 
		SYNTAX  INTEGER
		MAX-ACCESS  read-write
		STATUS  current
		DESCRIPTION
			"Inhibits OMMP101 OTU Out Of Frame Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 125 }

	ommp101OtuLossOfMultiFrameAlarmInhibit OBJECT-TYPE		 
		SYNTAX  INTEGER
		MAX-ACCESS  read-write
		STATUS  current
		DESCRIPTION
			"Inhibits OMMP101 OTU Loss Of Multi Frame Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 126 }

	ommp101OtuOutOfMultiFrameAlarmInhibit OBJECT-TYPE		 
		SYNTAX  INTEGER
		MAX-ACCESS  read-write
		STATUS  current
		DESCRIPTION
			"Inhibits OMMP101 OTU Out Of Multi Frame Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 127 }

	ommp101OtuSignalFailAlarmInhibit OBJECT-TYPE		 
		SYNTAX  INTEGER
		MAX-ACCESS  read-write
		STATUS  current
		DESCRIPTION
			"Inhibits OMMP101 OTU Signal Fail Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 128 }

	ommp101OtuSignalDegradeAlarmInhibit OBJECT-TYPE		 
		SYNTAX  INTEGER
		MAX-ACCESS  read-write
		STATUS  current
		DESCRIPTION
			"Inhibits OMMP101 OTU Signal Degrade Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 129 }

	ommp101OtuAlarmIndicationSignalAlarmInhibit OBJECT-TYPE		 
		SYNTAX  INTEGER
		MAX-ACCESS  read-write
		STATUS  current
		DESCRIPTION
			"Inhibits OMMP101 OTU Alarm Indication Signal Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 130 }

	ommp101OtuIncomingAlignmentErrorAlarmInhibit OBJECT-TYPE		 
		SYNTAX  INTEGER
		MAX-ACCESS  read-write
		STATUS  current
		DESCRIPTION
			"Inhibits OMMP101 OTU Incoming Alignment Error Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 131 }

	ommp101OtuBackwardIncomingAlignmentErrorAlarmInhibit OBJECT-TYPE		 
		SYNTAX  INTEGER
		MAX-ACCESS  read-write
		STATUS  current
		DESCRIPTION
			"Inhibits OMMP101 OTU Backward Incoming Alignment Error Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 132 }

	ommp101OtuBackwardDefectIndicationAlarmInhibit OBJECT-TYPE		 
		SYNTAX  INTEGER
		MAX-ACCESS  read-write
		STATUS  current
		DESCRIPTION
			"Inhibits OMMP101 OTU Backward Defect Indication Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 133 }

	ommp101OduSignalFailAlarmInhibit OBJECT-TYPE		 
		SYNTAX  INTEGER
		MAX-ACCESS  read-write
		STATUS  current
		DESCRIPTION
			"Inhibits OMMP101 ODU Signal Fail Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 134 }

	ommp101OduSignalDegradeAlarmInhibit OBJECT-TYPE		 
		SYNTAX  INTEGER
		MAX-ACCESS  read-write
		STATUS  current
		DESCRIPTION
			"Inhibits OMMP101 ODU Signal Degrade Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 135 }

	ommp101OduAlarmIndicationSignalAlarmInhibit OBJECT-TYPE		 
		SYNTAX  INTEGER
		MAX-ACCESS  read-write
		STATUS  current
		DESCRIPTION
			"Inhibits OMMP101 ODU Alarm Indication Signal Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 136 }

	ommp101OduTcm1IncomingAlignmentErrorAlarmInhibit OBJECT-TYPE		 
		SYNTAX  INTEGER
		MAX-ACCESS  read-write
		STATUS  current
		DESCRIPTION
			"Inhibits OMMP101 ODU TCM1 Incoming Alignment Error
			Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 137 }

	ommp101OduTcm2IncomingAlignmentErrorAlarmInhibit OBJECT-TYPE		 
		SYNTAX  INTEGER
		MAX-ACCESS  read-write
		STATUS  current
		DESCRIPTION
			"Inhibits OMMP101 ODU TCM2 Incoming Alignment Error
			Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 138 }

	ommp101OduTcm3IncomingAlignmentErrorAlarmInhibit OBJECT-TYPE		 
		SYNTAX  INTEGER
		MAX-ACCESS  read-write
		STATUS  current
		DESCRIPTION
			"Inhibits OMMP101 ODU TCM3 Incoming Alignment Error
			Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 139 }

	ommp101OduTcm4IncomingAlignmentErrorAlarmInhibit OBJECT-TYPE		 
		SYNTAX  INTEGER
		MAX-ACCESS  read-write
		STATUS  current
		DESCRIPTION
			"Inhibits OMMP101 ODU TCM4 Incoming Alignment Error
			Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 140 }

	ommp101OduTcm5IncomingAlignmentErrorAlarmInhibit OBJECT-TYPE		 
		SYNTAX  INTEGER
		MAX-ACCESS  read-write
		STATUS  current
		DESCRIPTION
			"Inhibits OMMP101 ODU TCM5 Incoming Alignment Error
			Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 141 }

	ommp101OduTcm6IncomingAlignmentErrorAlarmInhibit OBJECT-TYPE		 
		SYNTAX  INTEGER
		MAX-ACCESS  read-write
		STATUS  current
		DESCRIPTION
			"Inhibits OMMP101 ODU TCM6 Incoming Alignment Error
			Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 142 }

	ommp101OduLockedDefectAlarmInhibit OBJECT-TYPE		 
		SYNTAX  INTEGER
		MAX-ACCESS  read-write
		STATUS  current
		DESCRIPTION
			"Inhibits OMMP101 ODU Locked Defect Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 143 }

	ommp101OduOpenConnectionIndicationAlarmInhibit OBJECT-TYPE		 
		SYNTAX  INTEGER
		MAX-ACCESS  read-write
		STATUS  current
		DESCRIPTION
			"Inhibits OMMP101 ODU Open Connection Indication
			Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 144 }

	ommp101OduBackwardDefectIndicationAlarmInhibit OBJECT-TYPE		 
		SYNTAX  INTEGER
		MAX-ACCESS  read-write
		STATUS  current
		DESCRIPTION
			"Inhibits OMMP101 ODU Backward Defect Indication
			Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 145 }

	ommp101OduTcm1BackwardIncomingAlignmentErrorAlarmInhibit OBJECT-TYPE		 
		SYNTAX  INTEGER
		MAX-ACCESS  read-write
		STATUS  current
		DESCRIPTION
			"Inhibits OMMP101 ODU TCM1 Backward Incoming
			Alignment Error Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 146 }

	ommp101OduTcm2BackwardIncomingAlignmentErrorAlarmInhibit OBJECT-TYPE		 
		SYNTAX  INTEGER
		MAX-ACCESS  read-write
		STATUS  current
		DESCRIPTION
			"Inhibits OMMP101 ODU TCM2 Backward Incoming
			Alignment Error Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 147 }

	ommp101OduTcm3BackwardIncomingAlignmentErrorAlarmInhibit OBJECT-TYPE		 
		SYNTAX  INTEGER
		MAX-ACCESS  read-write
		STATUS  current
		DESCRIPTION
			"Inhibits OMMP101 ODU TCM3 Backward Incoming
			Alignment Error Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 148 }

	ommp101OduTcm4BackwardIncomingAlignmentErrorAlarmInhibit OBJECT-TYPE		 
		SYNTAX  INTEGER
		MAX-ACCESS  read-write
		STATUS  current
		DESCRIPTION
			"Inhibits OMMP101 ODU TCM4 Backward Incoming
			Alignment Error Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 149 }

	ommp101OduTcm5BackwardIncomingAlignmentErrorAlarmInhibit OBJECT-TYPE		 
		SYNTAX  INTEGER
		MAX-ACCESS  read-write
		STATUS  current
		DESCRIPTION
			"Inhibits OMMP101 ODU TCM5 Backward Incoming
			Alignment Error Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 150 }

	ommp101OduTcm6BackwardIncomingAlignmentErrorAlarmInhibit OBJECT-TYPE		 
		SYNTAX  INTEGER
		MAX-ACCESS  read-write
		STATUS  current
		DESCRIPTION
			"Inhibits OMMP101 ODU TCM6 Backward Incoming
			Alignment Error Alarm for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 151 }

	ommp101OduLossOfFrameLossOfMultiframeAlarmInhibit OBJECT-TYPE		 
		SYNTAX  INTEGER
		MAX-ACCESS  read-write
		STATUS  current
		DESCRIPTION
			"Inhibits OMMP101 ODU Loss Of Frame Loss Of
			Multiframe Alarm for the requested port
			-----------------------------
			ommp101InterfaceNumber:
			1, 2, 3, 4 - Slice number
			-----------------------------
			Value:
			1 - Inhibit
			0 - Do Not Inhibit
			-----------------------------"
	::= { ommp101ConfigurationEntry 152 }

	ommp101OpuPayloadMismatchAlarmInhibit OBJECT-TYPE		 
		SYNTAX  INTEGER
		MAX-ACCESS  read-write
		STATUS  current
		DESCRIPTION
			"Inhibits OMMP101 OPU Payload Mismatch Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 153 }

	ommp101SdhLossOfSignalAlarmInhibit OBJECT-TYPE		 
		SYNTAX  INTEGER
		MAX-ACCESS  read-write
		STATUS  current
		DESCRIPTION
			"Inhibits OMMP101 SDH Loss Of Signal Alarm
			for the requested port
			-----------------------------
			ommp101InterfaceNumber:
			1 to 10 - CLIENT-1 to CLIENT-10
			-----------------------------
			Value:
			1 - Inhibit
			0 - Do Not Inhibit
			-----------------------------"
	::= { ommp101ConfigurationEntry 154 }

	ommp101SdhOutOfFrameAlarmInhibit OBJECT-TYPE		 
		SYNTAX  INTEGER
		MAX-ACCESS  read-write
		STATUS  current
		DESCRIPTION
			"Inhibits OMMP101 SDH Out Of Frame Alarm
			for the requested port
			-----------------------------
			ommp101InterfaceNumber:
			1 to 10 - CLIENT-1 to CLIENT-10
			-----------------------------
			Value:
			1 - Inhibit
			0 - Do Not Inhibit
			-----------------------------"
	::= { ommp101ConfigurationEntry 155 }

	ommp101SdhLossOfFrameAlarmInhibit OBJECT-TYPE		 
		SYNTAX  INTEGER
		MAX-ACCESS  read-write
		STATUS  current
		DESCRIPTION
			"Inhibits OMMP101 SDH Loss Of Frame Alarm
			for the requested port
			-----------------------------
			ommp101InterfaceNumber:
			1 to 10 - CLIENT-1 to CLIENT-10
			-----------------------------
			Value:
			1 - Inhibit
			0 - Do Not Inhibit
			-----------------------------"
	::= { ommp101ConfigurationEntry 156 }

	ommp101SdhRsTraceIdentifierMismatchAlarmInhibit OBJECT-TYPE		 
		SYNTAX  INTEGER
		MAX-ACCESS  read-write
		STATUS  current
		DESCRIPTION
			"Inhibits OMMP101 SDH Rs Trace Identifier
			Mismatch Alarm for the requested port
			-----------------------------
			ommp101InterfaceNumber:
			1 to 10 - CLIENT-1 to CLIENT-10
			-----------------------------
			Value:
			1 - Inhibit
			0 - Do Not Inhibit
			-----------------------------"
	::= { ommp101ConfigurationEntry 157 }

	ommp101SdhMsAlarmIndicationSignalAlarmInhibit OBJECT-TYPE		 
		SYNTAX  INTEGER
		MAX-ACCESS  read-write
		STATUS  current
		DESCRIPTION
			"Inhibits OMMP101 SDH Ms Alarm Indication Signal
			Alarm for the requested port
			-----------------------------
			ommp101InterfaceNumber:
			1 to 10 - CLIENT-1 to CLIENT-10
			-----------------------------
			Value:
			1 - Inhibit
			0 - Do Not Inhibit
			-----------------------------"
	::= { ommp101ConfigurationEntry 158 }

	ommp101SdhMsRemoteDefectIndicationAlarmInhibit OBJECT-TYPE		 
		SYNTAX  INTEGER
		MAX-ACCESS  read-write
		STATUS  current
		DESCRIPTION
			"Inhibits OMMP101 SDH Ms Remote Defect Indication
			Alarm for the requested port
			-----------------------------
			ommp101InterfaceNumber:
			1 to 10 - CLIENT-1 to CLIENT-10
			-----------------------------
			Value:
			1 - Inhibit
			0 - Do Not Inhibit
			-----------------------------"
	::= { ommp101ConfigurationEntry 159 }

	ommp101EthernetLossOfSignalAlarmInhibit OBJECT-TYPE		 
		SYNTAX  INTEGER
		MAX-ACCESS  read-write
		STATUS  current
		DESCRIPTION
			"Inhibits OMMP101 Ethernet Loss Of Signal Alarm
			for the requested port
			-----------------------------
			ommp101InterfaceNumber:
			1 to 10 - CLIENT-1 to CLIENT-10
			-----------------------------
			Value:
			1 - Inhibit
			0 - Do Not Inhibit
			-----------------------------"
	::= { ommp101ConfigurationEntry 160 }

	ommp101EthernetLinkFailureAlarmInhibit OBJECT-TYPE		 
		SYNTAX  INTEGER
		MAX-ACCESS  read-write
		STATUS  current
		DESCRIPTION
			"Inhibits OMMP101 Ethernet Link Failure Alarm
			for the requested port
			-----------------------------
			ommp101InterfaceNumber:
			1 to 10 - CLIENT-1 to CLIENT-10
			-----------------------------
			Value:
			1 - Inhibit
			0 - Do Not Inhibit
			-----------------------------"
	::= { ommp101ConfigurationEntry 161 }

	ommp101EthernetHighBerAlarmInhibit OBJECT-TYPE		 
		SYNTAX  INTEGER
		MAX-ACCESS  read-write
		STATUS  current
		DESCRIPTION
			"Inhibits OMMP101 Ethernet High Ber Alarm
			for the requested port
			-----------------------------
			ommp101InterfaceNumber:
			1 to 10 - CLIENT-1 to CLIENT-10
			-----------------------------
			Value:
			1 - Inhibit
			0 - Do Not Inhibit
			-----------------------------"
	::= { ommp101ConfigurationEntry 162 }

	ommp101EthernetLocalFaultAlarmInhibit OBJECT-TYPE		 
		SYNTAX  INTEGER
		MAX-ACCESS  read-write
		STATUS  current
		DESCRIPTION
			"Inhibits OMMP101 Ethernet Local Fault Alarm
			for the requested port
			-----------------------------
			ommp101InterfaceNumber:
			1 to 10 - CLIENT-1 to CLIENT-10
			-----------------------------
			Value:
			1 - Inhibit
			0 - Do Not Inhibit
			-----------------------------"
	::= { ommp101ConfigurationEntry 163 }

	ommp101EthernetRemoteFaultAlarmInhibit OBJECT-TYPE		 
		SYNTAX  INTEGER
		MAX-ACCESS  read-write
		STATUS  current
		DESCRIPTION
			"Inhibits OMMP101 Ethernet Remote Fault Alarm
			for the requested port
			-----------------------------
			ommp101InterfaceNumber:
			1 to 10 - CLIENT-1 to CLIENT-10
			-----------------------------
			Value:
			1 - Inhibit
			0 - Do Not Inhibit
			-----------------------------"
	::= { ommp101ConfigurationEntry 164 }

	ommp101Cfp2InputPowerFailureAlarmSeverity OBJECT-TYPE		 
		SYNTAX  DisplayString
		MAX-ACCESS  read-write
		STATUS  current
		DESCRIPTION
			"Set or Get the alarm severity level of the
			OMMP101 CFP2 Input Power Failure Alarm   
			for requested port
			-----------------------------
			ommp101InterfaceNumber:
			11 - LINE PORT
			-----------------------------
			Value:
			critical
			major
			minor
			deferred
			---------------------------"
	::= { ommp101ConfigurationEntry 165 }

	ommp101Cfp2OutputPowerFailureAlarmSeverity OBJECT-TYPE		 
		SYNTAX  DisplayString
		MAX-ACCESS  read-write
		STATUS  current
		DESCRIPTION
			"Set or Get the alarm severity level of the
			OMMP101 CFP2 Output Power Failure Alarm   
			for requested port
			-----------------------------
			ommp101InterfaceNumber:
			11 - LINE PORT
			-----------------------------
			Value:
			critical
			major
			minor
			deferred
			---------------------------"
	::= { ommp101ConfigurationEntry 166 }

	ommp101Cfp2HighTemperatureAlarmSeverity OBJECT-TYPE		 
		SYNTAX  DisplayString
		MAX-ACCESS  read-write
		STATUS  current
		DESCRIPTION
			"Set or Get the alarm severity level of the
			OMMP101 CFP2 High Temperature Alarm   
			for requested port
			-----------------------------
			ommp101InterfaceNumber:
			11 - LINE PORT
			-----------------------------
			Value:
			critical
			major
			minor
			deferred
			---------------------------"
	::= { ommp101ConfigurationEntry 167 }

	ommp101Cfp2LowTemperatureAlarmSeverity OBJECT-TYPE		 
		SYNTAX  DisplayString
		MAX-ACCESS  read-write
		STATUS  current
		DESCRIPTION
			"Set or Get the alarm severity level of the
			OMMP101 CFP2 Low Temperature Alarm   
			for requested port
			-----------------------------
			ommp101InterfaceNumber:
			11 - LINE PORT
			-----------------------------
			Value:
			critical
			major
			minor
			deferred
			---------------------------"
	::= { ommp101ConfigurationEntry 168 }

	ommp101Cfp2HighTemperatureWarningSeverity OBJECT-TYPE		 
		SYNTAX  DisplayString
		MAX-ACCESS  read-write
		STATUS  current
		DESCRIPTION
			"Set or Get the alarm severity level of the
			OMMP101 CFP2 High Temperature Warning   
			for requested port
			-----------------------------
			ommp101InterfaceNumber:
			11 - LINE PORT
			-----------------------------
			Value:
			critical
			major
			minor
			deferred
			---------------------------"
	::= { ommp101ConfigurationEntry 169 }

	ommp101Cfp2LowTemperatureWarningSeverity OBJECT-TYPE		 
		SYNTAX  DisplayString
		MAX-ACCESS  read-write
		STATUS  current
		DESCRIPTION
			"Set or Get the alarm severity level of the
			OMMP101 CFP2 Low Temperature Warning   
			for requested port
			-----------------------------
			ommp101InterfaceNumber:
			11 - LINE PORT
			-----------------------------
			Value:
			critical
			major
			minor
			deferred
			---------------------------"
	::= { ommp101ConfigurationEntry 170 }

	ommp101Cfp2InputHighPowerAlarmSeverity OBJECT-TYPE		 
		SYNTAX  DisplayString
		MAX-ACCESS  read-write
		STATUS  current
		DESCRIPTION
			"Set or Get the alarm severity level of the
			OMMP101 CFP2 Input High Power Alarm   
			for requested port
			-----------------------------
			ommp101InterfaceNumber:
			11 - LINE PORT
			-----------------------------
			Value:
			critical
			major
			minor
			deferred
			---------------------------"
	::= { ommp101ConfigurationEntry 171 }

	ommp101Cfp2InputLowPowerAlarmSeverity OBJECT-TYPE		 
		SYNTAX  DisplayString
		MAX-ACCESS  read-write
		STATUS  current
		DESCRIPTION
			"Set or Get the alarm severity level of the
			OMMP101 CFP2 Input Low Power Alarm   
			for requested port
			-----------------------------
			ommp101InterfaceNumber:
			11 - LINE PORT
			-----------------------------
			Value:
			critical
			major
			minor
			deferred
			---------------------------"
	::= { ommp101ConfigurationEntry 172 }

	ommp101Cfp2InputHighPowerWarningSeverity OBJECT-TYPE		 
		SYNTAX  DisplayString
		MAX-ACCESS  read-write
		STATUS  current
		DESCRIPTION
			"Set or Get the alarm severity level of the
			OMMP101 CFP2 Input High Power Warning   
			for requested port
			-----------------------------
			ommp101InterfaceNumber:
			11 - LINE PORT
			-----------------------------
			Value:
			critical
			major
			minor
			deferred
			---------------------------"
	::= { ommp101ConfigurationEntry 173 }

	ommp101Cfp2InputLowPowerWarningSeverity OBJECT-TYPE		 
		SYNTAX  DisplayString
		MAX-ACCESS  read-write
		STATUS  current
		DESCRIPTION
			"Set or Get the alarm severity level of the
			OMMP101 CFP2 Input Low Power Warning   
			for requested port
			-----------------------------
			ommp101InterfaceNumber:
			11 - LINE PORT
			-----------------------------
			Value:
			critical
			major
			minor
			deferred
			---------------------------"
	::= { ommp101ConfigurationEntry 174 }

	ommp101Cfp2OutputHighPowerAlarmSeverity OBJECT-TYPE		 
		SYNTAX  DisplayString
		MAX-ACCESS  read-write
		STATUS  current
		DESCRIPTION
			"Set or Get the alarm severity level of the
			OMMP101 CFP2 Output High Power Alarm   
			for requested port
			-----------------------------
			ommp101InterfaceNumber:
			11 - LINE PORT
			-----------------------------
			Value:
			critical
			major
			minor
			deferred
			---------------------------"
	::= { ommp101ConfigurationEntry 175 }

	ommp101Cfp2OutputLowPowerAlarmSeverity OBJECT-TYPE		 
		SYNTAX  DisplayString
		MAX-ACCESS  read-write
		STATUS  current
		DESCRIPTION
			"Set or Get the alarm severity level of the
			OMMP101 CFP2 Output Low Power Alarm   
			for requested port
			-----------------------------
			ommp101InterfaceNumber:
			11 - LINE PORT
			-----------------------------
			Value:
			critical
			major
			minor
			deferred
			---------------------------"
	::= { ommp101ConfigurationEntry 176 }

	ommp101Cfp2OutputHighPowerWarningSeverity OBJECT-TYPE		 
		SYNTAX  DisplayString
		MAX-ACCESS  read-write
		STATUS  current
		DESCRIPTION
			"Set or Get the alarm severity level of the
			OMMP101 CFP2 Output High Power Warning   
			for requested port
			-----------------------------
			ommp101InterfaceNumber:
			11 - LINE PORT
			-----------------------------
			Value:
			critical
			major
			minor
			deferred
			---------------------------"
	::= { ommp101ConfigurationEntry 177 }

	ommp101Cfp2OutputLowPowerWarningSeverity OBJECT-TYPE		 
		SYNTAX  DisplayString
		MAX-ACCESS  read-write
		STATUS  current
		DESCRIPTION
			"Set or Get the alarm severity level of the
			OMMP101 CFP2 Output Low Power Warning   
			for requested port
			-----------------------------
			ommp101InterfaceNumber:
			11 - LINE PORT
			-----------------------------
			Value:
			critical
			major
			minor
			deferred
			---------------------------"
	::= { ommp101ConfigurationEntry 178 }

	ommp101Cfp2HighSupplyVoltageAlarmSeverity OBJECT-TYPE		 
		SYNTAX  DisplayString
		MAX-ACCESS  read-write
		STATUS  current
		DESCRIPTION
			"Set or Get the alarm severity level of the
			OMMP101 CFP2 High Supply Voltage Alarm   
			for requested port
			-----------------------------
			ommp101InterfaceNumber:
			11 - LINE PORT
			-----------------------------
			Value:
			critical
			major
			minor
			deferred
			---------------------------"
	::= { ommp101ConfigurationEntry 179 }

	ommp101Cfp2LowSupplyVoltageAlarmSeverity OBJECT-TYPE		 
		SYNTAX  DisplayString
		MAX-ACCESS  read-write
		STATUS  current
		DESCRIPTION
			"Set or Get the alarm severity level of the
			OMMP101 CFP2 Low Supply Voltage Alarm   
			for requested port
			-----------------------------
			ommp101InterfaceNumber:
			11 - LINE PORT
			-----------------------------
			Value:
			critical
			major
			minor
			deferred
			---------------------------"
	::= { ommp101ConfigurationEntry 180 }

	ommp101Cfp2HighSupplyVoltageWarningSeverity OBJECT-TYPE		 
		SYNTAX  DisplayString
		MAX-ACCESS  read-write
		STATUS  current
		DESCRIPTION
			"Set or Get the alarm severity level of the
			OMMP101 CFP2 High Supply Voltage Warning   
			for requested port
			-----------------------------
			ommp101InterfaceNumber:
			11 - LINE PORT
			-----------------------------
			Value:
			critical
			major
			minor
			deferred
			---------------------------"
	::= { ommp101ConfigurationEntry 181 }

	ommp101Cfp2LowSupplyVoltageWarningSeverity OBJECT-TYPE		 
		SYNTAX  DisplayString
		MAX-ACCESS  read-write
		STATUS  current
		DESCRIPTION
			"Set or Get the alarm severity level of the
			OMMP101 CFP2 Low Supply Voltage Warning   
			for requested port
			-----------------------------
			ommp101InterfaceNumber:
			11 - LINE PORT
			-----------------------------
			Value:
			critical
			major
			minor
			deferred
			---------------------------"
	::= { ommp101ConfigurationEntry 182 }

	ommp101Cfp2PresenceAbsenceNotificationSeverity OBJECT-TYPE		 
		SYNTAX  DisplayString
		MAX-ACCESS  read-write
		STATUS  current
		DESCRIPTION
			"Set or Get the alarm severity level of the
			OMMP101 CFP2 Presence Absence Notification   
			for requested port
			-----------------------------
			ommp101InterfaceNumber:
			11 - LINE PORT
			-----------------------------
			Value:
			critical
			major
			minor
			deferred
			---------------------------"
	::= { ommp101ConfigurationEntry 183 }

	ommp101SfpPlusInputPowerFailureAlarmSeverity OBJECT-TYPE		 
		SYNTAX  DisplayString
		MAX-ACCESS  read-write
		STATUS  current
		DESCRIPTION
			"Set or Get the alarm severity level of the
			OMMP101 SFP PLUS Input Power Failure Alarm   
			for requested port
			-----------------------------
			ommp101InterfaceNumber:
			1 to 10 - CLIENT-1 to CLIENT-10
			-----------------------------
			Value:
			critical
			major
			minor
			deferred
			---------------------------"
	::= { ommp101ConfigurationEntry 184 }

	ommp101SfpPlusOutputPowerFailureAlarmSeverity OBJECT-TYPE		 
		SYNTAX  DisplayString
		MAX-ACCESS  read-write
		STATUS  current
		DESCRIPTION
			"Set or Get the alarm severity level of the
			OMMP101 SFP PLUS Output Power Failure Alarm   
			for requested port
			-----------------------------
			ommp101InterfaceNumber:
			1 to 10 - CLIENT-1 to CLIENT-10
			-----------------------------
			Value:
			critical
			major
			minor
			deferred
			---------------------------"
	::= { ommp101ConfigurationEntry 185 }

	ommp101SfpPlusHighTemperatureAlarmSeverity OBJECT-TYPE		 
		SYNTAX  DisplayString
		MAX-ACCESS  read-write
		STATUS  current
		DESCRIPTION
			"Set or Get the alarm severity level of the
			OMMP101 SFP PLUS High Temperature Alarm   
			for requested port
			-----------------------------
			ommp101InterfaceNumber:
			1 to 10 - CLIENT-1 to CLIENT-10
			-----------------------------
			Value:
			critical
			major
			minor
			deferred
			---------------------------"
	::= { ommp101ConfigurationEntry 186 }

	ommp101SfpPlusLowTemperatureAlarmSeverity OBJECT-TYPE		 
		SYNTAX  DisplayString
		MAX-ACCESS  read-write
		STATUS  current
		DESCRIPTION
			"Set or Get the alarm severity level of the
			OMMP101 SFP PLUS Low Temperature Alarm   
			for requested port
			-----------------------------
			ommp101InterfaceNumber:
			1 to 10 - CLIENT-1 to CLIENT-10
			-----------------------------
			Value:
			critical
			major
			minor
			deferred
			---------------------------"
	::= { ommp101ConfigurationEntry 187 }

	ommp101SfpPlusHighTemperatureWarningSeverity OBJECT-TYPE		 
		SYNTAX  DisplayString
		MAX-ACCESS  read-write
		STATUS  current
		DESCRIPTION
			"Set or Get the alarm severity level of the
			OMMP101 SFP PLUS High Temperature Warning   
			for requested port
			-----------------------------
			ommp101InterfaceNumber:
			1 to 10 - CLIENT-1 to CLIENT-10
			-----------------------------
			Value:
			critical
			major
			minor
			deferred
			---------------------------"
	::= { ommp101ConfigurationEntry 188 }

	ommp101SfpPlusLowTemperatureWarningSeverity OBJECT-TYPE		 
		SYNTAX  DisplayString
		MAX-ACCESS  read-write
		STATUS  current
		DESCRIPTION
			"Set or Get the alarm severity level of the
			OMMP101 SFP PLUS Low Temperature Warning   
			for requested port
			-----------------------------
			ommp101InterfaceNumber:
			1 to 10 - CLIENT-1 to CLIENT-10
			-----------------------------
			Value:
			critical
			major
			minor
			deferred
			---------------------------"
	::= { ommp101ConfigurationEntry 189 }

	ommp101SfpPlusHighBiasCurrentAlarmSeverity OBJECT-TYPE		 
		SYNTAX  DisplayString
		MAX-ACCESS  read-write
		STATUS  current
		DESCRIPTION
			"Set or Get the alarm severity level of the
			OMMP101 SFP PLUS High Bias Current Alarm   
			for requested port
			-----------------------------
			ommp101InterfaceNumber:
			1 to 10 - CLIENT-1 to CLIENT-10
			-----------------------------
			Value:
			critical
			major
			minor
			deferred
			---------------------------"
	::= { ommp101ConfigurationEntry 190 }

	ommp101SfpPlusLowBiasCurrentAlarmSeverity OBJECT-TYPE		 
		SYNTAX  DisplayString
		MAX-ACCESS  read-write
		STATUS  current
		DESCRIPTION
			"Set or Get the alarm severity level of the
			OMMP101 SFP PLUS Low Bias Current Alarm   
			for requested port
			-----------------------------
			ommp101InterfaceNumber:
			1 to 10 - CLIENT-1 to CLIENT-10
			-----------------------------
			Value:
			critical
			major
			minor
			deferred
			---------------------------"
	::= { ommp101ConfigurationEntry 191 }

	ommp101SfpPlusHighBiasCurrentWarningSeverity OBJECT-TYPE		 
		SYNTAX  DisplayString
		MAX-ACCESS  read-write
		STATUS  current
		DESCRIPTION
			"Set or Get the alarm severity level of the
			OMMP101 SFP PLUS High Bias Current Warning   
			for requested port
			-----------------------------
			ommp101InterfaceNumber:
			1 to 10 - CLIENT-1 to CLIENT-10
			-----------------------------
			Value:
			critical
			major
			minor
			deferred
			---------------------------"
	::= { ommp101ConfigurationEntry 192 }

	ommp101SfpPlusLowBiasCurrentWarningSeverity OBJECT-TYPE		 
		SYNTAX  DisplayString
		MAX-ACCESS  read-write
		STATUS  current
		DESCRIPTION
			"Set or Get the alarm severity level of the
			OMMP101 SFP PLUS Low Bias Current Warning   
			for requested port
			-----------------------------
			ommp101InterfaceNumber:
			1 to 10 - CLIENT-1 to CLIENT-10
			-----------------------------
			Value:
			critical
			major
			minor
			deferred
			---------------------------"
	::= { ommp101ConfigurationEntry 193 }

	ommp101SfpPlusInputHighPowerAlarmSeverity OBJECT-TYPE		 
		SYNTAX  DisplayString
		MAX-ACCESS  read-write
		STATUS  current
		DESCRIPTION
			"Set or Get the alarm severity level of the
			OMMP101 SFP PLUS Input High Power Alarm   
			for requested port
			-----------------------------
			ommp101InterfaceNumber:
			1 to 10 - CLIENT-1 to CLIENT-10
			-----------------------------
			Value:
			critical
			major
			minor
			deferred
			---------------------------"
	::= { ommp101ConfigurationEntry 194 }

	ommp101SfpPlusInputLowPowerAlarmSeverity OBJECT-TYPE		 
		SYNTAX  DisplayString
		MAX-ACCESS  read-write
		STATUS  current
		DESCRIPTION
			"Set or Get the alarm severity level of the
			OMMP101 SFP PLUS Input Low Power Alarm   
			for requested port
			-----------------------------
			ommp101InterfaceNumber:
			1 to 10 - CLIENT-1 to CLIENT-10
			-----------------------------
			Value:
			critical
			major
			minor
			deferred
			---------------------------"
	::= { ommp101ConfigurationEntry 195 }

	ommp101SfpPlusInputHighPowerWarningSeverity OBJECT-TYPE		 
		SYNTAX  DisplayString
		MAX-ACCESS  read-write
		STATUS  current
		DESCRIPTION
			"Set or Get the alarm severity level of the
			OMMP101 SFP PLUS Input High Power Warning   
			for requested port
			-----------------------------
			ommp101InterfaceNumber:
			1 to 10 - CLIENT-1 to CLIENT-10
			-----------------------------
			Value:
			critical
			major
			minor
			deferred
			---------------------------"
	::= { ommp101ConfigurationEntry 196 }

	ommp101SfpPlusInputLowPowerWarningSeverity OBJECT-TYPE		 
		SYNTAX  DisplayString
		MAX-ACCESS  read-write
		STATUS  current
		DESCRIPTION
			"Set or Get the alarm severity level of the
			OMMP101 SFP PLUS Input Low Power Warning   
			for requested port
			-----------------------------
			ommp101InterfaceNumber:
			1 to 10 - CLIENT-1 to CLIENT-10
			-----------------------------
			Value:
			critical
			major
			minor
			deferred
			---------------------------"
	::= { ommp101ConfigurationEntry 197 }

	ommp101SfpPlusOutputHighPowerAlarmSeverity OBJECT-TYPE		 
		SYNTAX  DisplayString
		MAX-ACCESS  read-write
		STATUS  current
		DESCRIPTION
			"Set or Get the alarm severity level of the
			OMMP101 SFP PLUS Output High Power Alarm   
			for requested port
			-----------------------------
			ommp101InterfaceNumber:
			1 to 10 - CLIENT-1 to CLIENT-10
			-----------------------------
			Value:
			critical
			major
			minor
			deferred
			---------------------------"
	::= { ommp101ConfigurationEntry 198 }

	ommp101SfpPlusOutputLowPowerAlarmSeverity OBJECT-TYPE		 
		SYNTAX  DisplayString
		MAX-ACCESS  read-write
		STATUS  current
		DESCRIPTION
			"Set or Get the alarm severity level of the
			OMMP101 SFP PLUS Output Low Power Alarm   
			for requested port
			-----------------------------
			ommp101InterfaceNumber:
			1 to 10 - CLIENT-1 to CLIENT-10
			-----------------------------
			Value:
			critical
			major
			minor
			deferred
			---------------------------"
	::= { ommp101ConfigurationEntry 199 }

	ommp101SfpPlusOutputHighPowerWarningSeverity OBJECT-TYPE		 
		SYNTAX  DisplayString
		MAX-ACCESS  read-write
		STATUS  current
		DESCRIPTION
			"Set or Get the alarm severity level of the
			OMMP101 SFP PLUS Output High Power Warning   
			for requested port
			-----------------------------
			ommp101InterfaceNumber:
			1 to 10 - CLIENT-1 to CLIENT-10
			-----------------------------
			Value:
			critical
			major
			minor
			deferred
			---------------------------"
	::= { ommp101ConfigurationEntry 200 }

	ommp101SfpPlusOutputLowPowerWarningSeverity OBJECT-TYPE		 
		SYNTAX  DisplayString
		MAX-ACCESS  read-write
		STATUS  current
		DESCRIPTION
			"Set or Get the alarm severity level of the
			OMMP101 SFP PLUS Output Low Power Warning   
			for requested port
			-----------------------------
			ommp101InterfaceNumber:
			1 to 10 - CLIENT-1 to CLIENT-10
			-----------------------------
			Value:
			critical
			major
			minor
			deferred
			---------------------------"
	::= { ommp101ConfigurationEntry 201 }

	ommp101SfpPlusHighSupplyVoltageAlarmSeverity OBJECT-TYPE		 
		SYNTAX  DisplayString
		MAX-ACCESS  read-write
		STATUS  current
		DESCRIPTION
			"Set or Get the alarm severity level of the
			OMMP101 SFP PLUS High Supply Voltage Alarm   
			for requested port
			-----------------------------
			ommp101InterfaceNumber:
			1 to 10 - CLIENT-1 to CLIENT-10
			-----------------------------
			Value:
			critical
			major
			minor
			deferred
			---------------------------"
	::= { ommp101ConfigurationEntry 202 }

	ommp101SfpPlusLowSupplyVoltageAlarmSeverity OBJECT-TYPE		 
		SYNTAX  DisplayString
		MAX-ACCESS  read-write
		STATUS  current
		DESCRIPTION
			"Set or Get the alarm severity level of the
			OMMP101 SFP PLUS Low Supply Voltage Alarm   
			for requested port
			-----------------------------
			ommp101InterfaceNumber:
			1 to 10 - CLIENT-1 to CLIENT-10
			-----------------------------
			Value:
			critical
			major
			minor
			deferred
			---------------------------"
	::= { ommp101ConfigurationEntry 203 }

	ommp101SfpPlusHighSupplyVoltageWarningSeverity OBJECT-TYPE		 
		SYNTAX  DisplayString
		MAX-ACCESS  read-write
		STATUS  current
		DESCRIPTION
			"Set or Get the alarm severity level of the
			OMMP101 SFP PLUS High Supply Voltage Warning   
			for requested port
			-----------------------------
			ommp101InterfaceNumber:
			1 to 10 - CLIENT-1 to CLIENT-10
			-----------------------------
			Value:
			critical
			major
			minor
			deferred
			---------------------------"
	::= { ommp101ConfigurationEntry 204 }

	ommp101SfpPlusLowSupplyVoltageWarningSeverity OBJECT-TYPE		 
		SYNTAX  DisplayString
		MAX-ACCESS  read-write
		STATUS  current
		DESCRIPTION
			"Set or Get the alarm severity level of the
			OMMP101 SFP PLUS Low Supply Voltage Warning   
			for requested port
			-----------------------------
			ommp101InterfaceNumber:
			1 to 10 - CLIENT-1 to CLIENT-10
			-----------------------------
			Value:
			critical
			major
			minor
			deferred
			---------------------------"
	::= { ommp101ConfigurationEntry 205 }

	ommp101SfpPlusPresenceAbsenceNotificationSeverity OBJECT-TYPE		 
		SYNTAX  DisplayString
		MAX-ACCESS  read-write
		STATUS  current
		DESCRIPTION
			"Set or Get the alarm severity level of the
			OMMP101 SFP PLUS Presence Absence Notification   
			for requested port
			-----------------------------
			ommp101InterfaceNumber:
			1 to 10 - CLIENT-1 to CLIENT-10
			11 - LINE PORT
			-----------------------------
			Value:
			critical
			major
			minor
			deferred
			---------------------------"
	::= { ommp101ConfigurationEntry 206 }

	ommp101SfpPlusTransmitFaultPresenceAlarmSeverity OBJECT-TYPE		 
		SYNTAX  DisplayString
		MAX-ACCESS  read-write
		STATUS  current
		DESCRIPTION
			"Set or Get the alarm severity level of the
			OMMP101 SFP PLUS Transmit Fault Presence Alarm   
			for requested port
			-----------------------------
			ommp101InterfaceNumber:
			1 to 10 - CLIENT-1 to CLIENT-10
			-----------------------------
			Value:
			critical
			major
			minor
			deferred
			---------------------------"
	::= { ommp101ConfigurationEntry 207 }

	ommp101OtuLossOfSignalAlarmSeverity OBJECT-TYPE		 
		SYNTAX  DisplayString
		MAX-ACCESS  read-write
		STATUS  current
		DESCRIPTION
			"Set or Get the alarm severity level of the
			OMMP101 OTU Loss Of Signal Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 208 }

	ommp101OtuLossOfFrameAlarmSeverity OBJECT-TYPE		 
		SYNTAX  DisplayString
		MAX-ACCESS  read-write
		STATUS  current
		DESCRIPTION
			"Set or Get the alarm severity level of the
			OMMP101 OTU Loss Of Frame Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 209 }

	ommp101OtuOutOfFrameAlarmSeverity OBJECT-TYPE		 
		SYNTAX  DisplayString
		MAX-ACCESS  read-write
		STATUS  current
		DESCRIPTION
			"Set or Get the alarm severity level of the
			OMMP101 OTU Out Of Frame Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 210 }

	ommp101OtuLossOfMultiFrameAlarmSeverity OBJECT-TYPE		 
		SYNTAX  DisplayString
		MAX-ACCESS  read-write
		STATUS  current
		DESCRIPTION
			"Set or Get the alarm severity level of the
			OMMP101 OTU Loss Of Multi Frame Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 211 }

	ommp101OtuOutOfMultiFrameAlarmSeverity OBJECT-TYPE		 
		SYNTAX  DisplayString
		MAX-ACCESS  read-write
		STATUS  current
		DESCRIPTION
			"Set or Get the alarm severity level of the
			OMMP101 OTU Out Of Multi Frame Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 212 }

	ommp101OtuSignalFailAlarmSeverity OBJECT-TYPE		 
		SYNTAX  DisplayString
		MAX-ACCESS  read-write
		STATUS  current
		DESCRIPTION
			"Set or Get the alarm severity level of the
			OMMP101 OTU Signal Fail Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 213 }

	ommp101OtuSignalDegradeAlarmSeverity OBJECT-TYPE		 
		SYNTAX  DisplayString
		MAX-ACCESS  read-write
		STATUS  current
		DESCRIPTION
			"Set or Get the alarm severity level of the
			OMMP101 OTU Signal Degrade Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 214 }

	ommp101OtuAlarmIndicationSignalAlarmSeverity OBJECT-TYPE		 
		SYNTAX  DisplayString
		MAX-ACCESS  read-write
		STATUS  current
		DESCRIPTION
			"Set or Get the alarm severity level of the
			OMMP101 OTU Alarm Indication Signal Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 215 }

	ommp101OtuIncomingAlignmentErrorAlarmSeverity OBJECT-TYPE		 
		SYNTAX  DisplayString
		MAX-ACCESS  read-write
		STATUS  current
		DESCRIPTION
			"Set or Get the alarm severity level of the
			OMMP101 OTU Incoming Alignment Error Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 216 }

	ommp101OtuBackwardIncomingAlignmentErrorAlarmSeverity OBJECT-TYPE		 
		SYNTAX  DisplayString
		MAX-ACCESS  read-write
		STATUS  current
		DESCRIPTION
			"Set or Get the alarm severity level of the
			OMMP101 OTU Backward Incoming Alignment Error Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 217 }

	ommp101OtuBackwardDefectIndicationAlarmSeverity OBJECT-TYPE		 
		SYNTAX  DisplayString
		MAX-ACCESS  read-write
		STATUS  current
		DESCRIPTION
			"Set or Get the alarm severity level of the
			OMMP101 OTU Backward Defect Indication Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 218 }

	ommp101OduSignalFailAlarmSeverity OBJECT-TYPE		 
		SYNTAX  DisplayString
		MAX-ACCESS  read-write
		STATUS  current
		DESCRIPTION
			"Set or Get the alarm severity level of the
			OMMP101 ODU Signal Fail Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 219 }

	ommp101OduSignalDegradeAlarmSeverity OBJECT-TYPE		 
		SYNTAX  DisplayString
		MAX-ACCESS  read-write
		STATUS  current
		DESCRIPTION
			"Set or Get the alarm severity level of the
			OMMP101 ODU Signal Degrade Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 220 }

	ommp101OduAlarmIndicationSignalAlarmSeverity OBJECT-TYPE		 
		SYNTAX  DisplayString
		MAX-ACCESS  read-write
		STATUS  current
		DESCRIPTION
			"Set or Get the alarm severity level of the
			OMMP101 ODU Alarm Indication Signal Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 221 }

	ommp101OduTcm1IncomingAlignmentErrorAlarmSeverity OBJECT-TYPE		 
		SYNTAX  DisplayString
		MAX-ACCESS  read-write
		STATUS  current
		DESCRIPTION
			"Set or Get the alarm severity level of the
			OMMP101 ODU TCM1 Incoming Alignment Error Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 222 }

	ommp101OduTcm2IncomingAlignmentErrorAlarmSeverity OBJECT-TYPE		 
		SYNTAX  DisplayString
		MAX-ACCESS  read-write
		STATUS  current
		DESCRIPTION
			"Set or Get the alarm severity level of the
			OMMP101 ODU TCM2 Incoming Alignment Error Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 223 }

	ommp101OduTcm3IncomingAlignmentErrorAlarmSeverity OBJECT-TYPE		 
		SYNTAX  DisplayString
		MAX-ACCESS  read-write
		STATUS  current
		DESCRIPTION
			"Set or Get the alarm severity level of the
			OMMP101 ODU TCM3 Incoming Alignment Error Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 224 }

	ommp101OduTcm4IncomingAlignmentErrorAlarmSeverity OBJECT-TYPE		 
		SYNTAX  DisplayString
		MAX-ACCESS  read-write
		STATUS  current
		DESCRIPTION
			"Set or Get the alarm severity level of the
			OMMP101 ODU TCM4 Incoming Alignment Error Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 225 }

	ommp101OduTcm5IncomingAlignmentErrorAlarmSeverity OBJECT-TYPE		 
		SYNTAX  DisplayString
		MAX-ACCESS  read-write
		STATUS  current
		DESCRIPTION
			"Set or Get the alarm severity level of the
			OMMP101 ODU TCM5 Incoming Alignment Error Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 226 }

	ommp101OduTcm6IncomingAlignmentErrorAlarmSeverity OBJECT-TYPE		 
		SYNTAX  DisplayString
		MAX-ACCESS  read-write
		STATUS  current
		DESCRIPTION
			"Set or Get the alarm severity level of the
			OMMP101 ODU TCM6 Incoming Alignment Error Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 227 }

	ommp101OduLockedDefectAlarmSeverity OBJECT-TYPE		 
		SYNTAX  DisplayString
		MAX-ACCESS  read-write
		STATUS  current
		DESCRIPTION
			"Set or Get the alarm severity level of the
			OMMP101 ODU Locked Defect Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 228 }

	ommp101OduOpenConnectionIndicationAlarmSeverity OBJECT-TYPE		 
		SYNTAX  DisplayString
		MAX-ACCESS  read-write
		STATUS  current
		DESCRIPTION
			"Set or Get the alarm severity level of the
			OMMP101 ODU Open Connection Indication Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 229 }

	ommp101OduBackwardDefectIndicationAlarmSeverity OBJECT-TYPE		 
		SYNTAX  DisplayString
		MAX-ACCESS  read-write
		STATUS  current
		DESCRIPTION
			"Set or Get the alarm severity level of the
			OMMP101 ODU Backward Defect Indication Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 230 }

	ommp101OduTcm1BackwardIncomingAlignmentErrorAlarmSeverity OBJECT-TYPE		 
		SYNTAX  DisplayString
		MAX-ACCESS  read-write
		STATUS  current
		DESCRIPTION
			"Set or Get the alarm severity level of the
			OMMP101 ODU TCM1 Backward Incoming Alignment Error
			Alarm for requested port
			-----------------------------
			ommp101InterfaceNumber:
			1 to 10 - CLIENT-1 to CLIENT-10
			11 - LINE PORT
			-----------------------------
			Value:
			critical
			major
			minor
			deferred
			---------------------------"
	::= { ommp101ConfigurationEntry 231 }

	ommp101OduTcm2BackwardIncomingAlignmentErrorAlarmSeverity OBJECT-TYPE		 
		SYNTAX  DisplayString
		MAX-ACCESS  read-write
		STATUS  current
		DESCRIPTION
			"Set or Get the alarm severity level of the
			OMMP101 ODU TCM2 Backward Incoming Alignment Error
			Alarm for requested port
			-----------------------------
			ommp101InterfaceNumber:
			1 to 10 - CLIENT-1 to CLIENT-10
			11 - LINE PORT
			-----------------------------
			Value:
			critical
			major
			minor
			deferred
			---------------------------"
	::= { ommp101ConfigurationEntry 232 }

	ommp101OduTcm3BackwardIncomingAlignmentErrorAlarmSeverity OBJECT-TYPE		 
		SYNTAX  DisplayString
		MAX-ACCESS  read-write
		STATUS  current
		DESCRIPTION
			"Set or Get the alarm severity level of the
			OMMP101 ODU TCM3 Backward Incoming Alignment Error
			Alarm for requested port
			-----------------------------
			ommp101InterfaceNumber:
			1 to 10 - CLIENT-1 to CLIENT-10
			11 - LINE PORT
			-----------------------------
			Value:
			critical
			major
			minor
			deferred
			---------------------------"
	::= { ommp101ConfigurationEntry 233 }

	ommp101OduTcm4BackwardIncomingAlignmentErrorAlarmSeverity OBJECT-TYPE		 
		SYNTAX  DisplayString
		MAX-ACCESS  read-write
		STATUS  current
		DESCRIPTION
			"Set or Get the alarm severity level of the
			OMMP101 ODU TCM4 Backward Incoming Alignment Error
			Alarm for requested port
			-----------------------------
			ommp101InterfaceNumber:
			1 to 10 - CLIENT-1 to CLIENT-10
			11 - LINE PORT
			-----------------------------
			Value:
			critical
			major
			minor
			deferred
			---------------------------"
	::= { ommp101ConfigurationEntry 234 }

	ommp101OduTcm5BackwardIncomingAlignmentErrorAlarmSeverity OBJECT-TYPE		 
		SYNTAX  DisplayString
		MAX-ACCESS  read-write
		STATUS  current
		DESCRIPTION
			"Set or Get the alarm severity level of the
			OMMP101 ODU TCM5 Backward Incoming Alignment Error
			Alarm for requested port
			-----------------------------
			ommp101InterfaceNumber:
			1 to 10 - CLIENT-1 to CLIENT-10
			11 - LINE PORT
			-----------------------------
			Value:
			critical
			major
			minor
			deferred
			---------------------------"
	::= { ommp101ConfigurationEntry 235 }

	ommp101OduTcm6BackwardIncomingAlignmentErrorAlarmSeverity OBJECT-TYPE		 
		SYNTAX  DisplayString
		MAX-ACCESS  read-write
		STATUS  current
		DESCRIPTION
			"Set or Get the alarm severity level of the
			OMMP101 ODU TCM6 Backward Incoming Alignment Error
			Alarm for requested port
			-----------------------------
			ommp101InterfaceNumber:
			1 to 10 - CLIENT-1 to CLIENT-10
			11 - LINE PORT
			-----------------------------
			Value:
			critical
			major
			minor
			deferred
			---------------------------"
	::= { ommp101ConfigurationEntry 236 }

	ommp101OduLossOfFrameLossOfMultiframeAlarmSeverity OBJECT-TYPE		 
		SYNTAX  DisplayString
		MAX-ACCESS  read-write
		STATUS  current
		DESCRIPTION
			"Set or Get the alarm severity level of the
			OMMP101 ODU Loss Of Frame Loss Of Multiframe Alarm   
			for requested port
			-----------------------------
			ommp101InterfaceNumber:
			1, 2, 3, 4 - Slice number
			-----------------------------
			Value:
			critical
			major
			minor
			deferred
			---------------------------"
	::= { ommp101ConfigurationEntry 237 }

	ommp101OpuPayloadMismatchAlarmSeverity OBJECT-TYPE		 
		SYNTAX  DisplayString
		MAX-ACCESS  read-write
		STATUS  current
		DESCRIPTION
			"Set or Get the alarm severity level of the
			OMMP101 OPU Payload Mismatch Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 238 }

	ommp101SdhLossOfSignalAlarmSeverity OBJECT-TYPE		 
		SYNTAX  DisplayString
		MAX-ACCESS  read-write
		STATUS  current
		DESCRIPTION
			"Set or Get the alarm severity level of the
			OMMP101 SDH Loss Of Signal Alarm   
			for requested port
			-----------------------------
			ommp101InterfaceNumber:
			1 to 10 - CLIENT-1 to CLIENT-10
			-----------------------------
			Value:
			critical
			major
			minor
			deferred
			---------------------------"
	::= { ommp101ConfigurationEntry 239 }

	ommp101SdhOutOfFrameAlarmSeverity OBJECT-TYPE		 
		SYNTAX  DisplayString
		MAX-ACCESS  read-write
		STATUS  current
		DESCRIPTION
			"Set or Get the alarm severity level of the
			OMMP101 SDH Out Of Frame Alarm   
			for requested port
			-----------------------------
			ommp101InterfaceNumber:
			1 to 10 - CLIENT-1 to CLIENT-10,
			-----------------------------
			Value:
			critical
			major
			minor
			deferred
			---------------------------"
	::= { ommp101ConfigurationEntry 240 }

	ommp101SdhLossOfFrameAlarmSeverity OBJECT-TYPE		 
		SYNTAX  DisplayString
		MAX-ACCESS  read-write
		STATUS  current
		DESCRIPTION
			"Set or Get the alarm severity level of the
			OMMP101 SDH Loss Of Frame Alarm   
			for requested port
			-----------------------------
			ommp101InterfaceNumber:
			1 to 10 - CLIENT-1 to CLIENT-10
			-----------------------------
			Value:
			critical
			major
			minor
			deferred
			---------------------------"
	::= { ommp101ConfigurationEntry 241 }

	ommp101SdhRsTraceIdentifierMismatchAlarmSeverity OBJECT-TYPE		 
		SYNTAX  DisplayString
		MAX-ACCESS  read-write
		STATUS  current
		DESCRIPTION
			"Set or Get the alarm severity level of the
			OMMP101 SDH Rs Trace Identifier Mismatch Alarm   
			for requested port
			-----------------------------
			ommp101InterfaceNumber:
			1 to 10 - CLIENT-1 to CLIENT-10
			-----------------------------
			Value:
			critical
			major
			minor
			deferred
			---------------------------"
	::= { ommp101ConfigurationEntry 242 }

	ommp101SdhMsAlarmIndicationSignalAlarmSeverity OBJECT-TYPE		 
		SYNTAX  DisplayString
		MAX-ACCESS  read-write
		STATUS  current
		DESCRIPTION
			"Set or Get the alarm severity level of the
			OMMP101 SDH Ms Alarm Indication Signal Alarm   
			for requested port
			-----------------------------
			ommp101InterfaceNumber:
			1 to 10 - CLIENT-1 to CLIENT-10
			-----------------------------
			Value:
			critical
			major
			minor
			deferred
			---------------------------"
	::= { ommp101ConfigurationEntry 243 }

	ommp101SdhMsRemoteDefectIndicationAlarmSeverity OBJECT-TYPE		 
		SYNTAX  DisplayString
		MAX-ACCESS  read-write
		STATUS  current
		DESCRIPTION
			"Set or Get the alarm severity level of the
			OMMP101 SDH Ms Remote Defect Indication Alarm   
			for requested port
			-----------------------------
			ommp101InterfaceNumber:
			1 to 10 - CLIENT-1 to CLIENT-10
			-----------------------------
			Value:
			critical
			major
			minor
			deferred
			---------------------------"
	::= { ommp101ConfigurationEntry 244 }

	ommp101EthernetLossOfSignalAlarmSeverity OBJECT-TYPE		 
		SYNTAX  DisplayString
		MAX-ACCESS  read-write
		STATUS  current
		DESCRIPTION
			"Set or Get the alarm severity level of the
			OMMP101 Ethernet Loss Of Signal Alarm   
			for requested port
			-----------------------------
			ommp101InterfaceNumber:
			1 to 10 - CLIENT-1 to CLIENT-10
			-----------------------------
			Value:
			critical
			major
			minor
			deferred
			---------------------------"
	::= { ommp101ConfigurationEntry 245 }

	ommp101EthernetLinkFailureAlarmSeverity OBJECT-TYPE		 
		SYNTAX  DisplayString
		MAX-ACCESS  read-write
		STATUS  current
		DESCRIPTION
			"Set or Get the alarm severity level of the
			OMMP101 Ethernet Link Failure Alarm   
			for requested port
			-----------------------------
			ommp101InterfaceNumber:
			1 to 10 - CLIENT-1 to CLIENT-10
			-----------------------------
			Value:
			critical
			major
			minor
			deferred
			---------------------------"
	::= { ommp101ConfigurationEntry 246 }

	ommp101EthernetHighBerAlarmSeverity OBJECT-TYPE		 
		SYNTAX  DisplayString
		MAX-ACCESS  read-write
		STATUS  current
		DESCRIPTION
			"Set or Get the alarm severity level of the
			OMMP101 Ethernet High Ber Alarm   
			for requested port
			-----------------------------
			ommp101InterfaceNumber:
			1 to 10 - CLIENT-1 to CLIENT-10
			-----------------------------
			Value:
			critical
			major
			minor
			deferred
			---------------------------"
	::= { ommp101ConfigurationEntry 247 }

	ommp101EthernetLocalFaultAlarmSeverity OBJECT-TYPE		 
		SYNTAX  DisplayString
		MAX-ACCESS  read-write
		STATUS  current
		DESCRIPTION
			"Set or Get the alarm severity level of the
			OMMP101 Ethernet Local Fault Alarm   
			for requested port
			-----------------------------
			ommp101InterfaceNumber:
			1 to 10 - CLIENT-1 to CLIENT-10
			-----------------------------
			Value:
			critical
			major
			minor
			deferred
			---------------------------"
	::= { ommp101ConfigurationEntry 248 }

	ommp101EthernetRemoteFaultAlarmSeverity OBJECT-TYPE		 
		SYNTAX  DisplayString
		MAX-ACCESS  read-write
		STATUS  current
		DESCRIPTION
			"Set or Get the alarm severity level of the
			OMMP101 Ethernet Remote Fault Alarm   
			for requested port
			-----------------------------
			ommp101InterfaceNumber:
			1 to 10 - CLIENT-1 to CLIENT-10
			-----------------------------
			Value:
			critical
			major
			minor
			deferred
			---------------------------"
	::= { ommp101ConfigurationEntry 249 }

	ommp101TunableCfp2WavelengthGridSpacing OBJECT-TYPE		 
		SYNTAX  INTEGER
		MAX-ACCESS  read-write
		STATUS current
		DESCRIPTION
			"This property gives difference in the wavelength
			between two channels In GHz.
			-----------------------------
			ommp101InterfaceNumber:
			11 - LINE PORT
			-----------------------------
			Values:
			eg: 50
			-----------------------------"
		::= { ommp101ConfigurationEntry 250 }	

	ommp101OduLockedDefectAlarmInsertion OBJECT-TYPE		 
		SYNTAX  INTEGER
		MAX-ACCESS read-write
		STATUS current
		DESCRIPTION
			"Inserts ODU-LCK maintenance signal for the requested 
			port configured with OTU2/OTU4 traffic.
			-----------------------------
			ommp101InterfaceNumber:
			1 to 10 - CLIENT-1 to CLIENT-10
			11 - LINE PORT
			-----------------------------
			Values: 
			1 - Enable Insertion
			0 - Disable Insertion  
			-----------------------------"
		::= { ommp101ConfigurationEntry 251 }

	ommp101OduOpenConnectionIndicationAlarmInsertion OBJECT-TYPE		 
		SYNTAX  INTEGER
		MAX-ACCESS read-write
		STATUS current
		DESCRIPTION
			"Inserts ODU-OCI maintenance signal for the requested 
			port configured with OTU2/OTU4 traffic.
			-----------------------------
			ommp101InterfaceNumber:
			1 to 10 - CLIENT-1 to CLIENT-10
			11 - LINE PORT
			-----------------------------
			Values: 
			1 - Enable Insertion
			0 - Disable Insertion  
			-----------------------------"
		::= { ommp101ConfigurationEntry 252 }

	ommp101OtuTraceIdentifierMismatchAlarmInhibit  OBJECT-TYPE
		SYNTAX  INTEGER
		MAX-ACCESS  read-write
		STATUS  current
		DESCRIPTION
			"Inhibits OMMP101 OTU Trace Identifier Mismatch Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 253 }

	ommp101OduTraceIdentifierMismatchAlarmInhibit  OBJECT-TYPE
		SYNTAX  INTEGER
		MAX-ACCESS  read-write
		STATUS  current
		DESCRIPTION
			"Inhibits OMMP101 OTU Trace Identifier Mismatch Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 254 }

	ommp101OtuTraceIdentifierMismatchAlarmSeverity OBJECT-TYPE
		SYNTAX  DisplayString
		MAX-ACCESS  read-write
		STATUS  current
		DESCRIPTION
			"Set or Get the alarm severity level of the
			OMMP101 OTU Trace Identifier Mismatch Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 255 }

	ommp101OduTraceIdentifierMismatchAlarmSeverity OBJECT-TYPE
		SYNTAX  DisplayString
		MAX-ACCESS  read-write
		STATUS  current
		DESCRIPTION
			"Set or Get the alarm severity level of the
			OMMP101 ODU Trace Identifier Mismatch Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 256 }

	ommp101EthernetLossOfAlignmentAlarmInhibit  OBJECT-TYPE
		SYNTAX  INTEGER
		MAX-ACCESS  read-write
		STATUS  current
		DESCRIPTION
			"Inhibits OMMP101 Ethernet Loss Of Alignment Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 257 }

	ommp101EthernetLossOfBlockLockAlarmInhibit  OBJECT-TYPE
		SYNTAX  INTEGER
		MAX-ACCESS  read-write
		STATUS  current
		DESCRIPTION
			"Inhibits OMMP101 Ethernet Loss Of Block Lock Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 258 }

	ommp101EthernetNotAlignedInPcsAlarmInhibit  OBJECT-TYPE
		SYNTAX  INTEGER
		MAX-ACCESS  read-write
		STATUS  current
		DESCRIPTION
			"Inhibits OMMP101 Ethernet Not Aligned In Pcs Alarm
			for the requested port
			-----------------------------
			ommp101InterfaceNumber:
			1 to 10 - CLIENT-1 to CLIENT-10
			11 - LINE PORT
			-----------------------------
			Value:
			1 - Inhibit
			0 - Do Not Inhibit
			-----------------------------"
	::= { ommp101ConfigurationEntry 259 }

	ommp101EthernetLossOfAlignmentAlarmSeverity OBJECT-TYPE
		SYNTAX  DisplayString
		MAX-ACCESS  read-write
		STATUS  current
		DESCRIPTION
			"Set or Get the alarm severity level of the
			OMMP101 Ethernet Loss Of Alignment Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 260 }
	
	ommp101EthernetLossOfBlockLockAlarmSeverity OBJECT-TYPE
		SYNTAX  DisplayString
		MAX-ACCESS  read-write
		STATUS  current
		DESCRIPTION
			"Set or Get the alarm severity level of the
			OMMP101 Ethernet Loss Of Block Lock Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 261 }

	ommp101EthernetNotAlignedInPcsAlarmSeverity OBJECT-TYPE
		SYNTAX  DisplayString
		MAX-ACCESS  read-write
		STATUS  current
		DESCRIPTION
			"Set or Get the alarm severity level of the
			OMMP101 Ethernet Not Aligned In Pcs Alarm   
			for requested port
			-----------------------------
			ommp101InterfaceNumber:
			1 to 10 - CLIENT-1 to CLIENT-10
			11 - LINE PORT
			-----------------------------
			Value:
			critical
			major
			minor
			deferred
			---------------------------"
	::= { ommp101ConfigurationEntry 262 }

	ommp101ConfigurationTableRowStatus OBJECT-TYPE
              SYNTAX      RowStatus
              MAX-ACCESS  read-write
              STATUS      current
              DESCRIPTION
			"*****************************
			This is MIB realted property,
			NOT to be considered as a card property
			*****************************"
              ::= { ommp101ConfigurationEntry 263 }	


--*****************************************************************************
--				    ALARMS
--*****************************************************************************
                 
	ommp101AlarmQueryTable OBJECT-TYPE
	      SYNTAX  SEQUENCE OF Ommp101AlarmQueryEntry 
              MAX-ACCESS  not-accessible
              STATUS  current
              DESCRIPTION
                      "Gives Optical and Signal Alarms status of the OMMP101 card"
		::= { ommp101AlarmQuery 1 }	

	ommp101AlarmQueryEntry   OBJECT-TYPE
              SYNTAX  Ommp101AlarmQueryEntry 
              MAX-ACCESS  not-accessible
              STATUS  current
              DESCRIPTION 
              	""
		INDEX   { node, rack , subRack , slot , ommp101InterfaceNumber }
		::= { ommp101AlarmQueryTable 1 }
	
	Ommp101AlarmQueryEntry ::= 
			SEQUENCE {					
					ommp101Cfp2InputPowerFailureAlarm					DisplayString,
					ommp101Cfp2OutputPowerFailureAlarm					DisplayString,
					ommp101Cfp2HighTemperatureAlarm					DisplayString,
					ommp101Cfp2LowTemperatureAlarm					DisplayString,
					ommp101Cfp2HighTemperatureWarning					DisplayString,
					ommp101Cfp2LowTemperatureWarning					DisplayString,
					ommp101Cfp2InputHighPowerAlarm					DisplayString,
					ommp101Cfp2InputLowPowerAlarm						DisplayString,
					ommp101Cfp2InputHighPowerWarning					DisplayString,
					ommp101Cfp2InputLowPowerWarning					DisplayString,
					ommp101Cfp2OutputHighPowerAlarm					DisplayString,
					ommp101Cfp2OutputLowPowerAlarm					DisplayString,
					ommp101Cfp2OutputHighPowerWarning					DisplayString,
					ommp101Cfp2OutputLowPowerWarning					DisplayString,
					ommp101Cfp2HighSupplyVoltageAlarm					DisplayString,
					ommp101Cfp2LowSupplyVoltageAlarm					DisplayString,
					ommp101Cfp2HighSupplyVoltageWarning					DisplayString,
					ommp101Cfp2LowSupplyVoltageWarning					DisplayString,
					ommp101Cfp2PresenceAbsenceNotification				DisplayString,
					ommp101SfpPlusInputPowerFailureAlarm					DisplayString,
					ommp101SfpPlusOutputPowerFailureAlarm					DisplayString,
					ommp101SfpPlusHighTemperatureAlarm					DisplayString,
					ommp101SfpPlusLowTemperatureAlarm					DisplayString,
					ommp101SfpPlusHighTemperatureWarning					DisplayString,
					ommp101SfpPlusLowTemperatureWarning					DisplayString,
					ommp101SfpPlusHighBiasCurrentAlarm					DisplayString,
					ommp101SfpPlusLowBiasCurrentAlarm					DisplayString,
					ommp101SfpPlusHighBiasCurrentWarning					DisplayString,
					ommp101SfpPlusLowBiasCurrentWarning					DisplayString,
					ommp101SfpPlusInputHighPowerAlarm					DisplayString,
					ommp101SfpPlusInputLowPowerAlarm						DisplayString,
					ommp101SfpPlusInputHighPowerWarning					DisplayString,
					ommp101SfpPlusInputLowPowerWarning					DisplayString,
					ommp101SfpPlusOutputHighPowerAlarm					DisplayString,
					ommp101SfpPlusOutputLowPowerAlarm					DisplayString,
					ommp101SfpPlusOutputHighPowerWarning					DisplayString,
					ommp101SfpPlusOutputLowPowerWarning					DisplayString,
					ommp101SfpPlusHighSupplyVoltageAlarm					DisplayString,
					ommp101SfpPlusLowSupplyVoltageAlarm					DisplayString,
					ommp101SfpPlusHighSupplyVoltageWarning					DisplayString,
					ommp101SfpPlusLowSupplyVoltageWarning					DisplayString,
					ommp101SfpPlusPresenceAbsenceNotification				DisplayString,
					ommp101SfpPlusTransmitFaultPresenceAlarm					DisplayString,
					ommp101OtuLossOfSignalAlarm						DisplayString,
					ommp101OtuLossOfFrameAlarm						DisplayString,
					ommp101OtuOutOfFrameAlarm						DisplayString,
					ommp101OtuLossOfMultiFrameAlarm					DisplayString,
					ommp101OtuOutOfMultiFrameAlarm					DisplayString,
					ommp101OtuSignalFailAlarm						DisplayString,
					ommp101OtuSignalDegradeAlarm						DisplayString,
					ommp101OtuAlarmIndicationSignalAlarm					DisplayString,
					ommp101OtuIncomingAlignmentErrorAlarm				DisplayString,
					ommp101OtuBackwardIncomingAlignmentErrorAlarm			DisplayString,
					ommp101OtuBackwardDefectIndicationAlarm				DisplayString,
					ommp101OduSignalFailAlarm						DisplayString,
					ommp101OduSignalDegradeAlarm						DisplayString,
					ommp101OduAlarmIndicationSignalAlarm					DisplayString,
					ommp101OduTcm1IncomingAlignmentErrorAlarm				DisplayString,
					ommp101OduTcm2IncomingAlignmentErrorAlarm				DisplayString,
					ommp101OduTcm3IncomingAlignmentErrorAlarm				DisplayString,
					ommp101OduTcm4IncomingAlignmentErrorAlarm				DisplayString,
					ommp101OduTcm5IncomingAlignmentErrorAlarm				DisplayString,
					ommp101OduTcm6IncomingAlignmentErrorAlarm				DisplayString,
					ommp101OduLockedDefectAlarm						DisplayString,
					ommp101OduOpenConnectionIndicationAlarm				DisplayString,
					ommp101OduBackwardDefectIndicationAlarm				DisplayString,
					ommp101OduTcm1BackwardIncomingAlignmentErrorAlarm			DisplayString,
					ommp101OduTcm2BackwardIncomingAlignmentErrorAlarm			DisplayString,
					ommp101OduTcm3BackwardIncomingAlignmentErrorAlarm			DisplayString,
					ommp101OduTcm4BackwardIncomingAlignmentErrorAlarm			DisplayString,
					ommp101OduTcm5BackwardIncomingAlignmentErrorAlarm			DisplayString,
					ommp101OduTcm6BackwardIncomingAlignmentErrorAlarm			DisplayString,
					ommp101OduLossOfFrameLossOfMultiframeAlarm				DisplayString,
					ommp101OpuPayloadMismatchAlarm					DisplayString,
					ommp101SdhLossOfSignalAlarm						DisplayString,
					ommp101SdhOutOfFrameAlarm						DisplayString,
					ommp101SdhLossOfFrameAlarm						DisplayString,
					ommp101SdhMsAlarmIndicationSignalAlarm				DisplayString,
					ommp101SdhMsRemoteDefectIndicationAlarm				DisplayString,
					ommp101SdhMsB2ExcessiveErrorAlarm					DisplayString,
					ommp101SdhMsB2SignalDegradeAlarm					DisplayString,
					ommp101EthernetLossOfSignalAlarm					DisplayString,
					ommp101EthernetLinkFailureAlarm					DisplayString,
					ommp101EthernetHighBerAlarm						DisplayString,
					ommp101EthernetLocalFaultAlarm					DisplayString,
					ommp101EthernetRemoteFaultAlarm					DisplayString,
					ommp101OtuTraceIdentifierMismatchAlarm				DisplayString,
					ommp101OduTraceIdentifierMismatchAlarm				DisplayString,
					ommp101EthernetLossOfAlignmentAlarm				DisplayString,
					ommp101EthernetLossOfBlockLockAlarm				DisplayString,
					ommp101EthernetNotAlignedInPcsAlarm				DisplayString,
					ommp101AlarmQueryTableRowStatus					RowStatus
		}

--*****************************************************************************
--				OPTICAL	ALARMS
--***************************************************************************** 

	ommp101Cfp2InputPowerFailureAlarm OBJECT-TYPE
              SYNTAX  DisplayString
              MAX-ACCESS  read-only
              STATUS  current
              DESCRIPTION
			"If optical input power at requested interface is less than
			-20dbm, this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 1 }

	ommp101Cfp2OutputPowerFailureAlarm OBJECT-TYPE
              SYNTAX  DisplayString
              MAX-ACCESS  read-only
              STATUS  current
              DESCRIPTION
			"If optical output power at requested interface is less than
			-10dbm, this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 2 }

	ommp101Cfp2HighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 3 }

	ommp101Cfp2LowTemperatureAlarm OBJECT-TYPE
              SYNTAX  DisplayString
              MAX-ACCESS  read-only
              STATUS  current
              DESCRIPTION
			"If optical temperature at requested interface is lower 
			than the Low Temperature Alarm Threshold, alarm will be 
			generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 4 }

	ommp101Cfp2HighTemperatureWarning OBJECT-TYPE
              SYNTAX  DisplayString
              MAX-ACCESS  read-only
              STATUS  current
              DESCRIPTION
			"If optical temperature at requested interface is greater
			than the High Temperature Warning Threshold, this alarm 
			will be generated.
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 5 }

	ommp101Cfp2LowTemperatureWarning OBJECT-TYPE
              SYNTAX  DisplayString
              MAX-ACCESS  read-only
              STATUS  current
              DESCRIPTION
			"If optical temperature at requested interface is lesser
			than the Low Temperature Warning Threshold, this alarm 
			will be generated.
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 6 }

	ommp101Cfp2InputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 7 }

	ommp101Cfp2InputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 8 }

	ommp101Cfp2InputHighPowerWarning OBJECT-TYPE
              SYNTAX  DisplayString
              MAX-ACCESS  read-only
              STATUS  current
              DESCRIPTION
			"If optical Input power at requested interface is 
			greater than the High Input Power Warning Threshold, 
			this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 9 }

	ommp101Cfp2InputLowPowerWarning OBJECT-TYPE
              SYNTAX  DisplayString
              MAX-ACCESS  read-only
              STATUS  current
              DESCRIPTION
			"If optical Input power at requested interface is lesser
			than the Low Input Power Warning Threshold, this alarm 
			will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 10 }

	ommp101Cfp2OutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 11 }

	ommp101Cfp2OutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 12 }

	ommp101Cfp2OutputHighPowerWarning OBJECT-TYPE
              SYNTAX  DisplayString
              MAX-ACCESS  read-only
              STATUS  current
              DESCRIPTION
			"If optical Output power at requested interface is 
			greater than the High Output Power Warning Threshold, 
			this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 13 }

	ommp101Cfp2OutputLowPowerWarning OBJECT-TYPE
              SYNTAX  DisplayString
              MAX-ACCESS  read-only
              STATUS  current
              DESCRIPTION
			"If optical Output power at requested interface is 
			lesser than the Low Output Power Warning Threshold, 
			this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 14 }

	ommp101Cfp2HighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 15 }

	ommp101Cfp2LowSupplyVoltageAlarm OBJECT-TYPE
              SYNTAX  DisplayString
              MAX-ACCESS  read-only
              STATUS  current
              DESCRIPTION
			"If optical Supply Voltage at requested interface is 
			lesser than the Low Supply Voltage Alarm Threshold, 
			this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 16 }

	ommp101Cfp2HighSupplyVoltageWarning OBJECT-TYPE
              SYNTAX  DisplayString
              MAX-ACCESS  read-only
              STATUS  current
              DESCRIPTION
			"If optical Supply Voltage at requested interface is 
			higher than the High Supply Voltage Warning Threshold,
			this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 17 }

	ommp101Cfp2LowSupplyVoltageWarning OBJECT-TYPE
              SYNTAX  DisplayString
              MAX-ACCESS  read-only
              STATUS  current
              DESCRIPTION
			"If optical Supply Voltage at requested interface is 
			lesser than the Low Supply Voltage Warning Threshold, 
			this alarm will be generated
			-----------------------------
			ommp101InterfaceNumber:
			11 - LINE PORT
			-----------------------------
			Values :
			If Alarm is Present - Date and Time Stamp
				    eg:2017-5-18,9:47:20.0,+5:30
			If Alarm is Absent  - 0
			-----------------------------"
		::= { ommp101AlarmQueryEntry 18 }

	ommp101Cfp2PresenceAbsenceNotification OBJECT-TYPE
              SYNTAX  DisplayString
              MAX-ACCESS  read-only
              STATUS  current
              DESCRIPTION
			"Whenever the CFP2 is jacked in or jacked out, this 
			notification is generated.
			-----------------------------
			ommp101InterfaceNumber:
			11 - LINE PORT
			-----------------------------
			Values :
			If Alarm is Present(module absent) - Date and Time Stamp
				    eg:2017-5-18,9:47:20.0,+5:30
			If Alarm is Absent(module present) - 0
			-----------------------------"
		::= { ommp101AlarmQueryEntry 19 }

	ommp101SfpPlusInputPowerFailureAlarm OBJECT-TYPE
              SYNTAX  DisplayString
              MAX-ACCESS  read-only
              STATUS  current
              DESCRIPTION
			"If optical input power at requested interface is less than
			-20dbm, this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 20 }

	ommp101SfpPlusOutputPowerFailureAlarm OBJECT-TYPE
              SYNTAX  DisplayString
              MAX-ACCESS  read-only
              STATUS  current
              DESCRIPTION
			"If optical output power at requested interface is less than
			-10dbm, this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 21 }

	ommp101SfpPlusHighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 22 }

	ommp101SfpPlusLowTemperatureAlarm OBJECT-TYPE
              SYNTAX  DisplayString
              MAX-ACCESS  read-only
              STATUS  current
              DESCRIPTION
			"If optical temperature at requested interface is lesser 
			than the Low Temperature Alarm Threshold, alarm will be 
			generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 23 }

	ommp101SfpPlusHighTemperatureWarning OBJECT-TYPE
              SYNTAX  DisplayString
              MAX-ACCESS  read-only
              STATUS  current
              DESCRIPTION
			"If optical temperature at requested interface is greater
			than the High Temperature Warning Threshold, this alarm 
			will be generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 24 }

	ommp101SfpPlusLowTemperatureWarning OBJECT-TYPE
              SYNTAX  DisplayString
              MAX-ACCESS  read-only
              STATUS  current
              DESCRIPTION
			"If optical temperature at requested interface is lesser
			than the Low Temperature Warning Threshold, this alarm 
			will be generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 25 }

	ommp101SfpPlusHighBiasCurrentAlarm OBJECT-TYPE
              SYNTAX  DisplayString
              MAX-ACCESS  read-only
              STATUS  current
              DESCRIPTION
			"If optical transmit bias current at requested interface
			is greater than the High Bias Current Alarm Threshold, 
			this alarm will be generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 26 }

	ommp101SfpPlusLowBiasCurrentAlarm OBJECT-TYPE
              SYNTAX  DisplayString
              MAX-ACCESS  read-only
              STATUS  current
              DESCRIPTION
			"If optical transmit bias current at requested interface
			is lesser than the Low Bias Current Alarm Threshold, 
			this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 27 }

	ommp101SfpPlusHighBiasCurrentWarning OBJECT-TYPE
              SYNTAX  DisplayString
              MAX-ACCESS  read-only
              STATUS  current
              DESCRIPTION
			"If optical transmit bias current at requested interface
			is greater than the High Bias Current Warning Threshold,
			this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 28 }

	ommp101SfpPlusLowBiasCurrentWarning OBJECT-TYPE
              SYNTAX  DisplayString
              MAX-ACCESS  read-only
              STATUS  current
              DESCRIPTION
			"If optical transmit bias current at requested interface
			is lesser than the Low Bias Current Warning Threshold, 
			this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 29}

	ommp101SfpPlusInputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 30 }

	ommp101SfpPlusInputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 31 }

	ommp101SfpPlusInputHighPowerWarning OBJECT-TYPE
              SYNTAX  DisplayString
              MAX-ACCESS  read-only
              STATUS  current
              DESCRIPTION
			"If optical Input power at requested interface is 
			greater than the High Input Power Warning Threshold, 
			this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 32 }

	ommp101SfpPlusInputLowPowerWarning OBJECT-TYPE
              SYNTAX  DisplayString
              MAX-ACCESS  read-only
              STATUS  current
              DESCRIPTION
			"If optical Input power at requested interface is lesser
			than the Low Input Power Warning Threshold, this alarm 
			will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 33 }

	ommp101SfpPlusOutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 34 }

	ommp101SfpPlusOutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 35 }

	ommp101SfpPlusOutputHighPowerWarning OBJECT-TYPE
              SYNTAX  DisplayString
              MAX-ACCESS  read-only
              STATUS  current
              DESCRIPTION
			"If optical Output power at requested interface is 
			greater than the High Output Power Warning Threshold, 
			this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 36 }

	ommp101SfpPlusOutputLowPowerWarning OBJECT-TYPE
              SYNTAX  DisplayString
              MAX-ACCESS  read-only
              STATUS  current
              DESCRIPTION
			"If optical Output power at requested interface is 
			lesser than the Low Output Power Warning Threshold, this
			alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 37 }

	ommp101SfpPlusHighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 38 }

	ommp101SfpPlusLowSupplyVoltageAlarm OBJECT-TYPE
              SYNTAX  DisplayString
              MAX-ACCESS  read-only
              STATUS  current
              DESCRIPTION
			"If optical Supply Voltage at requested interface is 
			lesser than the Low Supply Voltage Alarm Threshold, this
			alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 39 }

	ommp101SfpPlusHighSupplyVoltageWarning OBJECT-TYPE
              SYNTAX  DisplayString
              MAX-ACCESS  read-only
              STATUS  current
              DESCRIPTION
			"If optical Supply Voltage at requested interface is 
			greater than the High Supply Voltage Warning Threshold, 
			this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 40 }

	ommp101SfpPlusLowSupplyVoltageWarning OBJECT-TYPE
              SYNTAX  DisplayString
              MAX-ACCESS  read-only
              STATUS  current
              DESCRIPTION
			"If optical Supply Voltage at requested interface is 
			lesser than the Low Supply Voltage Warning Threshold, 
			this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 41 }

	ommp101SfpPlusPresenceAbsenceNotification OBJECT-TYPE
              SYNTAX  DisplayString
              MAX-ACCESS  read-only
              STATUS  current
              DESCRIPTION
			"Whenever the SFP PLUS is jacked in or jacked out, this 
			notification is generated.
			-----------------------------
			ommp101InterfaceNumber:
			1 to 10 - CLIENT-1 to CLIENT-10
			-----------------------------
			Values :
			If Alarm is Present(module absent) - Date and Time Stamp
				    eg:2017-5-18,9:47:20.0,+5:30
			If Alarm is Absent(module present) - 0
			-----------------------------"
		::= { ommp101AlarmQueryEntry 42 }

	ommp101SfpPlusTransmitFaultPresenceAlarm OBJECT-TYPE
              SYNTAX  DisplayString
              MAX-ACCESS  read-only
              STATUS  current
              DESCRIPTION
			"Whenever the SFP PLUS laser is unable to generate
			any data this alarm will be generated
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 43 }

	ommp101OtuLossOfSignalAlarm OBJECT-TYPE
              SYNTAX  DisplayString
              MAX-ACCESS  read-only
              STATUS  current
              DESCRIPTION
			"For port configured with OTU2 traffic,
			if there is no signal received then OTU-LOS Alarm
			is generated.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 44 }

	ommp101OtuLossOfFrameAlarm OBJECT-TYPE
              SYNTAX  DisplayString
              MAX-ACCESS  read-only
              STATUS  current
              DESCRIPTION
			"For port configured with OTU2 traffic, if
			OTU2/OTU4 frame received are in out-of-frame (OOF)
			state for 3 ms, then OTU-LOF Alarm is generated
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 45 }

	ommp101OtuOutOfFrameAlarm OBJECT-TYPE
              SYNTAX  DisplayString
              MAX-ACCESS  read-only
              STATUS  current
              DESCRIPTION
			"For port configured with OTU2 traffic, if 5
			consecutive OTU2 frames are received with
			invalid framing patterns then OOF Alarm is
			generated
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 46 }

	ommp101OtuLossOfMultiFrameAlarm OBJECT-TYPE
              SYNTAX  DisplayString
              MAX-ACCESS  read-only
              STATUS  current
              DESCRIPTION
			"For port configured with OTU2 traffic, if 
			OTU2/OTU4 frame received are in Out-of-multiframe
			(OOM) state for 3 ms then LOM Alarm is generated.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 47 }

	ommp101OtuOutOfMultiFrameAlarm OBJECT-TYPE
              SYNTAX  DisplayString
              MAX-ACCESS  read-only
              STATUS  current
              DESCRIPTION
			"For port configured with OTU2 traffic, if the
			received MFAS does not match with the expected multi
			frame number for five consecutive frames then
			OOM Alarm is generated.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 48 }

	ommp101OtuSignalFailAlarm OBJECT-TYPE
              SYNTAX  DisplayString
              MAX-ACCESS  read-only
              STATUS  current
              DESCRIPTION
			"For port configured with OTU2 traffic, 
			OTU SF alarm is generated when BIP errors evaluated by 
			SM field of OTU2 frame exceeds the 
			'ommp101OtuSignalFailThreshold' threshold
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 49 }

	ommp101OtuSignalDegradeAlarm OBJECT-TYPE
              SYNTAX  DisplayString
              MAX-ACCESS  read-only
              STATUS  current
              DESCRIPTION
			"For port configured with OTU2 traffic, 
			OTU SD alarm is generated when BIP errors evaluated by 
			SM field of OTU2 frame exceeds the 
			'ommp101OtuSignalDegradeThreshold' threshold.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 50 }

	ommp101OtuAlarmIndicationSignalAlarm OBJECT-TYPE
              SYNTAX  DisplayString
              MAX-ACCESS  read-only
              STATUS  current
              DESCRIPTION
			"For port configured with OTU2 traffic,
			OTU-AIS is generated and transmitted in forward 
			direction, when LOS has been detected at far-end port.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 51 }

	ommp101OtuIncomingAlignmentErrorAlarm OBJECT-TYPE
              SYNTAX  DisplayString
              MAX-ACCESS  read-only
              STATUS  current
              DESCRIPTION
			"For port configured with OTU2 traffic, IAE alarms
			shall be declared if the IAE bit in the SM overhead
			field (byte 3, bit 6) is 1 for 5 consecutive frames. 
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 52 }

	ommp101OtuBackwardIncomingAlignmentErrorAlarm OBJECT-TYPE
              SYNTAX  DisplayString
              MAX-ACCESS  read-only
              STATUS  current
              DESCRIPTION
			"For port configured with OTU2 traffic, 
			the presence of this alarm conveys that an incoming
			alignment error(IAE) condition is detected
			by the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 53 }

	ommp101OtuBackwardDefectIndicationAlarm OBJECT-TYPE
              SYNTAX  DisplayString
              MAX-ACCESS  read-only
              STATUS  current
              DESCRIPTION
			"For port configured with OTU2 traffic,
			the presence of this alarm conveys that a
			a defect like LOS, LOF, LOM has been detected in the
			by the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 54 }

	ommp101OduSignalFailAlarm OBJECT-TYPE
              SYNTAX  DisplayString
              MAX-ACCESS  read-only
              STATUS  current
              DESCRIPTION
			"For port configured with OTU2 traffic, ODU-SF
			alarm is generated when BIP errors evaluated by 
			PM field of OTU2 frame exceeds the 
			'ommp101OduSignalFailThreshold' threshold.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 55 }

	ommp101OduSignalDegradeAlarm OBJECT-TYPE
              SYNTAX  DisplayString
              MAX-ACCESS  read-only
              STATUS  current
              DESCRIPTION
			"For port configured with OTU2 traffic,ODU-SD
			alarm is generated when BIP errors evaluated by 
			PM field of OTU2 frame exceeds the 	
			'ommp101OduSignalDegradeThreshold' threshold.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 56 }

	ommp101OduAlarmIndicationSignalAlarm OBJECT-TYPE
              SYNTAX  DisplayString
              MAX-ACCESS  read-only
              STATUS  current
              DESCRIPTION
			"For port configured with OTU2 traffic, when the incoming
			OTU2 frame has all 1s in the entire ODUk signal,
			excluding the frame alignment overhead (FA OH),
			OTUk overhead (OTUk OH) and ODUk FTFL, this alarm is
			generated
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 57 }

	ommp101OduTcm1IncomingAlignmentErrorAlarm OBJECT-TYPE
              SYNTAX  DisplayString
              MAX-ACCESS  read-only
              STATUS  current
              DESCRIPTION
			"For port configured with OTU2 traffic, TCM1 IAE
			shall be declared if the accepted STAT information is
			0b010
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 58 }

	ommp101OduTcm2IncomingAlignmentErrorAlarm OBJECT-TYPE
              SYNTAX  DisplayString
              MAX-ACCESS  read-only
              STATUS  current
              DESCRIPTION
			"For port configured with OTU2 traffic, TCM2 IAE
			shall be declared if the accepted STAT information is
			0b010
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 59 }

	ommp101OduTcm3IncomingAlignmentErrorAlarm OBJECT-TYPE
              SYNTAX  DisplayString
              MAX-ACCESS  read-only
              STATUS  current
              DESCRIPTION
			"For port configured with OTU2 traffic, TCM3 IAE
			shall be declared if the accepted STAT information is
			0b010
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 60 }

	ommp101OduTcm4IncomingAlignmentErrorAlarm OBJECT-TYPE
              SYNTAX  DisplayString
              MAX-ACCESS  read-only
              STATUS  current
              DESCRIPTION
			"For port configured with OTU2 traffic, TCM4 IAE
			shall be declared if the accepted STAT information is
			0b010
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 61 }

	ommp101OduTcm5IncomingAlignmentErrorAlarm OBJECT-TYPE
              SYNTAX  DisplayString
              MAX-ACCESS  read-only
              STATUS  current
              DESCRIPTION
			"For port configured with OTU2 traffic, TCM5 IAE
			shall be declared if the accepted STAT information is
			0b010
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 62 }

	ommp101OduTcm6IncomingAlignmentErrorAlarm OBJECT-TYPE
              SYNTAX  DisplayString
              MAX-ACCESS  read-only
              STATUS  current
              DESCRIPTION
			"For port configured with OTU2 traffic, TCM6 IAE
			shall be declared if the accepted STAT information is
			0b010
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 63 }

	ommp101OduLockedDefectAlarm OBJECT-TYPE
              SYNTAX  DisplayString
              MAX-ACCESS  read-only
              STATUS  current
              DESCRIPTION
			"For port configured with OTU2 traffic, 
			the locked maintenance signal is generated on operator
			request in order to lock the signal from user access. It
			consists of a repeating 0b0101 0101 pattern in the
			entire ODUk signal, which excludes the Frame Alignment
			overhead and the OTUk overhead.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 64 }

	ommp101OduOpenConnectionIndicationAlarm OBJECT-TYPE
              SYNTAX  DisplayString
              MAX-ACCESS  read-only
              STATUS  current
              DESCRIPTION
			"For port configured with OTU2 traffic, 
			an open connection indication is sent downstream when
			no signal is detected from upstream. It consists of a
			repeating 0b0110 0110 pattern in the entire ODUk signal,
			which excludes the Frame Alignment overhead and the
			OTUk overhead.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 65 }

	ommp101OduBackwardDefectIndicationAlarm OBJECT-TYPE
              SYNTAX  DisplayString
              MAX-ACCESS  read-only
              STATUS  current
              DESCRIPTION
			"For port configured with OTU2 traffic, 
			the presence of this alarm conveys that either of
			OTU-LOS or OTU-LOF or OTU-LOM or OTU-AIS or ODU-AIS
			or ODU-OCI or ODU-LCK condition is detected
			by the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 66 }

	ommp101OduTcm1BackwardIncomingAlignmentErrorAlarm OBJECT-TYPE
              SYNTAX  DisplayString
              MAX-ACCESS  read-only
              STATUS  current
              DESCRIPTION
			"For port configured with OTU2 traffic, 
			the presence of this alarm conveys that
			TCM1 incoming alignment error (IAE) condition is 
			detected in the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 67 }

	ommp101OduTcm2BackwardIncomingAlignmentErrorAlarm OBJECT-TYPE
              SYNTAX  DisplayString
              MAX-ACCESS  read-only
              STATUS  current
              DESCRIPTION
			"For port configured with OTU2 traffic, 
			the presence of this alarm conveys that
			TCM2 incoming alignment error (IAE) condition is 
			detected in the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 68 }

	ommp101OduTcm3BackwardIncomingAlignmentErrorAlarm OBJECT-TYPE
              SYNTAX  DisplayString
              MAX-ACCESS  read-only
              STATUS  current
              DESCRIPTION
			"For port configured with OTU2 traffic, 
			the presence of this alarm conveys that
			TCM3 incoming alignment error (IAE) condition is 
			detected in the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 69 }


	ommp101OduTcm4BackwardIncomingAlignmentErrorAlarm OBJECT-TYPE
              SYNTAX  DisplayString
              MAX-ACCESS  read-only
              STATUS  current
              DESCRIPTION
			"For port configured with OTU2 traffic, 
			the presence of this alarm conveys that
			TCM4 incoming alignment error (IAE) condition is 
			detected in the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 70 }

	ommp101OduTcm5BackwardIncomingAlignmentErrorAlarm OBJECT-TYPE
              SYNTAX  DisplayString
              MAX-ACCESS  read-only
              STATUS  current
              DESCRIPTION
			"For port configured with OTU2 traffic, 
			the presence of this alarm conveys that
			TCM5 incoming alignment error (IAE) condition is 
			detected in the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 71 }

	ommp101OduTcm6BackwardIncomingAlignmentErrorAlarm OBJECT-TYPE
              SYNTAX  DisplayString
              MAX-ACCESS  read-only
              STATUS  current
              DESCRIPTION
			"For port configured with OTU2 traffic, 
			the presence of this alarm conveys that
			TCM6 incoming alignment error (IAE) condition is 
			detected in the far-end card.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 72 }

	ommp101OduLossOfFrameLossOfMultiframeAlarm OBJECT-TYPE
              SYNTAX  DisplayString
              MAX-ACCESS  read-only
              STATUS  current
              DESCRIPTION
			"While demultiplexing the incoming OPU2 frame into the
			ODU1, if the start of a ODU1 frame is not found	then 
			this alarm is generated. Since the alarm is generated at
			the demultiplexing level, the alarm cannot be
			represented with respect to a client/line port, as one
			ODU1 slice might have multiple client data. This
			property is w.r.t slice
			-----------------------------
			ommp101InterfaceNumber:
			ODU1 slices demapped from OTU2 signal received at LINE PORT
			5 - ODU1 Slice 5
			6 - ODU1 Slice 6
			7 - ODU1 Slice 7
			8 - ODU1 Slice 8
			-----------------------------
			Values :
			If Alarm is Present - Date and Time Stamp
				    eg:2017-5-18,9:47:20.0,+5:30
			If Alarm is Absent  - 0
			-----------------------------"
		::= { ommp101AlarmQueryEntry 73 }

	ommp101OpuPayloadMismatchAlarm OBJECT-TYPE
              SYNTAX  DisplayString
              MAX-ACCESS  read-only
              STATUS  current
              DESCRIPTION
			"For port configured with OTU2 traffic, 
			OPU-PLM Alarm is declared if the accepted payload type
			is not equal to the expected payload type.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 74 }

	ommp101SdhLossOfSignalAlarm OBJECT-TYPE
              SYNTAX  DisplayString
              MAX-ACCESS  read-only
              STATUS  current
              DESCRIPTION
			"For port configured with STM-16 traffic, if there
			is no signal received then SDH-LOS Alarm is 
			generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 75 }

	ommp101SdhOutOfFrameAlarm OBJECT-TYPE
              SYNTAX  DisplayString
              MAX-ACCESS  read-only
              STATUS  current
              DESCRIPTION
			"For port configured with STM-16 traffic, when
			several consecutive SDH frames have A1, A2 bytes errored
			for a period more than 625us, this alarm will be
			generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 76 }

	ommp101SdhLossOfFrameAlarm OBJECT-TYPE
              SYNTAX  DisplayString
              MAX-ACCESS  read-only
              STATUS  current
              DESCRIPTION
			"For port configured with STM-16 traffic, 
			If SDH frame received are out-of-frame (OOF) state for 
			3 ms then LOF alarm is generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 77 }

	ommp101SdhMsAlarmIndicationSignalAlarm OBJECT-TYPE
              SYNTAX  DisplayString
              MAX-ACCESS  read-only
              STATUS  current
              DESCRIPTION
			"For port configured with STM-16 traffic, 
			MS-AIS is an alarm indication signal (AIS) is a signal 
			sent downstream as an indication that an upstream
			defect has been detected.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 82 }

	ommp101SdhMsRemoteDefectIndicationAlarm OBJECT-TYPE
              SYNTAX  DisplayString
              MAX-ACCESS  read-only
              STATUS  current
              DESCRIPTION
			"For port configured with STM-16 traffic, 
			MS-RDI is a signal returned to the transmitting equipment 
			upon detecting a LOS, LOF, or MS-AIS defect
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 84 }

	ommp101SdhMsB2ExcessiveErrorAlarm OBJECT-TYPE
              SYNTAX  DisplayString
              MAX-ACCESS  read-only
              STATUS  current
              DESCRIPTION
			"For port configured with STM-16 traffic, 
			B2 SF alarm is generated when Parity errors evaluated 
			by byte B2 of SDH frame exceeds the 
			'ommp101SdhMsB2ExcessiveErrorThreshold' threshold.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 86 }

	ommp101SdhMsB2SignalDegradeAlarm OBJECT-TYPE
              SYNTAX  DisplayString
              MAX-ACCESS  read-only
              STATUS  current
              DESCRIPTION
			"For port configured with STM-16 traffic,
			B2 SD alarm is generated when Parity errors evaluated 
			by byte B2 of SDH frame exceeds the 
			'ommp101SdhMsB2SignalDegradeThreshold' threshold.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 87 }

	ommp101EthernetLossOfSignalAlarm OBJECT-TYPE
              SYNTAX  DisplayString
              MAX-ACCESS  read-only
              STATUS  current
              DESCRIPTION
			"For port configured with 
			LAN10G traffic,
			if there is no signal received then LOS Alarm is 
			generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 91 }

	ommp101EthernetLinkFailureAlarm OBJECT-TYPE
              SYNTAX  DisplayString
              MAX-ACCESS  read-only
              STATUS  current
              DESCRIPTION
			"For port configured with 
			LAN10G traffic,
			in the event of ingress client signal failure, 
			the link failure alarm is generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 92 }

	ommp101EthernetHighBerAlarm OBJECT-TYPE
              SYNTAX  DisplayString
              MAX-ACCESS  read-only
              STATUS  current
              DESCRIPTION
			"For port configured with 
			LAN10G traffic,
			this alarm is generated when signal BER is
			greater than 1e−4. 
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 93 }

	ommp101EthernetLocalFaultAlarm OBJECT-TYPE
              SYNTAX  DisplayString
              MAX-ACCESS  read-only
              STATUS  current
              DESCRIPTION
			"For port configured with 
			LAN10G traffic,
			if fault is detected on the receive data path then Local
			Fault Alarm is generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 94 }

	ommp101EthernetRemoteFaultAlarm OBJECT-TYPE
              SYNTAX  DisplayString
              MAX-ACCESS  read-only
              STATUS  current
              DESCRIPTION
			"For port configured with 
			LAN10G traffic,
			if fault is detected on the transmit data path then 
			Remote Fault Alarm is generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 95 }

	ommp101OtuTraceIdentifierMismatchAlarm OBJECT-TYPE
              SYNTAX  DisplayString
              MAX-ACCESS  read-only
              STATUS  current
              DESCRIPTION
			"For port configured with OTU2/OTU4 traffic, when there
			is a mismatch between the incoming and the expected
			Trail Trace Identifier(TTI) at the SM section,
			OTU-TIM alarm is generated.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 96 }

	ommp101OduTraceIdentifierMismatchAlarm OBJECT-TYPE
              SYNTAX  DisplayString
              MAX-ACCESS  read-only
              STATUS  current
              DESCRIPTION
			"For port configured with OTU2/OTU4 traffic, when there
			is a mismatch between the incoming and the expected
			Trail Trace Identifier(TTI) at the PM section,
			ODU-TIM alarm is generated.
			-----------------------------
			ommp101InterfaceNumber:
			1 to 10 - CLIENT-1 to CLIENT-10
			11 - LINE PORT
			-----------------------------
			Values :
			If Alarm is Present - Date and Time Stamp
				    eg:2017-5-18,9:47:20.0,+5:30
			If Alarm is Absent  - 0
			-----------------------------"
		::= { ommp101AlarmQueryEntry 97 }

	ommp101EthernetLossOfAlignmentAlarm OBJECT-TYPE
              SYNTAX  DisplayString
              MAX-ACCESS  read-only
              STATUS  current
              DESCRIPTION
			"For port configured with 
			LAN10G traffic,
			if fault is detected on the transmit data path then 
			LOss Of Alignment Alarm is generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 98 }

	ommp101EthernetLossOfBlockLockAlarm OBJECT-TYPE
              SYNTAX  DisplayString
              MAX-ACCESS  read-only
              STATUS  current
              DESCRIPTION
			"For port configured with 
			LAN10G traffic,
			if fault is detected on the transmit data path then 
			Loss Of Block Lock Alarm is generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 99 }

	ommp101EthernetNotAlignedInPcsAlarm OBJECT-TYPE
              SYNTAX  DisplayString
              MAX-ACCESS  read-only
              STATUS  current
              DESCRIPTION
			"For port configured with 
			LAN10G traffic,
			if fault is detected on the transmit data path then 
			Not Aligned In Pcs Alarm is generated.
			-----------------------------
			ommp101InterfaceNumber:
			1 to 10 - CLIENT-1 to CLIENT-10
			-----------------------------
			Values :
			If Alarm is Present - Date and Time Stamp
				    eg:2017-5-18,9:47:20.0,+5:30
			If Alarm is Absent  - 0
			-----------------------------"
		::= { ommp101AlarmQueryEntry 100 }

	ommp101AlarmQueryTableRowStatus OBJECT-TYPE
              SYNTAX      RowStatus
              MAX-ACCESS  read-write
              STATUS      current
              DESCRIPTION
			"*****************************
			This is MIB realted property,
			NOT to be considered as a card property
			*****************************"
              ::= { ommp101AlarmQueryEntry 101 }	                                

--*****************************************************************************
--				    ALARM Notification Table
--*****************************************************************************
	ommp101Cfp2InputPowerFailureAlarmTrap NOTIFICATION-TYPE
		OBJECTS { ommp101Cfp2InputPowerFailureAlarm  }
		STATUS  current
		DESCRIPTION
                        "OMMP101 CFP2 Input Power Failure Alarm Trap"
        ::= { ommp101AlarmNotification 1 }

	ommp101Cfp2OutputPowerFailureAlarmTrap NOTIFICATION-TYPE
		OBJECTS { ommp101Cfp2OutputPowerFailureAlarm  }
		STATUS  current
		DESCRIPTION
                        "OMMP101 CFP2 Output Power Failure Alarm Trap" 
        ::= { ommp101AlarmNotification 2 }

	ommp101Cfp2HighTemperatureAlarmTrap NOTIFICATION-TYPE
		OBJECTS { ommp101Cfp2HighTemperatureAlarm  }
		STATUS  current
		DESCRIPTION
                        "OMMP101 CFP2 High Temperature Alarm Trap" 
        ::= { ommp101AlarmNotification 3 }

	ommp101Cfp2LowTemperatureAlarmTrap NOTIFICATION-TYPE
		OBJECTS { ommp101Cfp2LowTemperatureAlarm  }
		STATUS  current
		DESCRIPTION
                        "OMMP101 CFP2 Low Temperature Alarm Trap" 
        ::= { ommp101AlarmNotification 4 }

	ommp101Cfp2HighTemperatureWarningTrap NOTIFICATION-TYPE
		OBJECTS { ommp101Cfp2HighTemperatureWarning  }
		STATUS  current
		DESCRIPTION
                        "OMMP101 CFP2 High Temperature Warning Trap" 
        ::= { ommp101AlarmNotification 5 }

	ommp101Cfp2LowTemperatureWarningTrap NOTIFICATION-TYPE
		OBJECTS { ommp101Cfp2LowTemperatureWarning  }
		STATUS  current
		DESCRIPTION
                        "OMMP101 CFP2 Low Temperature Warning Trap" 
        ::= { ommp101AlarmNotification 6 }

	ommp101Cfp2InputHighPowerAlarmTrap NOTIFICATION-TYPE
		OBJECTS { ommp101Cfp2InputHighPowerAlarm  }
		STATUS  current
		DESCRIPTION
                        "OMMP101 CFP2 Input High Power Alarm Trap" 
        ::= { ommp101AlarmNotification 7 }

	ommp101Cfp2InputLowPowerAlarmTrap NOTIFICATION-TYPE
		OBJECTS { ommp101Cfp2InputLowPowerAlarm  }
		STATUS  current
		DESCRIPTION
                        "OMMP101 CFP2 Input Low Power Alarm Trap" 
        ::= { ommp101AlarmNotification 8 }

	ommp101Cfp2InputHighPowerWarningTrap NOTIFICATION-TYPE
		OBJECTS { ommp101Cfp2InputHighPowerWarning  }
		STATUS  current
		DESCRIPTION
                        "OMMP101 CFP2 Input High Power Warning Trap" 
        ::= { ommp101AlarmNotification 9 }

	ommp101Cfp2InputLowPowerWarningTrap NOTIFICATION-TYPE
		OBJECTS { ommp101Cfp2InputLowPowerWarning  }
		STATUS  current
		DESCRIPTION
                        "OMMP101 CFP2 Input Low Power Warning Trap" 
        ::= { ommp101AlarmNotification 10 }

	ommp101Cfp2OutputHighPowerAlarmTrap NOTIFICATION-TYPE
		OBJECTS { ommp101Cfp2OutputHighPowerAlarm  }
		STATUS  current
		DESCRIPTION
                        "OMMP101 CFP2 Output High Power Alarm Trap" 
        ::= { ommp101AlarmNotification 11 }

	ommp101Cfp2OutputLowPowerAlarmTrap NOTIFICATION-TYPE
		OBJECTS { ommp101Cfp2OutputLowPowerAlarm  }
		STATUS  current
		DESCRIPTION
                        "OMMP101 CFP2 Output Low Power Alarm Trap" 
        ::= { ommp101AlarmNotification 12 }

	ommp101Cfp2OutputHighPowerWarningTrap NOTIFICATION-TYPE
		OBJECTS { ommp101Cfp2OutputHighPowerWarning  }
		STATUS  current
		DESCRIPTION
                        "OMMP101 CFP2 Output High Power Warning Trap" 
        ::= { ommp101AlarmNotification 13 }

	ommp101Cfp2OutputLowPowerWarningTrap NOTIFICATION-TYPE
		OBJECTS { ommp101Cfp2OutputLowPowerWarning  }
		STATUS  current
		DESCRIPTION
                        "OMMP101 CFP2 Output Low Power Warning Trap" 
        ::= { ommp101AlarmNotification 14 }

	ommp101Cfp2HighSupplyVoltageAlarmTrap NOTIFICATION-TYPE
		OBJECTS { ommp101Cfp2HighSupplyVoltageAlarm  }
		STATUS  current
		DESCRIPTION
                        "OMMP101 CFP2 High Supply Voltage Alarm Trap" 
        ::= { ommp101AlarmNotification 15 }

	ommp101Cfp2LowSupplyVoltageAlarmTrap NOTIFICATION-TYPE
		OBJECTS { ommp101Cfp2LowSupplyVoltageAlarm  }
		STATUS  current
		DESCRIPTION
                        "OMMP101 CFP2 Low Supply Voltage Alarm Trap" 
        ::= { ommp101AlarmNotification 16 }

	ommp101Cfp2HighSupplyVoltageWarningTrap NOTIFICATION-TYPE
		OBJECTS { ommp101Cfp2HighSupplyVoltageWarning  }
		STATUS  current
		DESCRIPTION
                        "OMMP101 CFP2 High Supply Voltage Warning Trap" 
        ::= { ommp101AlarmNotification 17 }

	ommp101Cfp2LowSupplyVoltageWarningTrap NOTIFICATION-TYPE
		OBJECTS { ommp101Cfp2LowSupplyVoltageWarning  }
		STATUS  current
		DESCRIPTION
                        "OMMP101 CFP2 Low Supply Voltage Warning Trap" 
        ::= { ommp101AlarmNotification 18 }

	ommp101Cfp2PresenceAbsenceNotificationTrap NOTIFICATION-TYPE
		OBJECTS { ommp101Cfp2PresenceAbsenceNotification  }
		STATUS  current
		DESCRIPTION
                        "OMMP101 CFP2 Presence Absence Notification Trap" 
        ::= { ommp101AlarmNotification 19 }

	ommp101SfpPlusInputPowerFailureAlarmTrap NOTIFICATION-TYPE
		OBJECTS { ommp101SfpPlusInputPowerFailureAlarm  }
		STATUS  current
		DESCRIPTION
                        "OMMP101 SFP PLUS Input Power Failure Alarm Trap" 
        ::= { ommp101AlarmNotification 20 }

	ommp101SfpPlusOutputPowerFailureAlarmTrap NOTIFICATION-TYPE
		OBJECTS { ommp101SfpPlusOutputPowerFailureAlarm  }
		STATUS  current
		DESCRIPTION
                        "OMMP101 SFP PLUS Output Power Failure Alarm Trap" 
        ::= { ommp101AlarmNotification 21 }

	ommp101SfpPlusHighTemperatureAlarmTrap NOTIFICATION-TYPE
		OBJECTS { ommp101SfpPlusHighTemperatureAlarm  }
		STATUS  current
		DESCRIPTION
                        "OMMP101 SFP PLUS High Temperature Alarm Trap" 
        ::= { ommp101AlarmNotification 22 }

	ommp101SfpPlusLowTemperatureAlarmTrap NOTIFICATION-TYPE
		OBJECTS { ommp101SfpPlusLowTemperatureAlarm  }
		STATUS  current
		DESCRIPTION
                        "OMMP101 SFP PLUS Low Temperature Alarm Trap" 
        ::= { ommp101AlarmNotification 23 }

	ommp101SfpPlusHighTemperatureWarningTrap NOTIFICATION-TYPE
		OBJECTS { ommp101SfpPlusHighTemperatureWarning  }
		STATUS  current
		DESCRIPTION
                        "OMMP101 SFP PLUS High Temperature Warning Trap" 
        ::= { ommp101AlarmNotification 24 }

	ommp101SfpPlusLowTemperatureWarningTrap NOTIFICATION-TYPE
		OBJECTS { ommp101SfpPlusLowTemperatureWarning  }
		STATUS  current
		DESCRIPTION
                        "OMMP101 SFP PLUS Low Temperature Warning Trap" 
        ::= { ommp101AlarmNotification 25 }

	ommp101SfpPlusHighBiasCurrentAlarmTrap NOTIFICATION-TYPE
		OBJECTS { ommp101SfpPlusHighBiasCurrentAlarm  }
		STATUS  current
		DESCRIPTION
                        "OMMP101 SFP PLUS High Bias Current Alarm Trap" 
        ::= { ommp101AlarmNotification 26 }

	ommp101SfpPlusLowBiasCurrentAlarmTrap NOTIFICATION-TYPE
		OBJECTS { ommp101SfpPlusLowBiasCurrentAlarm  }
		STATUS  current
		DESCRIPTION
                        "OMMP101 SFP PLUS Low Bias Current Alarm Trap" 
        ::= { ommp101AlarmNotification 27 }

	ommp101SfpPlusHighBiasCurrentWarningTrap NOTIFICATION-TYPE
		OBJECTS { ommp101SfpPlusHighBiasCurrentWarning  }
		STATUS  current
		DESCRIPTION
                        "OMMP101 SFP PLUS High Bias Current Warning Trap" 
        ::= { ommp101AlarmNotification 28 }

	ommp101SfpPlusLowBiasCurrentWarningTrap NOTIFICATION-TYPE
		OBJECTS { ommp101SfpPlusLowBiasCurrentWarning  }
		STATUS  current
		DESCRIPTION
                        "OMMP101 SFP PLUS Low Bias Current Warning Trap" 
        ::= { ommp101AlarmNotification 29 }

	ommp101SfpPlusInputHighPowerAlarmTrap NOTIFICATION-TYPE
		OBJECTS { ommp101SfpPlusInputHighPowerAlarm  }
		STATUS  current
		DESCRIPTION
                        "OMMP101 SFP PLUS Input High Power Alarm Trap" 
        ::= { ommp101AlarmNotification 30 }

	ommp101SfpPlusInputLowPowerAlarmTrap NOTIFICATION-TYPE
		OBJECTS { ommp101SfpPlusInputLowPowerAlarm  }
		STATUS  current
		DESCRIPTION
                        "OMMP101 SFP PLUS Input Low Power Alarm Trap" 
        ::= { ommp101AlarmNotification 31 }

	ommp101SfpPlusInputHighPowerWarningTrap NOTIFICATION-TYPE
		OBJECTS { ommp101SfpPlusInputHighPowerWarning  }
		STATUS  current
		DESCRIPTION
                        "OMMP101 SFP PLUS Input High Power Warning Trap" 
        ::= { ommp101AlarmNotification 32 }

	ommp101SfpPlusInputLowPowerWarningTrap NOTIFICATION-TYPE
		OBJECTS { ommp101SfpPlusInputLowPowerWarning  }
		STATUS  current
		DESCRIPTION
                        "OMMP101 SFP PLUS Input Low Power Warning Trap" 
        ::= { ommp101AlarmNotification 33 }

	ommp101SfpPlusOutputHighPowerAlarmTrap NOTIFICATION-TYPE
		OBJECTS { ommp101SfpPlusOutputHighPowerAlarm  }
		STATUS  current
		DESCRIPTION
                        "OMMP101 SFP PLUS Output High Power Alarm Trap" 
        ::= { ommp101AlarmNotification 34 }

	ommp101SfpPlusOutputLowPowerAlarmTrap NOTIFICATION-TYPE
		OBJECTS { ommp101SfpPlusOutputLowPowerAlarm  }
		STATUS  current
		DESCRIPTION
                        "OMMP101 SFP PLUS Output Low Power Alarm Trap" 
        ::= { ommp101AlarmNotification 35 }

	ommp101SfpPlusOutputHighPowerWarningTrap NOTIFICATION-TYPE
		OBJECTS { ommp101SfpPlusOutputHighPowerWarning  }
		STATUS  current
		DESCRIPTION
                        "OMMP101 SFP PLUS Output High Power Warning Trap" 
        ::= { ommp101AlarmNotification 36 }

	ommp101SfpPlusOutputLowPowerWarningTrap NOTIFICATION-TYPE
		OBJECTS { ommp101SfpPlusOutputLowPowerWarning  }
		STATUS  current
		DESCRIPTION
                        "OMMP101 SFP PLUS Output Low Power Warning Trap" 
        ::= { ommp101AlarmNotification 37 }

	ommp101SfpPlusHighSupplyVoltageAlarmTrap NOTIFICATION-TYPE
		OBJECTS { ommp101SfpPlusHighSupplyVoltageAlarm  }
		STATUS  current
		DESCRIPTION
                        "OMMP101 SFP PLUS High Supply Voltage Alarm Trap" 
        ::= { ommp101AlarmNotification 38 }

	ommp101SfpPlusLowSupplyVoltageAlarmTrap NOTIFICATION-TYPE
		OBJECTS { ommp101SfpPlusLowSupplyVoltageAlarm  }
		STATUS  current
		DESCRIPTION
                        "OMMP101 SFP PLUS Low Supply Voltage Alarm Trap" 
        ::= { ommp101AlarmNotification 39 }

	ommp101SfpPlusHighSupplyVoltageWarningTrap NOTIFICATION-TYPE
		OBJECTS { ommp101SfpPlusHighSupplyVoltageWarning  }
		STATUS  current
		DESCRIPTION
                        "OMMP101 SFP PLUS High Supply Voltage Warning Trap" 
        ::= { ommp101AlarmNotification 40 }

	ommp101SfpPlusLowSupplyVoltageWarningTrap NOTIFICATION-TYPE
		OBJECTS { ommp101SfpPlusLowSupplyVoltageWarning  }
		STATUS  current
		DESCRIPTION
                        "OMMP101 SFP PLUS Low Supply Voltage Warning Trap" 
        ::= { ommp101AlarmNotification 41 }

	ommp101SfpPlusPresenceAbsenceNotificationTrap NOTIFICATION-TYPE
		OBJECTS { ommp101SfpPlusPresenceAbsenceNotification  }
		STATUS  current
		DESCRIPTION
                        "OMMP101 SFP PLUS Presence Absence Notification Trap" 
        ::= { ommp101AlarmNotification 42 }

	ommp101SfpPlusTransmitFaultPresenceAlarmTrap NOTIFICATION-TYPE
		OBJECTS { ommp101SfpPlusTransmitFaultPresenceAlarm  }
		STATUS  current
		DESCRIPTION
                        "OMMP101 SFP PLUS Transmit Fault Presence Alarm Trap" 
        ::= { ommp101AlarmNotification 43 }

	ommp101OtuLossOfSignalAlarmTrap NOTIFICATION-TYPE
		OBJECTS { ommp101OtuLossOfSignalAlarm  }
		STATUS  current
		DESCRIPTION
                        "OMMP101 OTU Loss Of Signal Alarm Trap" 
        ::= { ommp101AlarmNotification 44 }

	ommp101OtuLossOfFrameAlarmTrap NOTIFICATION-TYPE
		OBJECTS { ommp101OtuLossOfFrameAlarm  }
		STATUS  current
		DESCRIPTION
                        "OMMP101 OTU Loss Of Frame Alarm Trap" 
        ::= { ommp101AlarmNotification 45 }

	ommp101OtuOutOfFrameAlarmTrap NOTIFICATION-TYPE
		OBJECTS { ommp101OtuOutOfFrameAlarm  }
		STATUS  current
		DESCRIPTION
                        "OMMP101 OTU Out Of Frame Alarm Trap" 
        ::= { ommp101AlarmNotification 46 }

	ommp101OtuLossOfMultiFrameAlarmTrap NOTIFICATION-TYPE
		OBJECTS { ommp101OtuLossOfMultiFrameAlarm  }
		STATUS  current
		DESCRIPTION
                        "OMMP101 OTU Loss Of Multi Frame Alarm Trap" 
        ::= { ommp101AlarmNotification 47 }

	ommp101OtuOutOfMultiFrameAlarmTrap NOTIFICATION-TYPE
		OBJECTS { ommp101OtuOutOfMultiFrameAlarm  }
		STATUS  current
		DESCRIPTION
                        "OMMP101 OTU Out Of Multi Frame Alarm Trap" 
        ::= { ommp101AlarmNotification 48 }

	ommp101OtuSignalFailAlarmTrap NOTIFICATION-TYPE
		OBJECTS { ommp101OtuSignalFailAlarm  }
		STATUS  current
		DESCRIPTION
                        "OMMP101 OTU Signal Fail Alarm Trap" 
        ::= { ommp101AlarmNotification 49 }

	ommp101OtuSignalDegradeAlarmTrap NOTIFICATION-TYPE
		OBJECTS { ommp101OtuSignalDegradeAlarm  }
		STATUS  current
		DESCRIPTION
                        "OMMP101 OTU Signal Degrade Alarm Trap" 
        ::= { ommp101AlarmNotification 50 }

	ommp101OtuAlarmIndicationSignalAlarmTrap NOTIFICATION-TYPE
		OBJECTS { ommp101OtuAlarmIndicationSignalAlarm  }
		STATUS  current
		DESCRIPTION
                        "OMMP101 OTU Alarm Indication Signal Alarm Trap" 
        ::= { ommp101AlarmNotification 51 }

	ommp101OtuIncomingAlignmentErrorAlarmTrap NOTIFICATION-TYPE
		OBJECTS { ommp101OtuIncomingAlignmentErrorAlarm  }
		STATUS  current
		DESCRIPTION
                        "OMMP101 OTU Incoming Alignment Error Alarm Trap" 
        ::= { ommp101AlarmNotification 52 }

	ommp101OtuBackwardIncomingAlignmentErrorAlarmTrap NOTIFICATION-TYPE
		OBJECTS { ommp101OtuBackwardIncomingAlignmentErrorAlarm  }
		STATUS  current
		DESCRIPTION
                        "OMMP101 OTU Backward Incoming Alignment Error Alarm Trap" 
        ::= { ommp101AlarmNotification 53 }

	ommp101OtuBackwardDefectIndicationAlarmTrap NOTIFICATION-TYPE
		OBJECTS { ommp101OtuBackwardDefectIndicationAlarm  }
		STATUS  current
		DESCRIPTION
                        "OMMP101 OTU Backward Defect Indication Alarm Trap" 
        ::= { ommp101AlarmNotification 54 }

	ommp101OduSignalFailAlarmTrap NOTIFICATION-TYPE
		OBJECTS { ommp101OduSignalFailAlarm  }
		STATUS  current
		DESCRIPTION
                        "OMMP101 ODU Signal Fail Alarm Trap" 
        ::= { ommp101AlarmNotification 55 }

	ommp101OduSignalDegradeAlarmTrap NOTIFICATION-TYPE
		OBJECTS { ommp101OduSignalDegradeAlarm  }
		STATUS  current
		DESCRIPTION
                        "OMMP101 ODU Signal Degrade Alarm Trap" 
        ::= { ommp101AlarmNotification 56 }

	ommp101OduAlarmIndicationSignalAlarmTrap NOTIFICATION-TYPE
		OBJECTS { ommp101OduAlarmIndicationSignalAlarm  }
		STATUS  current
		DESCRIPTION
                        "OMMP101 ODU Alarm Indication Signal Alarm Trap" 
        ::= { ommp101AlarmNotification 57 }

	ommp101OduTcm1IncomingAlignmentErrorAlarmTrap NOTIFICATION-TYPE
		OBJECTS { ommp101OduTcm1IncomingAlignmentErrorAlarm  }
		STATUS  current
		DESCRIPTION
                        "OMMP101 ODU TCM1 Incoming Alignment Error Alarm Trap" 
        ::= { ommp101AlarmNotification 58 }

	ommp101OduTcm2IncomingAlignmentErrorAlarmTrap NOTIFICATION-TYPE
		OBJECTS { ommp101OduTcm2IncomingAlignmentErrorAlarm  }
		STATUS  current
		DESCRIPTION
                        "OMMP101 ODU TCM2 Incoming Alignment Error Alarm Trap" 
        ::= { ommp101AlarmNotification 59 }

	ommp101OduTcm3IncomingAlignmentErrorAlarmTrap NOTIFICATION-TYPE
		OBJECTS { ommp101OduTcm3IncomingAlignmentErrorAlarm  }
		STATUS  current
		DESCRIPTION
                        "OMMP101 ODU TCM3 Incoming Alignment Error Alarm Trap" 
        ::= { ommp101AlarmNotification 60 }

	ommp101OduTcm4IncomingAlignmentErrorAlarmTrap NOTIFICATION-TYPE
		OBJECTS { ommp101OduTcm4IncomingAlignmentErrorAlarm  }
		STATUS  current
		DESCRIPTION
                        "OMMP101 ODU TCM4 Incoming Alignment Error Alarm Trap" 
        ::= { ommp101AlarmNotification 61 }

	ommp101OduTcm5IncomingAlignmentErrorAlarmTrap NOTIFICATION-TYPE
		OBJECTS { ommp101OduTcm5IncomingAlignmentErrorAlarm  }
		STATUS  current
		DESCRIPTION
                        "OMMP101 ODU TCM5 Incoming Alignment Error Alarm Trap" 
        ::= { ommp101AlarmNotification 62 }

	ommp101OduTcm6IncomingAlignmentErrorAlarmTrap NOTIFICATION-TYPE
		OBJECTS { ommp101OduTcm6IncomingAlignmentErrorAlarm  }
		STATUS  current
		DESCRIPTION
                        "OMMP101 ODU TCM6 Incoming Alignment Error Alarm Trap" 
        ::= { ommp101AlarmNotification 63 }

	ommp101OduLockedDefectAlarmTrap NOTIFICATION-TYPE
		OBJECTS { ommp101OduLockedDefectAlarm  }
		STATUS  current
		DESCRIPTION
                        "OMMP101 ODU Locked Defect Alarm Trap" 
        ::= { ommp101AlarmNotification 64 }

	ommp101OduOpenConnectionIndicationAlarmTrap NOTIFICATION-TYPE
		OBJECTS { ommp101OduOpenConnectionIndicationAlarm  }
		STATUS  current
		DESCRIPTION
                        "OMMP101 ODU Open Connection Indication Alarm Trap" 
        ::= { ommp101AlarmNotification 65 }

	ommp101OduBackwardDefectIndicationAlarmTrap NOTIFICATION-TYPE
		OBJECTS { ommp101OduBackwardDefectIndicationAlarm  }
		STATUS  current
		DESCRIPTION
                        "OMMP101 ODU Backward Defect Indication Alarm Trap" 
        ::= { ommp101AlarmNotification 66 }

	ommp101OduTcm1BackwardIncomingAlignmentErrorAlarmTrap NOTIFICATION-TYPE
		OBJECTS { ommp101OduTcm1BackwardIncomingAlignmentErrorAlarm  }
		STATUS  current
		DESCRIPTION
                        "OMMP101 ODU TCM1 Backward Incoming Alignment Error Alarm Trap" 
        ::= { ommp101AlarmNotification 67 }

	ommp101OduTcm2BackwardIncomingAlignmentErrorAlarmTrap NOTIFICATION-TYPE
		OBJECTS { ommp101OduTcm2BackwardIncomingAlignmentErrorAlarm  }
		STATUS  current
		DESCRIPTION
                        "OMMP101 ODU TCM2 Backward Incoming Alignment Error Alarm Trap" 
        ::= { ommp101AlarmNotification 68 }

	ommp101OduTcm3BackwardIncomingAlignmentErrorAlarmTrap NOTIFICATION-TYPE
		OBJECTS { ommp101OduTcm3BackwardIncomingAlignmentErrorAlarm  }
		STATUS  current
		DESCRIPTION
                        "OMMP101 ODU TCM3 Backward Incoming Alignment Error Alarm Trap" 
        ::= { ommp101AlarmNotification 69 }

	ommp101OduTcm4BackwardIncomingAlignmentErrorAlarmTrap NOTIFICATION-TYPE
		OBJECTS { ommp101OduTcm4BackwardIncomingAlignmentErrorAlarm  }
		STATUS  current
		DESCRIPTION
                        "OMMP101 ODU TCM4 Backward Incoming Alignment Error Alarm Trap" 
        ::= { ommp101AlarmNotification 70 }

	ommp101OduTcm5BackwardIncomingAlignmentErrorAlarmTrap NOTIFICATION-TYPE
		OBJECTS { ommp101OduTcm5BackwardIncomingAlignmentErrorAlarm  }
		STATUS  current
		DESCRIPTION
                        "OMMP101 ODU TCM5 Backward Incoming Alignment Error Alarm Trap" 
        ::= { ommp101AlarmNotification 71 }

	ommp101OduTcm6BackwardIncomingAlignmentErrorAlarmTrap NOTIFICATION-TYPE
		OBJECTS { ommp101OduTcm6BackwardIncomingAlignmentErrorAlarm  }
		STATUS  current
		DESCRIPTION
                        "OMMP101 ODU TCM6 Backward Incoming Alignment Error Alarm Trap" 
        ::= { ommp101AlarmNotification 72 }

	ommp101OduLossOfFrameLossOfMultiframeAlarmTrap NOTIFICATION-TYPE
		OBJECTS { ommp101OduLossOfFrameLossOfMultiframeAlarm  }
		STATUS  current
		DESCRIPTION
                        "OMMP101 ODU Loss Of Frame Loss Of Multiframe Alarm Trap" 
        ::= { ommp101AlarmNotification 73 }

	ommp101OpuPayloadMismatchAlarmTrap NOTIFICATION-TYPE
		OBJECTS { ommp101OpuPayloadMismatchAlarm  }
		STATUS  current
		DESCRIPTION
                        "OMMP101 OPU Payload Mismatch Alarm Trap" 
        ::= { ommp101AlarmNotification 74 }

	ommp101SdhLossOfSignalAlarmTrap NOTIFICATION-TYPE
		OBJECTS { ommp101SdhLossOfSignalAlarm  }
		STATUS  current
		DESCRIPTION
                        "OMMP101 SDH Loss Of Signal Alarm Trap" 
        ::= { ommp101AlarmNotification 75 }

	ommp101SdhOutOfFrameAlarmTrap NOTIFICATION-TYPE
		OBJECTS { ommp101SdhOutOfFrameAlarm  }
		STATUS  current
		DESCRIPTION
                        "OMMP101 SDH Out Of Frame Alarm Trap" 
        ::= { ommp101AlarmNotification 76 }

	ommp101SdhLossOfFrameAlarmTrap NOTIFICATION-TYPE
		OBJECTS { ommp101SdhLossOfFrameAlarm  }
		STATUS  current
		DESCRIPTION
                        "OMMP101 SDH Loss Of Frame Alarm Trap" 
        ::= { ommp101AlarmNotification 77 }

	ommp101SdhMsAlarmIndicationSignalAlarmTrap NOTIFICATION-TYPE
		OBJECTS { ommp101SdhMsAlarmIndicationSignalAlarm  }
		STATUS  current
		DESCRIPTION
                        "OMMP101 SDH MS Alarm Indication Signal Alarm Trap" 
        ::= { ommp101AlarmNotification 82 }

	ommp101SdhMsRemoteDefectIndicationAlarmTrap NOTIFICATION-TYPE
		OBJECTS { ommp101SdhMsRemoteDefectIndicationAlarm  }
		STATUS  current
		DESCRIPTION
                        "OMMP101 SDH MS Remote Defect Indication Alarm Trap" 
        ::= { ommp101AlarmNotification 84 }

	ommp101SdhMsB2ExcessiveErrorAlarmTrap NOTIFICATION-TYPE
		OBJECTS { ommp101SdhMsB2ExcessiveErrorAlarm  }
		STATUS  current
		DESCRIPTION
                        "OMMP101 SDH MS B2 Signal Fail Alarm Trap" 
        ::= { ommp101AlarmNotification 86 }

	ommp101SdhMsB2SignalDegradeAlarmTrap NOTIFICATION-TYPE
		OBJECTS { ommp101SdhMsB2SignalDegradeAlarm  }
		STATUS  current
		DESCRIPTION
                        "OMMP101 SDH MS B2 Signal Degrade Alarm Trap" 
        ::= { ommp101AlarmNotification 87 }

	ommp101EthernetLossOfSignalAlarmTrap NOTIFICATION-TYPE
		OBJECTS { ommp101EthernetLossOfSignalAlarm  }
		STATUS  current
		DESCRIPTION
                        "OMMP101 Ethernet Loss Of Signal Alarm Trap" 
        ::= { ommp101AlarmNotification 91 }

	ommp101EthernetLinkFailureAlarmTrap NOTIFICATION-TYPE
		OBJECTS { ommp101EthernetLinkFailureAlarm  }
		STATUS  current
		DESCRIPTION
                        "OMMP101 Ethernet Link Failure Alarm Trap" 
        ::= { ommp101AlarmNotification 92 }

	ommp101EthernetHighBerAlarmTrap NOTIFICATION-TYPE
		OBJECTS { ommp101EthernetHighBerAlarm  }
		STATUS  current
		DESCRIPTION
                        "OMMP101 Ethernet High Ber Alarm Trap" 
        ::= { ommp101AlarmNotification 93 }

	ommp101EthernetLocalFaultAlarmTrap NOTIFICATION-TYPE
		OBJECTS { ommp101EthernetLocalFaultAlarm  }
		STATUS  current
		DESCRIPTION
                        "OMMP101 Ethernet Local Fault Alarm Trap" 
        ::= { ommp101AlarmNotification 94 }

	ommp101EthernetRemoteFaultAlarmTrap NOTIFICATION-TYPE
		OBJECTS { ommp101EthernetRemoteFaultAlarm  }
		STATUS  current
		DESCRIPTION
                        "OMMP101 Ethernet Remote Fault Alarm Trap" 
        ::= { ommp101AlarmNotification 95 }
        
	ommp101OtuTraceIdentifierMismatchAlarmTrap NOTIFICATION-TYPE
		OBJECTS { ommp101OtuTraceIdentifierMismatchAlarm  }
		STATUS  current
		DESCRIPTION
                        "OMMP101 OTU Trace Identifier Mismatch Alarm Trap" 
        ::= { ommp101AlarmNotification 96 }
		
	ommp101OduTraceIdentifierMismatchAlarmTrap NOTIFICATION-TYPE
		OBJECTS { ommp101OduTraceIdentifierMismatchAlarm  }
		STATUS  current
		DESCRIPTION
                        "OMMP101 ODU Trace Identifier Mismatch Alarm Trap" 
        ::= { ommp101AlarmNotification 97 }

	ommp101EthernetLossOfAlignmentAlarmTrap NOTIFICATION-TYPE
		OBJECTS { ommp101EthernetLossOfAlignmentAlarm  }
		STATUS  current
		DESCRIPTION
                        "OMMP101 Ethernet Loss Of Alignment Alarm Trap" 
        ::= { ommp101AlarmNotification 98 }

	ommp101EthernetLossOfBlockLockAlarmTrap NOTIFICATION-TYPE
		OBJECTS { ommp101EthernetLossOfBlockLockAlarm  }
		STATUS  current
		DESCRIPTION
                        "OMMP101 Ethernet Loss Of Block Lock Alarm Trap" 
        ::= { ommp101AlarmNotification 99 }
        
	ommp101EthernetNotAlignedInPcsAlarmTrap NOTIFICATION-TYPE
		OBJECTS { ommp101EthernetNotAlignedInPcsAlarm  }
		STATUS  current
		DESCRIPTION
                        "OMMP101 Ethernet Remote Not Aligned In PCS Alarm Trap" 
        ::= { ommp101AlarmNotification 100 }

--*****************************************************************************
--				    PERFORMANCE
--*****************************************************************************        

	ommp101PerformanceTable OBJECT-TYPE
	      SYNTAX  SEQUENCE OF Ommp101PerformanceEntry
              MAX-ACCESS  not-accessible
              STATUS  current
              DESCRIPTION
                      "Gives Optical and Signal performance status of the OMMP101 card"
		::= { ommp101Performance 1 }	

	ommp101PerformanceEntry   OBJECT-TYPE
              SYNTAX  Ommp101PerformanceEntry 
              MAX-ACCESS  not-accessible
              STATUS  current
              DESCRIPTION 
              	""
		INDEX   { node, rack , subRack , slot , ommp101InterfaceNumber}
		::= { ommp101PerformanceTable 1 }
	
	Ommp101PerformanceEntry ::= 
		SEQUENCE {
				ommp101Cfp2InputPower							DisplayString,
				ommp101Cfp2OutputPower						DisplayString,
				ommp101Cfp2SupplyVoltage						DisplayString,
				ommp101Cfp2Temperature						DisplayString,
				ommp101SfpPlusInputPower							DisplayString,
				ommp101SfpPlusOutputPower						DisplayString,
				ommp101SfpPlusBiasCurrent						DisplayString,
				ommp101SfpPlusSupplyVoltage						DisplayString,
				ommp101SfpPlusTemperature						DisplayString,
				ommp101OtnFecUncorrectedWords					DisplayString,
				ommp101OtnFecCorrectedBits						DisplayString,
				ommp101OtnFecZerosCorrectedBits					DisplayString,
				ommp101OtnFecOnesCorrectedBits					DisplayString,
				ommp101OtuBitInterleavedParityErrors					DisplayString,
				ommp101OtuBackwardErrorIndicationErrorCount				DisplayString,
				ommp101OtuErrorFreeSeconds						DisplayString,
				ommp101OtuErrorSeconds						DisplayString,
				ommp101OtuBackgroundBlockErrors					DisplayString,
				ommp101OtuSevereErrorSeconds						DisplayString,
				ommp101OtuUnavailableSeconds						DisplayString,
				ommp101OtuBackgroundBlockErrorRatio					DisplayString,
				ommp101OtuSevereErrorSecondsErrorRatio				DisplayString,
				ommp101OtuFarEndErrorFreeSeconds					DisplayString,
				ommp101OtuFarEndErrorSeconds						DisplayString,
				ommp101OtuFarEndBackgroundBlockErrors				DisplayString,
				ommp101OtuFarEndSevereErrorSeconds					DisplayString,
				ommp101OtuFarEndUnavailableSeconds					DisplayString,
				ommp101OtuFarEndBackgroundBlockErrorRatio				DisplayString,
				ommp101OtuFarEndSevereErrorSecondsErrorRatio				DisplayString,
				ommp101OtuErrorRatio							DisplayString,
				ommp101OtuBitErrorRate						DisplayString,
				ommp101OduBitInterleavedParityErrors					DisplayString,
				ommp101OduTcm1BitInterleavedParityErrors				DisplayString,
				ommp101OduTcm2BitInterleavedParityErrors				DisplayString,
				ommp101OduTcm3BitInterleavedParityErrors				DisplayString,
				ommp101OduTcm4BitInterleavedParityErrors				DisplayString,
				ommp101OduTcm5BitInterleavedParityErrors				DisplayString,
				ommp101OduTcm6BitInterleavedParityErrors				DisplayString,
				ommp101OduTcm1IncomingAlignmentErrorSeconds				DisplayString,
				ommp101OduBackwardErrorIndicationErrorCount				DisplayString,
				ommp101OduTcm1BackwardErrorIndicationErrorCount			DisplayString,
				ommp101OduTcm2BackwardErrorIndicationErrorCount			DisplayString,
				ommp101OduTcm3BackwardErrorIndicationErrorCount			DisplayString,
				ommp101OduTcm4BackwardErrorIndicationErrorCount			DisplayString,
				ommp101OduTcm5BackwardErrorIndicationErrorCount			DisplayString,
				ommp101OduTcm6BackwardErrorIndicationErrorCount			DisplayString,
				ommp101OduTcm1BackwardIncomingAlignmentErrorSeconds			DisplayString,
				ommp101OduDelayMeasurement						DisplayString,
				ommp101OduErrorFreeSeconds						DisplayString,
				ommp101OduErrorSeconds						DisplayString,
				ommp101OduBackgroundBlockErrors					DisplayString,
				ommp101OduSevereErrorSeconds						DisplayString,
				ommp101OduUnavailableSeconds						DisplayString,
				ommp101OduBackgroundBlockErrorRatio					DisplayString,
				ommp101OduSevereErrorSecondsErrorRatio				DisplayString,
				ommp101OduFarEndErrorFreeSeconds					DisplayString,
				ommp101OduFarEndErrorSeconds						DisplayString,
				ommp101OduFarEndBackgroundBlockErrors				DisplayString,
				ommp101OduFarEndSevereErrorSeconds					DisplayString,
				ommp101OduFarEndUnavailableSeconds					DisplayString,
				ommp101OduFarEndBackgroundBlockErrorRatio				DisplayString,
				ommp101OduFarEndSevereErrorSecondsErrorRatio				DisplayString,
				ommp101SdhRsB1BitInterleavedParityErrors				DisplayString,
				ommp101SdhMsB2BitInterleavedParityErrors				DisplayString,
				ommp101SdhMsRemoteErrorIndicationErrorCount				DisplayString,
				ommp101SdhErrorFreeSeconds						DisplayString,
				ommp101SdhErrorSeconds						DisplayString,
				ommp101SdhBackgroundBlockErrors					DisplayString,
				ommp101SdhSevereErrorSeconds						DisplayString,
				ommp101SdhUnavailableSeconds						DisplayString,
				ommp101SdhErrorSecondsErrorRatio					DisplayString,
				ommp101SdhBackgroundBlockErrorRatio					DisplayString,
				ommp101SdhSevereErrorSecondsErrorRatio					DisplayString,
				ommp101EthernetTerminatedFramesTransmitted				DisplayString,		
				ommp101EthernetTerminatedFramesReceived					DisplayString,		
				ommp101EthernetTerminatedVlanTaggedFramesTransmitted			DisplayString,		
				ommp101EthernetTerminatedVlanTaggedFramesReceived			DisplayString,		
				ommp101EthernetTerminatedUnicastFramesTransmitted			DisplayString,		
				ommp101EthernetTerminatedUnicastFramesReceived				DisplayString,				
				ommp101EthernetTerminatedBroadcastFramesTransmitted			DisplayString,		
				ommp101EthernetTerminatedBroadcastFramesReceived			DisplayString,				
				ommp101EthernetTerminatedMulticastFramesTransmitted			DisplayString,		
				ommp101EthernetTerminatedMulticastFramesReceived			DisplayString,				
				ommp101EthernetTerminatedOverSizeFramesTransmitted			DisplayString,
				ommp101EthernetTerminatedOverSizeFramesReceived				DisplayString,		
				ommp101EthernetTerminatedUnderSizeFramesTransmitted			DisplayString,
				ommp101EthernetTerminatedUnderSizeFramesReceived			DisplayString,		
				ommp101EthernetTerminatedFrameCheckSequenceErrorsTransmitted		DisplayString,		
				ommp101EthernetTerminatedFrameCheckSequenceErrorsReceived		DisplayString,				
				ommp101EthernetTerminatedControlFramesTransmitted			DisplayString,		
				ommp101EthernetTerminatedControlFramesReceived				DisplayString,				
				ommp101EthernetStatsPkts64OctsTransmitted				DisplayString,		
				ommp101EthernetStatsPkts64OctsReceived					DisplayString,				
				ommp101EthernetStatsPkts65to127OctsTransmitted				DisplayString,		
				ommp101EthernetStatsPkts65to127OctsReceived				DisplayString,				
				ommp101EthernetStatsPkts128to255OctsTransmitted				DisplayString,		
				ommp101EthernetStatsPkts128to255OctsReceived				DisplayString,				
				ommp101EthernetStatsPkts256to511OctsTransmitted				DisplayString,		
				ommp101EthernetStatsPkts256to511OctsReceived				DisplayString,				
				ommp101EthernetStatsPkts512to1023OctsTransmitted			DisplayString,		
				ommp101EthernetStatsPkts512to1023OctsReceived				DisplayString,				
				ommp101EthernetStatsPkts1024to1518OctsTransmitted			DisplayString,		
				ommp101EthernetStatsPkts1024to1518OctsReceived				DisplayString,				
				ommp101EthernetStatsPkts1519toMaxOctsTransmitted			DisplayString,		
				ommp101EthernetStatsPkts1519toMaxOctsReceived				DisplayString,				
				ommp101EthernetStatsJabberTransmitted					DisplayString,		
				ommp101EthernetStatsJabberReceived					DisplayString,				
				ommp101EthernetStatsFragmentsTransmitted				DisplayString,
				ommp101EthernetStatsFragmentsReceived					DisplayString,
				ommp101EthernetPauseControlFramesTransmitted				DisplayString,
				ommp101EthernetPauseControlFramesReceived				DisplayString,
				ommp101PerformanceTableRowStatus					RowStatus
			}	           

	ommp101Cfp2InputPower OBJECT-TYPE
		SYNTAX  DisplayString
		MAX-ACCESS  read-only
		STATUS  current
		DESCRIPTION
			"Gives the current Input power(dbm) received at the port
			-----------------------------
			ommp101InterfaceNumber:
			11 - LINE PORT
			-----------------------------
			Values:
			eg: -9.0
			-----------------------------"
	::= { ommp101PerformanceEntry 1 }

	ommp101Cfp2OutputPower OBJECT-TYPE
		SYNTAX  DisplayString
		MAX-ACCESS  read-only
		STATUS  current
		DESCRIPTION
			"Gives the current Output power(dbm) transmitted at the port
			-----------------------------
			ommp101InterfaceNumber:
			11 - LINE PORT
			-----------------------------
			Values:
			eg: -0.6
			-----------------------------"
	::= { ommp101PerformanceEntry 2 }

	ommp101Cfp2SupplyVoltage OBJECT-TYPE
		SYNTAX  DisplayString
		MAX-ACCESS  read-only
		STATUS  current
		DESCRIPTION
			"Gives the Supply Voltage of the port
			-----------------------------
			ommp101InterfaceNumber:
			11 - LINE PORT
			-----------------------------
			Values:
			eg: 3.3
			-----------------------------"
	::= { ommp101PerformanceEntry 3 }

	ommp101Cfp2Temperature OBJECT-TYPE
		SYNTAX  DisplayString
		MAX-ACCESS  read-only
		STATUS  current
		DESCRIPTION
			"Gives the temperature(degree celcius) of the transmitter
			at  the port
			-----------------------------
			ommp101InterfaceNumber:
			11 - LINE PORT
			-----------------------------
			Values:
			eg: 33.35
			-----------------------------"
	::= { ommp101PerformanceEntry 4 }

	ommp101SfpPlusInputPower OBJECT-TYPE
		SYNTAX  DisplayString
		MAX-ACCESS  read-only
		STATUS  current
		DESCRIPTION
			"Gives the current Input power(dbm) received at the port
			-----------------------------
			ommp101InterfaceNumber:
			1 to 10 - CLIENT-1 to CLIENT-10
			-----------------------------
			Values:
			eg: -9.0
			-----------------------------"
	::= { ommp101PerformanceEntry 5 }

	ommp101SfpPlusOutputPower OBJECT-TYPE
		SYNTAX  DisplayString
		MAX-ACCESS  read-only
		STATUS  current
		DESCRIPTION
			"Gives the current Output power(dbm) transmitted at the port
			-----------------------------
			ommp101InterfaceNumber:
			1 to 10 - CLIENT-1 to CLIENT-10
			-----------------------------
			Values:
			eg: -6.0
			-----------------------------"
	::= { ommp101PerformanceEntry 6 }

	ommp101SfpPlusBiasCurrent OBJECT-TYPE
		SYNTAX  DisplayString
		MAX-ACCESS  read-only
		STATUS  current
		DESCRIPTION
			"Gives the bias current(mA) thats transmitted at the port
			-----------------------------
			ommp101InterfaceNumber:
			1 to 10 - CLIENT-1 to CLIENT-10
			-----------------------------
			Values:
			eg: 55
			-----------------------------"
	::= { ommp101PerformanceEntry 7 }

	ommp101SfpPlusSupplyVoltage OBJECT-TYPE
		SYNTAX  DisplayString
		MAX-ACCESS  read-only
		STATUS  current
		DESCRIPTION
			"Gives the Supply Voltage of the port
			-----------------------------
			ommp101InterfaceNumber:
			1 to 10 - CLIENT-1 to CLIENT-10
			-----------------------------
			Values:
			eg: 3.3
			-----------------------------"
	::= { ommp101PerformanceEntry 8 }

	ommp101SfpPlusTemperature OBJECT-TYPE
		SYNTAX  DisplayString
		MAX-ACCESS  read-only
		STATUS  current
		DESCRIPTION
			"Gives the temperature(degree celcius) of the transmitter
			at the port
			-----------------------------
			ommp101InterfaceNumber:
			1 to 10 - CLIENT-1 to CLIENT-10
			-----------------------------
			Values:
			eg: 33.35
			-----------------------------"
	::= { ommp101PerformanceEntry 9 }

	ommp101OtnFecUncorrectedWords OBJECT-TYPE
		SYNTAX  DisplayString
		MAX-ACCESS  read-only
		STATUS  current
		DESCRIPTION
			"For port configured with OTU2 traffic,
			OTU Uncorrected Word Error Counter counts the number of
			FEC errored code words that could not be corrected.
			-----------------------------
			ommp101InterfaceNumber:
			1 to 10 - CLIENT-1 to CLIENT-10
			11 - LINE PORT
			-----------------------------
			Values:
			eg: 1234
			-----------------------------"
	::= { ommp101PerformanceEntry 10 }

	ommp101OtnFecCorrectedBits OBJECT-TYPE
		SYNTAX  DisplayString
		MAX-ACCESS  read-only
		STATUS  current
		DESCRIPTION
			"For port configured with OTU2 traffic,
			OTU Corrected Bit Error Counter counts the number of
			FEC error bits that could be corrected(sum of ones
			corrected and zeros corrected bits).
			-----------------------------
			ommp101InterfaceNumber:
			1 to 10 - CLIENT-1 to CLIENT-10
			11 - LINE PORT
			-----------------------------
			Values:
			eg: 1234
			-----------------------------"
	::= { ommp101PerformanceEntry 11 }

	ommp101OtnFecZerosCorrectedBits OBJECT-TYPE
		SYNTAX  DisplayString
		MAX-ACCESS  read-only
		STATUS  current
		DESCRIPTION
			"For port configured with OTU2 traffic,
			OTU Zero Corrected Bits Error Counter counts the number
			of FEC error bits that could be corrected from
			one to zero value(Expected 0 but received as 1).
			-----------------------------
			ommp101InterfaceNumber:
			1 to 10 - CLIENT-1 to CLIENT-10
			11 - LINE PORT
			-----------------------------
			Values:
			eg: 1234
			-----------------------------"
	::= { ommp101PerformanceEntry 12 }

	ommp101OtnFecOnesCorrectedBits OBJECT-TYPE
		SYNTAX  DisplayString
		MAX-ACCESS  read-only
		STATUS  current
		DESCRIPTION
			"For port configured with OTU2 traffic,
			OTU Ones Corrected Byte Error Counter counts the number
			of FEC error bytes that could be corrected from
			zero to one value(Expected 1 but received as 0).
			-----------------------------
			ommp101InterfaceNumber:
			1 to 10 - CLIENT-1 to CLIENT-10
			11 - LINE PORT
			-----------------------------
			Values:
			eg: 1234
			-----------------------------"
	::= { ommp101PerformanceEntry 13 }

	ommp101OtuBitInterleavedParityErrors OBJECT-TYPE
		SYNTAX  DisplayString
		MAX-ACCESS  read-only
		STATUS  current
		DESCRIPTION
			"For port configured with OTU2 traffic,
			OTU-BIP Counter counts the Parity errors evaluated by
			SM field of an OTU2 frame.
			-----------------------------
			ommp101InterfaceNumber:
			1 to 10 - CLIENT-1 to CLIENT-10
			11 - LINE PORT
			-----------------------------
			Values:
			eg: 1234
			-----------------------------"
	::= { ommp101PerformanceEntry 14 }

	ommp101OtuBackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code.
			-----------------------------
			ommp101InterfaceNumber:
			1 to 10 - CLIENT-1 to CLIENT-10
			11 - LINE PORT
			-----------------------------
			Values:
			eg: 1234
			-----------------------------"
	::= { ommp101PerformanceEntry 16 }

	ommp101OtuErrorFreeSeconds OBJECT-TYPE
		SYNTAX  DisplayString
		MAX-ACCESS  read-only
		STATUS  current
		DESCRIPTION
			"For port configured with OTU2 traffic,
			OTU Error Free Seconds increases when no BIP errors
			or defects are detected
			-----------------------------
			ommp101InterfaceNumber:
			1 to 10 - CLIENT-1 to CLIENT-10
			11 - LINE PORT
			-----------------------------
			Values:
			eg: 1234
			-----------------------------"
	::= { ommp101PerformanceEntry 18 }

	ommp101OtuErrorSeconds OBJECT-TYPE
		SYNTAX  DisplayString
		MAX-ACCESS  read-only
		STATUS  current
		DESCRIPTION
			"For port configured with OTU2 traffic,
			OTU Error Seconds increases when any defects like 
			OTU-AIS, SM-TIM etc are detected at the
			section monitoring level
			-----------------------------
			ommp101InterfaceNumber:
			1 to 10 - CLIENT-1 to CLIENT-10
			11 - LINE PORT
			-----------------------------
			Values:
			eg: 1234
			-----------------------------"
	::= { ommp101PerformanceEntry 19 }

	ommp101OtuBackgroundBlockErrors OBJECT-TYPE
		SYNTAX  DisplayString
		MAX-ACCESS  read-only
		STATUS  current
		DESCRIPTION
			"For port configured with OTU2 traffic,
			OTU Background Block Errors increases on defects 
			detected and when BIP errors are less than 15% errored
			blocks received 
			-----------------------------
			ommp101InterfaceNumber:
			1 to 10 - CLIENT-1 to CLIENT-10
			11 - LINE PORT
			-----------------------------
			Values:
			eg: 1234
			-----------------------------"
	::= { ommp101PerformanceEntry 20 }

	ommp101OtuSevereErrorSeconds OBJECT-TYPE
		SYNTAX  DisplayString
		MAX-ACCESS  read-only
		STATUS  current
		DESCRIPTION
			"For port configured with OTU2 traffic,
			OTU Severe Error Seconds increases on defects
			detected and when BIP errors are greater than or
			equal to 15% errored blocks received 
			-----------------------------
			ommp101InterfaceNumber:
			1 to 10 - CLIENT-1 to CLIENT-10
			11 - LINE PORT
			-----------------------------
			Values:
			eg: 1234
			-----------------------------"
	::= { ommp101PerformanceEntry 21 }

	ommp101OtuUnavailableSeconds OBJECT-TYPE
		SYNTAX  DisplayString
		MAX-ACCESS  read-only
		STATUS  current
		DESCRIPTION
			"For port configured with OTU2 traffic,
			OTU Unavailable Seconds increases,
			when 10 consecutive OTU Severe Error seconds
			are detected
			-----------------------------
			ommp101InterfaceNumber:
			1 to 10 - CLIENT-1 to CLIENT-10
			11 - LINE PORT
			-----------------------------
			Values:
			eg: 1234
			-----------------------------"
	::= { ommp101PerformanceEntry 22 }

	ommp101OtuBackgroundBlockErrorRatio OBJECT-TYPE
		SYNTAX  DisplayString
		MAX-ACCESS  read-only
		STATUS  current
		DESCRIPTION
			"For port configured with OTU2 traffic,
			gives OTU Background Block Error Seconds Error Ratio.
			The ratio of BBE in available time to total seconds
			in available time during a fixed measurement interval.
			-----------------------------
			ommp101InterfaceNumber:
			1 to 10 - CLIENT-1 to CLIENT-10
			11 - LINE PORT
			-----------------------------
			Values:
			eg: 1e-3
			-----------------------------"
	::= { ommp101PerformanceEntry 23 }

	ommp101OtuSevereErrorSecondsErrorRatio OBJECT-TYPE
		SYNTAX  DisplayString
		MAX-ACCESS  read-only
		STATUS  current
		DESCRIPTION
			"For port configured with OTU2 traffic,
			gives OTU Severe Error Seconds Error Ratio.
			The ratio of SES in available time to total seconds
			in available time during a fixed measurement interval.
			-----------------------------
			ommp101InterfaceNumber:
			1 to 10 - CLIENT-1 to CLIENT-10
			11 - LINE PORT
			-----------------------------
			Values:
			eg: 1e-3
			-----------------------------"
	::= { ommp101PerformanceEntry 24 }

	ommp101OtuFarEndErrorFreeSeconds OBJECT-TYPE
		SYNTAX  DisplayString
		MAX-ACCESS  read-only
		STATUS  current
		DESCRIPTION
			"For port configured with OTU2 traffic,
			OTU Far end Error Free Seconds, increases when no
			backward errors or defects like BDI or BEI
			are detected in the incoming OTU signal.
			-----------------------------
			ommp101InterfaceNumber:
			1 to 10 - CLIENT-1 to CLIENT-10
			11 - LINE PORT
			-----------------------------
			Values:
			eg: 1234
			-----------------------------"
	::= { ommp101PerformanceEntry 25 }

	ommp101OtuFarEndErrorSeconds OBJECT-TYPE
		SYNTAX  DisplayString
		MAX-ACCESS  read-only
		STATUS  current
		DESCRIPTION
			"For port configured with OTU2 traffic,
			OTU Far End Error Seconds increases on
			detection of defects like BDI in incoming
			OTU signal.
			-----------------------------
			ommp101InterfaceNumber:
			1 to 10 - CLIENT-1 to CLIENT-10
			11 - LINE PORT
			-----------------------------
			Values:
			eg: 1234
			-----------------------------"
	::= { ommp101PerformanceEntry 26 }

	ommp101OtuFarEndBackgroundBlockErrors OBJECT-TYPE
		SYNTAX  DisplayString
		MAX-ACCESS  read-only
		STATUS  current
		DESCRIPTION
			"For port configured with OTU2 traffic,
			OTU Far End Background Block Errors increases when BEI
			errors are less than 15% Errored Blocks in incoming
			OTU signal.
			-----------------------------
			ommp101InterfaceNumber:
			1 to 10 - CLIENT-1 to CLIENT-10
			11 - LINE PORT
			-----------------------------
			Values:
			eg: 1234
			-----------------------------"
	::= { ommp101PerformanceEntry 27 }

	ommp101OtuFarEndSevereErrorSeconds OBJECT-TYPE
		SYNTAX  DisplayString
		MAX-ACCESS  read-only
		STATUS  current
		DESCRIPTION
			"For port configured with OTU2 traffic,
			OTU Far End Severe Error Seconds increases on defects
			like BDI are detected and when BEI errors are greater
			than or equal to 15% Errored Blocks in incoming OTU 
			signal.
			-----------------------------
			ommp101InterfaceNumber:
			1 to 10 - CLIENT-1 to CLIENT-10
			11 - LINE PORT
			-----------------------------
			Values:
			eg: 1234
			-----------------------------"
	::= { ommp101PerformanceEntry 28 }

	ommp101OtuFarEndUnavailableSeconds OBJECT-TYPE
		SYNTAX  DisplayString
		MAX-ACCESS  read-only
		STATUS  current
		DESCRIPTION
			"For port configured with OTU2 traffic,
			OTU Far End Unavailable Seconds increases, 
			after 9 consecutive OTU Far End Severe Error
			seconds are detected
			-----------------------------
			ommp101InterfaceNumber:
			1 to 10 - CLIENT-1 to CLIENT-10
			11 - LINE PORT
			-----------------------------
			Values:
			eg: 1234
			-----------------------------"
	::= { ommp101PerformanceEntry 29 }

	ommp101OtuFarEndBackgroundBlockErrorRatio OBJECT-TYPE
		SYNTAX  DisplayString
		MAX-ACCESS  read-only
		STATUS  current
		DESCRIPTION
			"For port configured with OTU2 traffic,
			gives Otu Far End Background Block Error Ratio.
			The ratio of Far End BBE in available time to tota
			seconds in available time during a fixed measurement
			interval.
			-----------------------------
			ommp101InterfaceNumber:
			1 to 10 - CLIENT-1 to CLIENT-10
			11 - LINE PORT
			-----------------------------
			Values:
			eg: 1e-3
			-----------------------------"
	::= { ommp101PerformanceEntry 30 }

	ommp101OtuFarEndSevereErrorSecondsErrorRatio OBJECT-TYPE
		SYNTAX  DisplayString
		MAX-ACCESS  read-only
		STATUS  current
		DESCRIPTION
			"For port configured with OTU2 traffic,
			gives Otu Far End Severe Error Seconds Error Ratio.
			The ratio of Far End SES in available time to total seconds
			in available time during a fixed measurement interval.
			-----------------------------
			ommp101InterfaceNumber:
			1 to 10 - CLIENT-1 to CLIENT-10
			11 - LINE PORT
			-----------------------------
			Values:
			eg: 1e-3
			-----------------------------"
	::= { ommp101PerformanceEntry 31 }

	ommp101OtuErrorRatio   OBJECT-TYPE
              SYNTAX  DisplayString
              MAX-ACCESS  read-only
              STATUS  current
              DESCRIPTION
			"For port configured with OTU2 traffic,
			gives the OTU Error Ratio for requested port. The ratio  
			of number of error bits to the number of bits received in
			a particular second
			-----------------------------
			ommp101InterfaceNumber:
			1 to 10 - CLIENT-1 to CLIENT-10
			11 - LINE PORT
			-----------------------------	
			Value:
			eg: 4.0
			-----------------------------"
	::= { ommp101PerformanceEntry 32 } 

	ommp101OtuBitErrorRate  OBJECT-TYPE
              SYNTAX  DisplayString
              MAX-ACCESS  read-only
              STATUS  current
              DESCRIPTION
			"For port configured with OTU2 traffic, gives the 
			Bit Error Rate. Bit error rate is the Error ratio 
			multiplied by the OTU2 standard signal 
			data-rate( 10.709225316 Gbps )
			-----------------------------
			ommp101InterfaceNumber:
			1 to 10 - CLIENT-1 to CLIENT-10
			11 - LINE PORT
			-----------------------------	
			Value:
			eg: 4.0
			-----------------------------"
	::= { ommp101PerformanceEntry 33 }

	ommp101OduBitInterleavedParityErrors OBJECT-TYPE
		SYNTAX  DisplayString
		MAX-ACCESS  read-only
		STATUS  current
		DESCRIPTION
			"For port configured with OTU2 traffic,
			ODU-BIP Counter counts the Parity errors evaluated by
			PM field of an OTU2 frame
			-----------------------------
			ommp101InterfaceNumber:
			1 to 10 - CLIENT-1 to CLIENT-10
			11 - LINE PORT
			-----------------------------
			Values:
			eg: 1234
			-----------------------------"
	::= { ommp101PerformanceEntry 35 }

	ommp101OduTcm1BitInterleavedParityErrors OBJECT-TYPE
		SYNTAX  DisplayString
		MAX-ACCESS  read-only
		STATUS  current
		DESCRIPTION
			"For port configured with OTU2 traffic,
			TCM1-BIP Counter counts the Parity errors evaluated by
			TCM1 field in ODU frame
			-----------------------------
			ommp101InterfaceNumber:
			1 to 10 - CLIENT-1 to CLIENT-10
			11 - LINE PORT
			-----------------------------
			Values:
			eg: 1234
			-----------------------------"
	::= { ommp101PerformanceEntry 36 }

	ommp101OduTcm2BitInterleavedParityErrors OBJECT-TYPE
		SYNTAX  DisplayString
		MAX-ACCESS  read-only
		STATUS  current
		DESCRIPTION
			"For port configured with OTU2 traffic,
			TCM2-BIP Counter counts the Parity errors evaluated by
			TCM2 field in ODU frame
			-----------------------------
			ommp101InterfaceNumber:
			1 to 10 - CLIENT-1 to CLIENT-10
			11 - LINE PORT
			-----------------------------
			Values:
			eg: 1234
			-----------------------------"
	::= { ommp101PerformanceEntry 37 }

	ommp101OduTcm3BitInterleavedParityErrors OBJECT-TYPE
		SYNTAX  DisplayString
		MAX-ACCESS  read-only
		STATUS  current
		DESCRIPTION
			"For port configured with OTU2 traffic,
			TCM3-BIP Counter counts the Parity errors evaluated by
			TCM3 field in ODU frame
			-----------------------------
			ommp101InterfaceNumber:
			1 to 10 - CLIENT-1 to CLIENT-10
			11 - LINE PORT
			-----------------------------
			Values:
			eg: 1234
			-----------------------------"
	::= { ommp101PerformanceEntry 38 }

	ommp101OduTcm4BitInterleavedParityErrors OBJECT-TYPE
		SYNTAX  DisplayString
		MAX-ACCESS  read-only
		STATUS  current
		DESCRIPTION
			"For port configured with OTU2 traffic,
			TCM4-BIP Counter counts the Parity errors evaluated by
			TCM4 field in ODU frame
			-----------------------------
			ommp101InterfaceNumber:
			1 to 10 - CLIENT-1 to CLIENT-10
			11 - LINE PORT
			-----------------------------
			Values:
			eg: 1234
			-----------------------------"
	::= { ommp101PerformanceEntry 39 }

	ommp101OduTcm5BitInterleavedParityErrors OBJECT-TYPE
		SYNTAX  DisplayString
		MAX-ACCESS  read-only
		STATUS  current
		DESCRIPTION
			"For port configured with OTU2 traffic,
			TCM5-BIP Counter counts the Parity errors evaluated by
			TCM5 field in ODU frame
			-----------------------------
			ommp101InterfaceNumber:
			1 to 10 - CLIENT-1 to CLIENT-10
			11 - LINE PORT
			-----------------------------
			Values:
			eg: 1234
			-----------------------------"
	::= { ommp101PerformanceEntry 40 }

	ommp101OduTcm6BitInterleavedParityErrors OBJECT-TYPE
		SYNTAX  DisplayString
		MAX-ACCESS  read-only
		STATUS  current
		DESCRIPTION
			"For port configured with OTU2 traffic,
			TCM6-BIP Counter counts the Parity errors evaluated by
			TCM6 field in ODU frame
			-----------------------------
			ommp101InterfaceNumber:
			1 to 10 - CLIENT-1 to CLIENT-10
			11 - LINE PORT
			-----------------------------
			Values:
			eg: 1234
			-----------------------------"
	::= { ommp101PerformanceEntry 41 }

	ommp101OduTcm1IncomingAlignmentErrorSeconds OBJECT-TYPE
		SYNTAX  DisplayString
		MAX-ACCESS  read-only
		STATUS  current
		DESCRIPTION
			"For port configured with OTU2 traffic,
			ODU Incoming Alignment Error Count increases,
			when ODU-TCM1-IAE is detected in that particular second
			of the incoming OTU signal
			-----------------------------
			ommp101InterfaceNumber:
			1 to 10 - CLIENT-1 to CLIENT-10
			11 - LINE PORT
			-----------------------------
			Values:
			eg: 1234
			-----------------------------"
	::= { ommp101PerformanceEntry 42 }

	ommp101OduBackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code.
			-----------------------------
			ommp101InterfaceNumber:
			1 to 10 - CLIENT-1 to CLIENT-10
			11 - LINE PORT
			-----------------------------
			Values:
			eg: 1234
			-----------------------------"
	::= { ommp101PerformanceEntry 43 }

	ommp101OduTcm1BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at
			TCM1 level.
			-----------------------------
			ommp101InterfaceNumber:
			1 to 10 - CLIENT-1 to CLIENT-10
			11 - LINE PORT
			-----------------------------
			Values:
			eg: 1234
			-----------------------------"
	::= { ommp101PerformanceEntry 44 }

	ommp101OduTcm2BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at
			TCM2 level.
			-----------------------------
			ommp101InterfaceNumber:
			1 to 10 - CLIENT-1 to CLIENT-10
			11 - LINE PORT
			-----------------------------
			Values:
			eg: 1234
			-----------------------------"
	::= { ommp101PerformanceEntry 45 }

	ommp101OduTcm3BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at
			TCM3 level.
			-----------------------------
			ommp101InterfaceNumber:
			1 to 10 - CLIENT-1 to CLIENT-10
			11 - LINE PORT
			-----------------------------
			Values:
			eg: 1234
			-----------------------------"
	::= { ommp101PerformanceEntry 46 }

	ommp101OduTcm4BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at
			TCM4 level.
			-----------------------------
			ommp101InterfaceNumber:
			1 to 10 - CLIENT-1 to CLIENT-10
			11 - LINE PORT
			-----------------------------
			Values:
			eg: 1234
			-----------------------------"
	::= { ommp101PerformanceEntry 47 }

	ommp101OduTcm5BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at
			TCM5 level.
			-----------------------------
			ommp101InterfaceNumber:
			1 to 10 - CLIENT-1 to CLIENT-10
			11 - LINE PORT
			-----------------------------
			Values:
			eg: 1234
			-----------------------------"
	::= { ommp101PerformanceEntry 48 }

	ommp101OduTcm6BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at
			TCM6 level.
			-----------------------------
			ommp101InterfaceNumber:
			1 to 10 - CLIENT-1 to CLIENT-10
			11 - LINE PORT
			-----------------------------
			Values:
			eg: 1234
			-----------------------------"
	::= { ommp101PerformanceEntry 49 }

	ommp101OduTcm1BackwardIncomingAlignmentErrorSeconds OBJECT-TYPE
		SYNTAX  DisplayString
		MAX-ACCESS  read-only
		STATUS  current
		DESCRIPTION
			"For port configured with OTU2 traffic,
			ODU Backward Incoming Alignment Error Count increases,
			when ODU-TCM1-BIAE is detected in that particular second
			of the incoming OTU signal
			-----------------------------
			ommp101InterfaceNumber:
			1 to 10 - CLIENT-1 to CLIENT-10
			11 - LINE PORT
			-----------------------------
			Values:
			eg: 1234
			-----------------------------"
	::= { ommp101PerformanceEntry 50 }

	ommp101OduDelayMeasurement OBJECT-TYPE
		SYNTAX  DisplayString
		MAX-ACCESS  read-only
		STATUS  current
		DESCRIPTION
			"For port configured with OTU2 traffic,
			gives delay measurement of ODU frame
			-----------------------------
			ommp101InterfaceNumber:
			1 to 10 - CLIENT-1 to CLIENT-10
			11 - LINE PORT
			-----------------------------
			Values:
			eg: Reserved for further study
			-----------------------------"
	::= { ommp101PerformanceEntry 51 }

	ommp101OduErrorFreeSeconds OBJECT-TYPE
		SYNTAX  DisplayString
		MAX-ACCESS  read-only
		STATUS  current
		DESCRIPTION
			"For port configured with OTU2 traffic,
			ODU Error Free Seconds increases,
			when no BIP errors or defects are detected at the
			path monitoring level
			-----------------------------
			ommp101InterfaceNumber:
			1 to 10 - CLIENT-1 to CLIENT-10
			11 - LINE PORT
			-----------------------------
			Values:
			eg: 1234
			-----------------------------"
	::= { ommp101PerformanceEntry 52 }

	ommp101OduErrorSeconds OBJECT-TYPE
		SYNTAX  DisplayString
		MAX-ACCESS  read-only
		STATUS  current
		DESCRIPTION
			"For port configured with OTU2 traffic,
			ODU Error Seconds increases on defects detected at the
			path monitoring level
			-----------------------------
			ommp101InterfaceNumber:
			1 to 10 - CLIENT-1 to CLIENT-10
			11 - LINE PORT
			-----------------------------
			Values:
			eg: 1234
			-----------------------------"
	::= { ommp101PerformanceEntry 53 }

	ommp101OduBackgroundBlockErrors OBJECT-TYPE
		SYNTAX  DisplayString
		MAX-ACCESS  read-only
		STATUS  current
		DESCRIPTION
			"For port configured with OTU2 traffic,
			ODU Background Block Errors increases on defects 
			detected and when BIP errors are less than 15% 
			Errored Blocks in incoming OTU signal.
			-----------------------------
			ommp101InterfaceNumber:
			1 to 10 - CLIENT-1 to CLIENT-10
			11 - LINE PORT
			-----------------------------
			Values:
			eg: 1234
			-----------------------------"
	::= { ommp101PerformanceEntry 54 }

	ommp101OduSevereErrorSeconds OBJECT-TYPE
		SYNTAX  DisplayString
		MAX-ACCESS  read-only
		STATUS  current
		DESCRIPTION
			"For port configured with OTU2 traffic,
			ODU Severe Error Seconds increases on defects detected
			and when BIP errors are more than 15% Errored Blocks
			in incoming OTU signal.
			-----------------------------
			ommp101InterfaceNumber:
			1 to 10 - CLIENT-1 to CLIENT-10
			11 - LINE PORT
			-----------------------------
			Values:
			eg: 1234
			-----------------------------"
	::= { ommp101PerformanceEntry 55 }

	ommp101OduUnavailableSeconds OBJECT-TYPE
		SYNTAX  DisplayString
		MAX-ACCESS  read-only
		STATUS  current
		DESCRIPTION
			"For port configured with OTU2 traffic,
			ODU Unavailable Seconds increases, when 10 consecutive
			Severe ODU Error seconds are detected
			-----------------------------
			ommp101InterfaceNumber:
			1 to 10 - CLIENT-1 to CLIENT-10
			11 - LINE PORT
			-----------------------------
			Values:
			eg: 1234
			-----------------------------"
	::= { ommp101PerformanceEntry 56 }

	ommp101OduBackgroundBlockErrorRatio OBJECT-TYPE
		SYNTAX  DisplayString
		MAX-ACCESS  read-only
		STATUS  current
		DESCRIPTION
			"For port configured with OTU2 traffic,
			gives ODU Background Block Error Ratio i.e.
			the ratio of BBE in available time to total seconds
			in available time during a fixed measurement interval.
			-----------------------------
			ommp101InterfaceNumber:
			1 to 10 - CLIENT-1 to CLIENT-10
			11 - LINE PORT
			-----------------------------
			Values:
			eg: 1e-3
			-----------------------------"
	::= { ommp101PerformanceEntry 57 }

	ommp101OduSevereErrorSecondsErrorRatio OBJECT-TYPE
		SYNTAX  DisplayString
		MAX-ACCESS  read-only
		STATUS  current
		DESCRIPTION
			"For port configured with OTU2 traffic,
			gives ODU Severe Error Seconds Error Ratio i.e.
			the ratio of SES in available time to total seconds
			in available time during a fixed measurement interval.
			-----------------------------
			ommp101InterfaceNumber:
			1 to 10 - CLIENT-1 to CLIENT-10
			11 - LINE PORT
			-----------------------------
			Values:
			eg: 1e-3
			-----------------------------"
	::= { ommp101PerformanceEntry 58 }

	ommp101OduFarEndErrorFreeSeconds OBJECT-TYPE
		SYNTAX  DisplayString
		MAX-ACCESS  read-only
		STATUS  current
		DESCRIPTION
			"For port configured with OTU2 traffic,
			ODU Far end Error Free Seconds, increases when no
			far end errors or defects are detected
			-----------------------------
			ommp101InterfaceNumber:
			1 to 10 - CLIENT-1 to CLIENT-10
			11 - LINE PORT
			-----------------------------
			Values:
			eg: 1234
			-----------------------------"
	::= { ommp101PerformanceEntry 59 }

	ommp101OduFarEndErrorSeconds OBJECT-TYPE
		SYNTAX  DisplayString
		MAX-ACCESS  read-only
		STATUS  current
		DESCRIPTION
			"For port configured with OTU2 traffic,
			ODU Far End Error Seconds increases on detection of
			defects like BDI and BEI at path monitoring level
			-----------------------------
			ommp101InterfaceNumber:
			1 to 10 - CLIENT-1 to CLIENT-10
			11 - LINE PORT
			-----------------------------
			Values:
			eg: 1234
			-----------------------------"
	::= { ommp101PerformanceEntry 60 }

	ommp101OduFarEndBackgroundBlockErrors OBJECT-TYPE
		SYNTAX  DisplayString
		MAX-ACCESS  read-only
		STATUS  current
		DESCRIPTION
			"For port configured with OTU2 traffic,
			ODU Far End Background Block Errors increases when
			BEI errors are less than 15% Errored Blocks in
			incoming OTU signal.
			-----------------------------
			ommp101InterfaceNumber:
			1 to 10 - CLIENT-1 to CLIENT-10
			11 - LINE PORT
			-----------------------------
			Values:
			eg: 1234
			-----------------------------"
	::= { ommp101PerformanceEntry 61 }

	ommp101OduFarEndSevereErrorSeconds OBJECT-TYPE
		SYNTAX  DisplayString
		MAX-ACCESS  read-only
		STATUS  current
		DESCRIPTION
			"For port configured with OTU2 traffic,
			ODU Far End Severe Error Seconds increases on defects
			like BDI are detected and when BEI errors are more than
			15% Errored Blocks in incoming OTU signal.
			-----------------------------
			ommp101InterfaceNumber:
			1 to 10 - CLIENT-1 to CLIENT-10
			11 - LINE PORT
			-----------------------------
			Values:
			eg: 1234
			-----------------------------"
	::= { ommp101PerformanceEntry 62 }

	ommp101OduFarEndUnavailableSeconds OBJECT-TYPE
		SYNTAX  DisplayString
		MAX-ACCESS  read-only
		STATUS  current
		DESCRIPTION
			"For port configured with OTU2 traffic,
			ODU Far End Unavailable Seconds increases, when 10
			consecutive OTU Far End Error seconds are detected
			-----------------------------
			ommp101InterfaceNumber:
			1 to 10 - CLIENT-1 to CLIENT-10
			11 - LINE PORT
			-----------------------------
			Values:
			eg: 1234
			-----------------------------"
	::= { ommp101PerformanceEntry 63 }

	ommp101OduFarEndBackgroundBlockErrorRatio OBJECT-TYPE
		SYNTAX  DisplayString
		MAX-ACCESS  read-only
		STATUS  current
		DESCRIPTION
			"For port configured with OTU2 traffic,
			gives ODU Far End Background Block Error Ratio i.e.
			the ratio of Far End BBE in available time to total
			seconds	in available time during a fixed measurement
			interval.
			-----------------------------
			ommp101InterfaceNumber:
			1 to 10 - CLIENT-1 to CLIENT-10
			11 - LINE PORT
			-----------------------------
			Values:
			eg: 1e-3
			-----------------------------"
	::= { ommp101PerformanceEntry 64 }

	ommp101OduFarEndSevereErrorSecondsErrorRatio OBJECT-TYPE
		SYNTAX  DisplayString
		MAX-ACCESS  read-only
		STATUS  current
		DESCRIPTION
			"For port configured with OTU2 traffic,
			gives ODU Far End Severe Error Seconds Error Ratio i.e.
			The ratio of Far End SES in available time to total
			seconds in available time during a fixed measurement
			interval.
			-----------------------------
			ommp101InterfaceNumber:
			1 to 10 - CLIENT-1 to CLIENT-10
			11 - LINE PORT
			-----------------------------
			Values:
			eg: 1e-3
			-----------------------------"
	::= { ommp101PerformanceEntry 65 }

	ommp101SdhRsB1BitInterleavedParityErrors OBJECT-TYPE
		SYNTAX  DisplayString
		MAX-ACCESS  read-only
		STATUS  current
		DESCRIPTION
			"For port configured with STM-16 traffic,
			SDH B1 BIP counter counts the Parity errors evaluated
			from byte B1 of the STM frame
			-----------------------------
			ommp101InterfaceNumber:
			1 to 10 - CLIENT-1 to CLIENT-10
			-----------------------------
			Values:
			eg: 1234
			-----------------------------"
	::= { ommp101PerformanceEntry 66 }

	ommp101SdhMsB2BitInterleavedParityErrors OBJECT-TYPE
		SYNTAX  DisplayString
		MAX-ACCESS  read-only
		STATUS  current
		DESCRIPTION
			"For port configured with STM-16 traffic,
			SDH B2 BIP counter counts the Parity errors evaluated 
			from byte B2 of the STM frame
			-----------------------------
			ommp101InterfaceNumber:
			1 to 10 - CLIENT-1 to CLIENT-10
			-----------------------------
			Values:
			eg: 1234
			-----------------------------"
	::= { ommp101PerformanceEntry 67 }

	ommp101SdhMsRemoteErrorIndicationErrorCount OBJECT-TYPE
		SYNTAX  DisplayString
		MAX-ACCESS  read-only
		STATUS  current
		DESCRIPTION
			"For port configured with STM-16 traffic,
			SDH MS-REI error count increases when
			MS-REI is detected for that particular second
			in incoming SDH signal.
			-----------------------------
			ommp101InterfaceNumber:
			1 to 10 - CLIENT-1 to CLIENT-10
			-----------------------------
			Values:
			eg: 1234
			-----------------------------"
	::= { ommp101PerformanceEntry 68 }

	ommp101SdhErrorFreeSeconds OBJECT-TYPE
		SYNTAX  DisplayString
		MAX-ACCESS  read-only
		STATUS  current
		DESCRIPTION
			"For port configured with STM-16 traffic,
			SDH Error Free Seconds increases when no BIP
			errors or no defects are detected in incoming
			SDH signal.
			-----------------------------
			ommp101InterfaceNumber:
			1 to 10 - CLIENT-1 to CLIENT-10
			-----------------------------
			Values:
			eg: 1234
			-----------------------------"
	::= { ommp101PerformanceEntry 70 }

	ommp101SdhErrorSeconds OBJECT-TYPE
		SYNTAX  DisplayString
		MAX-ACCESS  read-only
		STATUS  current
		DESCRIPTION
			"For port configured with STM-16 traffic,
			SDH Error Seconds increases on detection of BIP errors
			and defects like B1 errors, LOS, LOF in incoming SDH
			signal.
			-----------------------------
			ommp101InterfaceNumber:
			1 to 10 - CLIENT-1 to CLIENT-10
			-----------------------------
			Values:
			eg: 1234
			-----------------------------"
	::= { ommp101PerformanceEntry 71 }

	ommp101SdhBackgroundBlockErrors OBJECT-TYPE
		SYNTAX  DisplayString
		MAX-ACCESS  read-only
		STATUS  current
		DESCRIPTION
			"For port configured with STM-16 traffic,
			SDH Background Block Errors increases on defects 
			detected and when BIP errors are less than 30%
			errored blocks in the incoming SDH signal.
			-----------------------------
			ommp101InterfaceNumber:
			1 to 10 - CLIENT-1 to CLIENT-10
			-----------------------------
			Values:
			eg: 1234
			-----------------------------"
	::= { ommp101PerformanceEntry 72 }

	ommp101SdhSevereErrorSeconds OBJECT-TYPE
		SYNTAX  DisplayString
		MAX-ACCESS  read-only
		STATUS  current
		DESCRIPTION
			"For port configured with STM-16 traffic,
			SDH Severe Error Secodns increases on defects 
			detected and when BIP errors are greater than or equal
			to 30% errored blocks in the incoming SDH signal.
			-----------------------------
			ommp101InterfaceNumber:
			1 to 10 - CLIENT-1 to CLIENT-10
			-----------------------------
			Values:
			eg: 1234
			-----------------------------"
	::= { ommp101PerformanceEntry 73 }

	ommp101SdhUnavailableSeconds OBJECT-TYPE
		SYNTAX  DisplayString
		MAX-ACCESS  read-only
		STATUS  current
		DESCRIPTION
			"For port configured with STM-16 traffic,
			SDH Unavailable Seconds increases, when 10 consecutive
			Severe Error seconds are detected
			-----------------------------
			ommp101InterfaceNumber:
			1 to 10 - CLIENT-1 to CLIENT-10
			-----------------------------
			Values:
			eg: 1234
			-----------------------------"
	::= { ommp101PerformanceEntry 74 }

	ommp101SdhErrorSecondsErrorRatio OBJECT-TYPE
		SYNTAX  DisplayString
		MAX-ACCESS  read-only
		STATUS  current
		DESCRIPTION
			"For port configured with STM-16 traffic,
			gives SDH Error Seconds Error Ratio.
			The ratio of ES in available time to total seconds
			in available time during a fixed measurement interval.
			-----------------------------
			ommp101InterfaceNumber:
			1 to 10 - CLIENT-1 to CLIENT-10
			-----------------------------
			Values:
			eg: 1234
			-----------------------------"
	::= { ommp101PerformanceEntry 75 }

	ommp101SdhBackgroundBlockErrorRatio OBJECT-TYPE
		SYNTAX  DisplayString
		MAX-ACCESS  read-only
		STATUS  current
		DESCRIPTION
			"For port configured with STM-16 traffic,
			gives SDH Background Block Error Ratio.
			The ratio of BBE in available time to total seconds
			in available time during a fixed measurement interval.
			-----------------------------
			ommp101InterfaceNumber:
			1 to 10 - CLIENT-1 to CLIENT-10
			-----------------------------
			Values:
			eg: 1234
			-----------------------------"
	::= { ommp101PerformanceEntry 76 }

	ommp101SdhSevereErrorSecondsErrorRatio OBJECT-TYPE
		SYNTAX  DisplayString
		MAX-ACCESS  read-only
		STATUS  current
		DESCRIPTION
			"For port configured with STM-16 traffic,
			gives SDH Severe Error Seconds Error Ratio.
			The ratio of SES in available time to total seconds
			in available time during a fixed measurement interval.
			-----------------------------
			ommp101InterfaceNumber:
			1 to 10 - CLIENT-1 to CLIENT-10
			-----------------------------
			Values:
			eg: 1234
			-----------------------------"
	::= { ommp101PerformanceEntry 77 }

	ommp101EthernetTerminatedFramesTransmitted OBJECT-TYPE
		SYNTAX  DisplayString
		MAX-ACCESS  read-only
		STATUS  current
		DESCRIPTION
			"For port configured with LAN10G traffic,
			gives the number of Ethernet frame transmitted.
			-----------------------------
			ommp101InterfaceNumber:
			1 to 10 - CLIENT-1 to CLIENT-10
			-----------------------------
			Values:
			eg: 1234
			-----------------------------"
	::= { ommp101PerformanceEntry 78 }

	ommp101EthernetTerminatedFramesReceived OBJECT-TYPE
		SYNTAX  DisplayString
		MAX-ACCESS  read-only
		STATUS  current
		DESCRIPTION
			"For port configured with LAN10G  traffic,
			gives the number of Ethernet frame received.
			-----------------------------
			ommp101InterfaceNumber:
			1 to 10 - CLIENT-1 to CLIENT-10
			-----------------------------
			Values:
			eg: 1234
			-----------------------------"
	::= { ommp101PerformanceEntry 79 }

	ommp101EthernetTerminatedVlanTaggedFramesTransmitted OBJECT-TYPE
		SYNTAX  DisplayString
		MAX-ACCESS  read-only
		STATUS  current
		DESCRIPTION
			"For port configured with LAN10G traffic,
			gives the number of Ethernet Vlan tagged frames transmitted.
			-----------------------------
			ommp101InterfaceNumber:
			1 to 10 - CLIENT-1 to CLIENT-10
			-----------------------------
			Values:
			eg: 1234
			-----------------------------"
	::= { ommp101PerformanceEntry 80 }

	ommp101EthernetTerminatedVlanTaggedFramesReceived OBJECT-TYPE
		SYNTAX  DisplayString
		MAX-ACCESS  read-only
		STATUS  current
		DESCRIPTION
			"For port configured with LAN10G  traffic,
			gives the number of Ethernet Vlan tagged frames received.
			-----------------------------
			ommp101InterfaceNumber:
			1 to 10 - CLIENT-1 to CLIENT-10
			-----------------------------
			Values:
			eg: 1234
			-----------------------------"
	::= { ommp101PerformanceEntry 81 }

	ommp101EthernetTerminatedUnicastFramesTransmitted OBJECT-TYPE
		SYNTAX  DisplayString
		MAX-ACCESS  read-only
		STATUS  current
		DESCRIPTION
			"For port configured with LAN10G traffic,
			gives the number of Ethernet Unicast frames transmitted.
			-----------------------------
			ommp101InterfaceNumber:
			1 to 10 - CLIENT-1 to CLIENT-10
			-----------------------------
			Values:
			eg: 1234
			-----------------------------"
	::= { ommp101PerformanceEntry 82 }

	ommp101EthernetTerminatedUnicastFramesReceived OBJECT-TYPE
		SYNTAX  DisplayString
		MAX-ACCESS  read-only
		STATUS  current
		DESCRIPTION
			"For port configured with LAN10G  traffic,
			gives the number of Ethernet Unicast frames received.
			-----------------------------
			ommp101InterfaceNumber:
			1 to 10 - CLIENT-1 to CLIENT-10
			-----------------------------
			Values:
			eg: 1234
			-----------------------------"
	::= { ommp101PerformanceEntry 83 }

	ommp101EthernetTerminatedBroadcastFramesTransmitted OBJECT-TYPE
		SYNTAX  DisplayString
		MAX-ACCESS  read-only
		STATUS  current
		DESCRIPTION
			"For port configured with LAN10G traffic,
			gives the number of Ethernet Broadcast frame transmitted.
			-----------------------------
			ommp101InterfaceNumber:
			1 to 10 - CLIENT-1 to CLIENT-10
			-----------------------------
			Values:
			eg: 1234
			-----------------------------"
	::= { ommp101PerformanceEntry 84 }

	ommp101EthernetTerminatedBroadcastFramesReceived OBJECT-TYPE
		SYNTAX  DisplayString
		MAX-ACCESS  read-only
		STATUS  current
		DESCRIPTION
			"For port configured with LAN10G  traffic,
			gives the number of Ethernet broadcast frame received.
			-----------------------------
			ommp101InterfaceNumber:
			1 to 10 - CLIENT-1 to CLIENT-10
			-----------------------------
			Values:
			eg: 1234
			-----------------------------"
	::= { ommp101PerformanceEntry 85 }

	ommp101EthernetTerminatedMulticastFramesTransmitted OBJECT-TYPE
		SYNTAX  DisplayString
		MAX-ACCESS  read-only
		STATUS  current
		DESCRIPTION
			"For port configured with LAN10G traffic,
			gives the number of Ethernet Multicast frame transmitted.
			-----------------------------
			ommp101InterfaceNumber:
			1 to 10 - CLIENT-1 to CLIENT-10
			-----------------------------
			Values:
			eg: 1234
			-----------------------------"
	::= { ommp101PerformanceEntry 86 }

	ommp101EthernetTerminatedMulticastFramesReceived OBJECT-TYPE
		SYNTAX  DisplayString
		MAX-ACCESS  read-only
		STATUS  current
		DESCRIPTION
			"For port configured with LAN10G  traffic,
			gives the number of Ethernet Multicast frame received.
			-----------------------------
			ommp101InterfaceNumber:
			1 to 10 - CLIENT-1 to CLIENT-10
			-----------------------------
			Values:
			eg: 1234
			-----------------------------"
	::= { ommp101PerformanceEntry 87 }

	ommp101EthernetTerminatedOverSizeFramesTransmitted OBJECT-TYPE
		SYNTAX  DisplayString
		MAX-ACCESS  read-only
		STATUS  current
		DESCRIPTION
			"For port configured with LAN10G traffic,
			gives the number of Ethernet Oversize frame transmitted.
			-----------------------------
			ommp101InterfaceNumber:
			1 to 10 - CLIENT-1 to CLIENT-10
			-----------------------------
			Values:
			eg: 1234
			-----------------------------"
	::= { ommp101PerformanceEntry 88 }

	ommp101EthernetTerminatedOverSizeFramesReceived OBJECT-TYPE
		SYNTAX  DisplayString
		MAX-ACCESS  read-only
		STATUS  current
		DESCRIPTION
			"For port configured with LAN10G  traffic,
			gives the number of Ethernet Oversizeframe received.
			-----------------------------
			ommp101InterfaceNumber:
			1 to 10 - CLIENT-1 to CLIENT-10
			-----------------------------
			Values:
			eg: 1234
			-----------------------------"
	::= { ommp101PerformanceEntry 89 }

	ommp101EthernetTerminatedUnderSizeFramesTransmitted OBJECT-TYPE
		SYNTAX  DisplayString
		MAX-ACCESS  read-only
		STATUS  current
		DESCRIPTION
			"For port configured with LAN10G traffic,
			gives the number of Ethernet UnderSize frames transmitted.
			-----------------------------
			ommp101InterfaceNumber:
			1 to 10 - CLIENT-1 to CLIENT-10
			-----------------------------
			Values:
			eg: 1234
			-----------------------------"
	::= { ommp101PerformanceEntry 90 }

	ommp101EthernetTerminatedUnderSizeFramesReceived OBJECT-TYPE
		SYNTAX  DisplayString
		MAX-ACCESS  read-only
		STATUS  current
		DESCRIPTION
			"For port configured with LAN10G  traffic,
			gives the number of Ethernet Undersize frames received.
			-----------------------------
			ommp101InterfaceNumber:
			1 to 10 - CLIENT-1 to CLIENT-10
			-----------------------------
			Values:
			eg: 1234
			-----------------------------"
	::= { ommp101PerformanceEntry 91 }

	ommp101EthernetTerminatedFrameCheckSequenceErrorsTransmitted OBJECT-TYPE
		SYNTAX  DisplayString
		MAX-ACCESS  read-only
		STATUS  current
		DESCRIPTION
			"For port configured with LAN10G traffic,
			gives the number of Ethernet FCS Errors transmitted.
			-----------------------------
			ommp101InterfaceNumber:
			1 to 10 - CLIENT-1 to CLIENT-10
			-----------------------------
			Values:
			eg: 1234
			-----------------------------"
	::= { ommp101PerformanceEntry 92 }

	ommp101EthernetTerminatedFrameCheckSequenceErrorsReceived OBJECT-TYPE
		SYNTAX  DisplayString
		MAX-ACCESS  read-only
		STATUS  current
		DESCRIPTION
			"For port configured with LAN10G  traffic,
			gives the number of Ethernet  FCS Errors received.
			-----------------------------
			ommp101InterfaceNumber:
			1 to 10 - CLIENT-1 to CLIENT-10
			-----------------------------
			Values:
			eg: 1234
			-----------------------------"
	::= { ommp101PerformanceEntry 93 }

	ommp101EthernetTerminatedControlFramesTransmitted OBJECT-TYPE
		SYNTAX  DisplayString
		MAX-ACCESS  read-only
		STATUS  current
		DESCRIPTION
			"For port configured with LAN10G traffic,
			gives the number of Ethernet Control frame transmitted.
			-----------------------------
			ommp101InterfaceNumber:
			1 to 10 - CLIENT-1 to CLIENT-10
			-----------------------------
			Values:
			eg: 1234
			-----------------------------"
	::= { ommp101PerformanceEntry 94 }

	ommp101EthernetTerminatedControlFramesReceived OBJECT-TYPE
		SYNTAX  DisplayString
		MAX-ACCESS  read-only
		STATUS  current
		DESCRIPTION
			"For port configured with LAN10G  traffic,
			gives the number of Ethernet control frame received.
			-----------------------------
			ommp101InterfaceNumber:
			1 to 10 - CLIENT-1 to CLIENT-10
			-----------------------------
			Values:
			eg: 1234
			-----------------------------"
	::= { ommp101PerformanceEntry 95 }

	ommp101EthernetStatsPkts64OctsTransmitted OBJECT-TYPE
		SYNTAX  DisplayString
		MAX-ACCESS  read-only
		STATUS  current
		DESCRIPTION
			"For port configured with LAN10G  traffic,
			gives the number of Ethernet StatsPkts64Octs Transmitted.
			-----------------------------
			ommp101InterfaceNumber:
			1 to 10 - CLIENT-1 to CLIENT-10
			-----------------------------
			Values:
			eg: 1234
			-----------------------------"
	::= { ommp101PerformanceEntry 96 }

	ommp101EthernetStatsPkts64OctsReceived OBJECT-TYPE
		SYNTAX  DisplayString
		MAX-ACCESS  read-only
		STATUS  current
		DESCRIPTION
			"For port configured with LAN10G  traffic,
			gives the number of Ethernet StatsPkts64Octs received.
			-----------------------------
			ommp101InterfaceNumber:
			1 to 10 - CLIENT-1 to CLIENT-10
			-----------------------------
			Values:
			eg: 1234
			-----------------------------"
	::= { ommp101PerformanceEntry 97 }

	ommp101EthernetStatsPkts65to127OctsTransmitted OBJECT-TYPE
		SYNTAX  DisplayString
		MAX-ACCESS  read-only
		STATUS  current
		DESCRIPTION
			"For port configured with LAN10G  traffic,
			gives the number of ethernet StatsPkts65to127Octs Transmitted.
			-----------------------------
			ommp101InterfaceNumber:
			1 to 10 - CLIENT-1 to CLIENT-10
			-----------------------------
			Values:
			eg: 1234
			-----------------------------"
	::= { ommp101PerformanceEntry 98 }

	ommp101EthernetStatsPkts65to127OctsReceived OBJECT-TYPE
		SYNTAX  DisplayString
		MAX-ACCESS  read-only
		STATUS  current
		DESCRIPTION
			"For port configured with LAN10G  traffic,
			gives the number of Ethernet StatsPkts65to127Octs received.
			-----------------------------
			ommp101InterfaceNumber:
			1 to 10 - CLIENT-1 to CLIENT-10
			-----------------------------
			Values:
			eg: 1234
			-----------------------------"
	::= { ommp101PerformanceEntry 99 }

	ommp101EthernetStatsPkts128to255OctsTransmitted OBJECT-TYPE
		SYNTAX  DisplayString
		MAX-ACCESS  read-only
		STATUS  current
		DESCRIPTION
			"For port configured with LAN10G  traffic,
			gives the number of Ethernet StatsPkts128to255Octs Transmitted.
			-----------------------------
			ommp101InterfaceNumber:
			1 to 10 - CLIENT-1 to CLIENT-10
			-----------------------------
			Values:
			eg: 1234
			-----------------------------"
	::= { ommp101PerformanceEntry 100 }

	ommp101EthernetStatsPkts128to255OctsReceived OBJECT-TYPE
		SYNTAX  DisplayString
		MAX-ACCESS  read-only
		STATUS  current
		DESCRIPTION
			"For port configured with LAN10G  traffic,
			gives the number of Ethernet StatsPkts128to255Octs received.
			-----------------------------
			ommp101InterfaceNumber:
			1 to 10 - CLIENT-1 to CLIENT-10
			-----------------------------
			Values:
			eg: 1234
			-----------------------------"
	::= { ommp101PerformanceEntry 101 }

	ommp101EthernetStatsPkts256to511OctsTransmitted OBJECT-TYPE
		SYNTAX  DisplayString
		MAX-ACCESS  read-only
		STATUS  current
		DESCRIPTION
			"For port configured with LAN10G  traffic,
			gives the number of ethernet StatsPkts256to511Octs Transmitted.
			-----------------------------
			ommp101InterfaceNumber:
			1 to 10 - CLIENT-1 to CLIENT-10
			-----------------------------
			Values:
			eg: 1234
			-----------------------------"
	::= { ommp101PerformanceEntry 102 }

	ommp101EthernetStatsPkts256to511OctsReceived OBJECT-TYPE
		SYNTAX  DisplayString
		MAX-ACCESS  read-only
		STATUS  current
		DESCRIPTION
			"For port configured with LAN10G  traffic,
			gives the number of Ethernet StatsPkts256to511Octs received.
			-----------------------------
			ommp101InterfaceNumber:
			1 to 10 - CLIENT-1 to CLIENT-10
			-----------------------------
			Values:
			eg: 1234
			-----------------------------"
	::= { ommp101PerformanceEntry 103 }

	ommp101EthernetStatsPkts512to1023OctsTransmitted OBJECT-TYPE
		SYNTAX  DisplayString
		MAX-ACCESS  read-only
		STATUS  current
		DESCRIPTION
			"For port configured with LAN10G  traffic,
			gives the number of Ethernet StatsPkts512to1023Octs Transmitted.
			-----------------------------
			ommp101InterfaceNumber:
			1 to 10 - CLIENT-1 to CLIENT-10
			-----------------------------
			Values:
			eg: 1234
			-----------------------------"
	::= { ommp101PerformanceEntry 104 }

	ommp101EthernetStatsPkts512to1023OctsReceived OBJECT-TYPE
		SYNTAX  DisplayString
		MAX-ACCESS  read-only
		STATUS  current
		DESCRIPTION
			"For port configured with LAN10G  traffic,
			gives the number of Ethernet StatsPkts512to1023Octs received.
			-----------------------------
			ommp101InterfaceNumber:
			1 to 10 - CLIENT-1 to CLIENT-10
			-----------------------------
			Values:
			eg: 1234
			-----------------------------"
	::= { ommp101PerformanceEntry 105 }

	ommp101EthernetStatsPkts1024to1518OctsTransmitted OBJECT-TYPE
		SYNTAX  DisplayString
		MAX-ACCESS  read-only
		STATUS  current
		DESCRIPTION
			"For port configured with LAN10G  traffic,
			gives the number of ethernet StatsPkts1024to1518Octs Transmitted.
			-----------------------------
			ommp101InterfaceNumber:
			1 to 10 - CLIENT-1 to CLIENT-10
			-----------------------------
			Values:
			eg: 1234
			-----------------------------"
	::= { ommp101PerformanceEntry 106 }

	ommp101EthernetStatsPkts1024to1518OctsReceived OBJECT-TYPE
		SYNTAX  DisplayString
		MAX-ACCESS  read-only
		STATUS  current
		DESCRIPTION
			"For port configured with LAN10G  traffic,
			gives the number of Ethernet StatsPkts1024to1518Octs received.
			-----------------------------
			ommp101InterfaceNumber:
			1 to 10 - CLIENT-1 to CLIENT-10
			-----------------------------
			Values:
			eg: 1234
			-----------------------------"
	::= { ommp101PerformanceEntry 107 }

	ommp101EthernetStatsPkts1519toMaxOctsTransmitted OBJECT-TYPE
		SYNTAX  DisplayString
		MAX-ACCESS  read-only
		STATUS  current
		DESCRIPTION
			"For port configured with LAN10G  traffic,
			gives the number of Ethernet StatsPkts1519toMaxOcts Transmitted.
			-----------------------------
			ommp101InterfaceNumber:
			1 to 10 - CLIENT-1 to CLIENT-10
			-----------------------------
			Values:
			eg: 1234
			-----------------------------"
	::= { ommp101PerformanceEntry 108 }

	ommp101EthernetStatsPkts1519toMaxOctsReceived OBJECT-TYPE
		SYNTAX  DisplayString
		MAX-ACCESS  read-only
		STATUS  current
		DESCRIPTION
			"For port configured with LAN10G  traffic,
			gives the number of Ethernet StatsPkts1519toMaxOcts received.
			-----------------------------
			ommp101InterfaceNumber:
			1 to 10 - CLIENT-1 to CLIENT-10
			-----------------------------
			Values:
			eg: 1234
			-----------------------------"
	::= { ommp101PerformanceEntry 109 }

	ommp101EthernetStatsJabberTransmitted OBJECT-TYPE
		SYNTAX  DisplayString
		MAX-ACCESS  read-only
		STATUS  current
		DESCRIPTION
			"For port configured with LAN10G  traffic,
			gives the number of Ethernet StatsJabber Transmitted.
			-----------------------------
			ommp101InterfaceNumber:
			1 to 10 - CLIENT-1 to CLIENT-10
			-----------------------------
			Values:
			eg: 1234
			-----------------------------"
	::= { ommp101PerformanceEntry 110 }

	ommp101EthernetStatsJabberReceived OBJECT-TYPE
		SYNTAX  DisplayString
		MAX-ACCESS  read-only
		STATUS  current
		DESCRIPTION
			"For port configured with LAN10G  traffic,
			gives the number of Ethernet StatsJabber received.
			-----------------------------
			ommp101InterfaceNumber:
			1 to 10 - CLIENT-1 to CLIENT-10
			-----------------------------
			Values:
			eg: 1234
			-----------------------------"
	::= { ommp101PerformanceEntry 112 }

	ommp101EthernetStatsFragmentsTransmitted OBJECT-TYPE
		SYNTAX  DisplayString
		MAX-ACCESS  read-only
		STATUS  current
		DESCRIPTION
			"For port configured with LAN10G  traffic,
			gives the number of Ethernet StatsFragments Transmitted.
			-----------------------------
			ommp101InterfaceNumber:
			1 to 10 - CLIENT-1 to CLIENT-10
			-----------------------------
			Values:
			eg: 1234
			-----------------------------"
	::= { ommp101PerformanceEntry 113 }

	ommp101EthernetStatsFragmentsReceived OBJECT-TYPE
		SYNTAX  DisplayString
		MAX-ACCESS  read-only
		STATUS  current
		DESCRIPTION
			"For port configured with LAN10G  traffic,
			gives the number of Ethernet StatsFragments received.
			-----------------------------
			ommp101InterfaceNumber:
			1 to 10 - CLIENT-1 to CLIENT-10
			-----------------------------
			Values:
			eg: 1234
			-----------------------------"
	::= { ommp101PerformanceEntry 114 }

	ommp101EthernetPauseControlFramesTransmitted OBJECT-TYPE
		SYNTAX  DisplayString
		MAX-ACCESS  read-only
		STATUS  current
		DESCRIPTION
			"For port configured with LAN10G  traffic,
			gives the number of Ethernet PauseControlFrames Transmitted.
			-----------------------------
			ommp101InterfaceNumber:
			1 to 10 - CLIENT-1 to CLIENT-10
			-----------------------------
			Values:
			eg: 1234
			-----------------------------"
	::= { ommp101PerformanceEntry 115 }

	ommp101EthernetPauseControlFramesReceived OBJECT-TYPE
		SYNTAX  DisplayString
		MAX-ACCESS  read-only
		STATUS  current
		DESCRIPTION
			"For port configured with LAN10G  traffic,
			gives the number of Ethernet PauseControlFrames received.
			-----------------------------
			ommp101InterfaceNumber:
			1 to 10 - CLIENT-1 to CLIENT-10
			-----------------------------
			Values:
			eg: 1234
			-----------------------------"
	::= { ommp101PerformanceEntry 116 }

	ommp101PerformanceTableRowStatus OBJECT-TYPE
              SYNTAX      RowStatus
              MAX-ACCESS  read-write
              STATUS      current
              DESCRIPTION
			"*****************************
			This is MIB realted property,
			NOT to be considered as a card property
			*****************************"
              ::= { ommp101PerformanceEntry 117 }
              
--*****************************************************************************

--*****************************************************************************

	snmpCurrentNotificationsGroup NOTIFICATION-GROUP
		NOTIFICATIONS { 
					ommp101Cfp2InputPowerFailureAlarmTrap,
					ommp101Cfp2OutputPowerFailureAlarmTrap,
					ommp101Cfp2HighTemperatureAlarmTrap,
					ommp101Cfp2LowTemperatureAlarmTrap,
					ommp101Cfp2HighTemperatureWarningTrap,
					ommp101Cfp2LowTemperatureWarningTrap,
					ommp101Cfp2InputHighPowerAlarmTrap,
					ommp101Cfp2InputLowPowerAlarmTrap,
					ommp101Cfp2InputHighPowerWarningTrap,
					ommp101Cfp2InputLowPowerWarningTrap,
					ommp101Cfp2OutputHighPowerAlarmTrap,
					ommp101Cfp2OutputLowPowerAlarmTrap,
					ommp101Cfp2OutputHighPowerWarningTrap,
					ommp101Cfp2OutputLowPowerWarningTrap,
					ommp101Cfp2HighSupplyVoltageAlarmTrap,
					ommp101Cfp2LowSupplyVoltageAlarmTrap,
					ommp101Cfp2HighSupplyVoltageWarningTrap,
					ommp101Cfp2LowSupplyVoltageWarningTrap,
					ommp101Cfp2PresenceAbsenceNotificationTrap,
					ommp101SfpPlusInputPowerFailureAlarmTrap,
					ommp101SfpPlusOutputPowerFailureAlarmTrap,
					ommp101SfpPlusHighTemperatureAlarmTrap,
					ommp101SfpPlusLowTemperatureAlarmTrap,
					ommp101SfpPlusHighTemperatureWarningTrap,
					ommp101SfpPlusLowTemperatureWarningTrap,
					ommp101SfpPlusHighBiasCurrentAlarmTrap,
					ommp101SfpPlusLowBiasCurrentAlarmTrap,
					ommp101SfpPlusHighBiasCurrentWarningTrap,
					ommp101SfpPlusLowBiasCurrentWarningTrap,
					ommp101SfpPlusInputHighPowerAlarmTrap,
					ommp101SfpPlusInputLowPowerAlarmTrap,
					ommp101SfpPlusInputHighPowerWarningTrap,
					ommp101SfpPlusInputLowPowerWarningTrap,
					ommp101SfpPlusOutputHighPowerAlarmTrap,
					ommp101SfpPlusOutputLowPowerAlarmTrap,
					ommp101SfpPlusOutputHighPowerWarningTrap,
					ommp101SfpPlusOutputLowPowerWarningTrap,
					ommp101SfpPlusHighSupplyVoltageAlarmTrap,
					ommp101SfpPlusLowSupplyVoltageAlarmTrap,
					ommp101SfpPlusHighSupplyVoltageWarningTrap,
					ommp101SfpPlusLowSupplyVoltageWarningTrap,
					ommp101SfpPlusPresenceAbsenceNotificationTrap,
					ommp101SfpPlusTransmitFaultPresenceAlarmTrap,
					ommp101OtuLossOfSignalAlarmTrap,
					ommp101OtuLossOfFrameAlarmTrap,
					ommp101OtuOutOfFrameAlarmTrap,
					ommp101OtuLossOfMultiFrameAlarmTrap,
					ommp101OtuOutOfMultiFrameAlarmTrap,
					ommp101OtuSignalFailAlarmTrap,
					ommp101OtuSignalDegradeAlarmTrap,
					ommp101OtuAlarmIndicationSignalAlarmTrap,
					ommp101OtuIncomingAlignmentErrorAlarmTrap,
					ommp101OtuBackwardIncomingAlignmentErrorAlarmTrap,
					ommp101OtuBackwardDefectIndicationAlarmTrap,
					ommp101OduSignalFailAlarmTrap,
					ommp101OduSignalDegradeAlarmTrap,
					ommp101OduAlarmIndicationSignalAlarmTrap,
					ommp101OduTcm1IncomingAlignmentErrorAlarmTrap,
					ommp101OduTcm2IncomingAlignmentErrorAlarmTrap,
					ommp101OduTcm3IncomingAlignmentErrorAlarmTrap,
					ommp101OduTcm4IncomingAlignmentErrorAlarmTrap,
					ommp101OduTcm5IncomingAlignmentErrorAlarmTrap,
					ommp101OduTcm6IncomingAlignmentErrorAlarmTrap,
					ommp101OduLockedDefectAlarmTrap,
					ommp101OduOpenConnectionIndicationAlarmTrap,
					ommp101OduBackwardDefectIndicationAlarmTrap,
					ommp101OduTcm1BackwardIncomingAlignmentErrorAlarmTrap,
					ommp101OduTcm2BackwardIncomingAlignmentErrorAlarmTrap,
					ommp101OduTcm3BackwardIncomingAlignmentErrorAlarmTrap,
					ommp101OduTcm4BackwardIncomingAlignmentErrorAlarmTrap,
					ommp101OduTcm5BackwardIncomingAlignmentErrorAlarmTrap,
					ommp101OduTcm6BackwardIncomingAlignmentErrorAlarmTrap,
					ommp101OduLossOfFrameLossOfMultiframeAlarmTrap,
					ommp101OpuPayloadMismatchAlarmTrap,
					ommp101SdhLossOfSignalAlarmTrap,
					ommp101SdhOutOfFrameAlarmTrap,
					ommp101SdhLossOfFrameAlarmTrap,
					ommp101SdhMsAlarmIndicationSignalAlarmTrap,
					ommp101SdhMsRemoteDefectIndicationAlarmTrap,
					ommp101SdhMsB2ExcessiveErrorAlarmTrap,
					ommp101SdhMsB2SignalDegradeAlarmTrap,
					ommp101EthernetLossOfSignalAlarmTrap,
					ommp101EthernetLinkFailureAlarmTrap,
					ommp101EthernetHighBerAlarmTrap,
					ommp101EthernetLocalFaultAlarmTrap,
					ommp101EthernetRemoteFaultAlarmTrap,
					ommp101OtuTraceIdentifierMismatchAlarmTrap,
					ommp101OduTraceIdentifierMismatchAlarmTrap,
					ommp101EthernetLossOfAlignmentAlarmTrap,
					ommp101EthernetLossOfBlockLockAlarmTrap,
					ommp101EthernetNotAlignedInPcsAlarmTrap
				}
  	STATUS current
	DESCRIPTION
  	   	"The UTL OMMP101 current notifications group"
  	::= { ommp101 6 }

            snmpcurrentGroup OBJECT-GROUP
    OBJECTS 	{ 
			ommp101InterfaceNumber,	
    			ommp101EepromCardId,
			ommp101EepromCardName,
			ommp101EepromPartCode,
			ommp101EepromCardSerialNumber,
			ommp101EepromHardwareExternalReleaseVersion,
			ommp101SoftwareExternalReleaseVersion,
			ommp101EepromHardwareInternalReleaseVersion,
			ommp101SoftwareInternalReleaseVersion,
			ommp101EepromCardUidNumber,
			ommp101EepromCardEui48Number,
			ommp101EepromCardEui64Number,
			ommp101CardInstallationDate,
			ommp101CardCommissionDate,
			ommp101CardRunningTime,
			ommp101CardRestartCount,
			ommp101Cfp2ReadyForOperation,
			ommp101Cfp2VendorName,
			ommp101Cfp2VendorIeeeId,
			ommp101Cfp2PartNumber,
			ommp101Cfp2SerialNumber,
			ommp101Cfp2ManufacturingDate,
			ommp101Cfp2HardwareVersionNumber,
			ommp101Cfp2FirmwareVersionNumber,
			ommp101Cfp2MediaType,
			ommp101NumberOfNetworkLanesInCfp2,
			ommp101NumberOfHostLanesInCfp2,
			ommp101Cfp2ModuleId,
			ommp101Cfp2PowerClass,
			ommp101Cfp2ProductCodeValue,
			ommp101Cfp2WavelengthTunabilitySupported,
			ommp101TunableCfp2LaserFirstFrequency,
			ommp101TunableCfp2LaserLastFrequency,
			ommp101Cfp2ConnectorType,
			ommp101Cfp2SignalEncodingTypeSupported,
			ommp101Cfp2MaximumBitrateSupported,
			ommp101Cfp2MaximumCaseTemperatureSupported,
			ommp101Cfp2MinimumCaseTemperatureSupported,
			ommp101Cfp2ActiveWavelengthControlSupported,
			ommp101Cfp2TransmitterIsCooledOrUncooled,
			ommp101SfpPlusEepromPage,
			ommp101CheckCodeOfSfpPlusEepromPage,
			ommp101ExtendedCheckCodeOfSfpPlusEepromPage,
			ommp101SfpPlusVendorName,
			ommp101SfpPlusVendorIeeeId,
			ommp101SfpPlusPartNumber,
			ommp101SfpPlusSerialNumber,
			ommp101SfpPlusRevisionNumber,
			ommp101SfpPlusManufacturingDate,
			ommp101FixedSfpPlusLaserWavelength,
			ommp101SfpPlusConnectorType,
			ommp101SfpPlusLinkLength,
			ommp101SfpPlusSignalEncodingTypeSupported,
			ommp101SfpPlusTransceiverCodesSupported,
			ommp101SfpPlusMaximumBitrateSupported,
			ommp101SfpPlusNominalBitrateSupported,
			ommp101SfpPlusMinimumBitrateSupported,
			ommp101CardGeneralDetailsTableRowStatus,
			ommp101CardSoftwareUpgrade,
			ommp101CardSignalMonitorState,
			ommp101CardOpticalMonitorState,
			ommp101CardSoftReset,
			ommp101CardFactoryReset,
			ommp101SyncSystemTimeWithNtpServer,
			ommp101SyncRtcWithNtpServer,
			ommp101SyncRtcWithSystemTime,
			ommp101UpdateGivenTimeIntoSystem,
			ommp101UpdateGivenTimeIntoRtc,
			ommp101SystemTimeAndRtcTime,
			ommp101TrafficConfiguration,
			ommp101LoopbackState,
			ommp101PortSignalMonitorState,
			ommp101PortOpticalMonitorState,
			ommp101ClearSignalPerformance,
			ommp101AlsState,
			ommp101AlsPulseRepetitionTime,
			ommp101OtuFecConfiguration,
			ommp101OtuSignalFailThreshold,
			ommp101OtuSignalDegradeThreshold,
			ommp101OtuSapiTransmitTraceMessage,
			ommp101OtuDapiTransmitTraceMessage,
			ommp101OtuOperatorSpecificTransmitTraceMessage,
			ommp101OtuSapiExpectedTraceMessage,
			ommp101OtuDapiExpectedTraceMessage,
			ommp101OtuOperatorSpecificExpectedTraceMessage,
			ommp101OduSignalFailThreshold,
			ommp101OduSignalDegradeThreshold,
			ommp101OduSapiTransmitTraceMessage,
			ommp101OduDapiTransmitTraceMessage,
			ommp101OduOperatorSpecificTransmitTraceMessage,
			ommp101OduSapiExpectedTraceMessage,
			ommp101OduDapiExpectedTraceMessage,
			ommp101OduOperatorSpecificExpectedTraceMessage,
			ommp101SdhMsB2ExcessiveErrorThreshold,
			ommp101SdhMsB2SignalDegradeThreshold,
			ommp101TunableCfp2LaserWavelength,
			ommp101TunableCfp2LaserChannelNumber,
			ommp101Cfp2LaserState,
			ommp101Cfp2Reset,
			ommp101Cfp2PowerDownMode,
			ommp101Cfp2HighTemperatureAlarmThreshold,
			ommp101Cfp2LowTemperatureAlarmThreshold,
			ommp101Cfp2HighTemperatureWarningThreshold,
			ommp101Cfp2LowTemperatureWarningThreshold,
			ommp101Cfp2InputHighPowerAlarmThreshold,
			ommp101Cfp2InputLowPowerAlarmThreshold,
			ommp101Cfp2InputHighPowerWarningThreshold,
			ommp101Cfp2InputLowPowerWarningThreshold,
			ommp101Cfp2OutputHighPowerAlarmThreshold,
			ommp101Cfp2OutputLowPowerAlarmThreshold,
			ommp101Cfp2OutputHighPowerWarningThreshold,
			ommp101Cfp2OutputLowPowerWarningThreshold,
			ommp101Cfp2HighSupplyVoltageAlarmThreshold,
			ommp101Cfp2LowSupplyVoltageAlarmThreshold,
			ommp101Cfp2HighSupplyVoltageWarningThreshold,
			ommp101Cfp2LowSupplyVoltageWarningThreshold,
			ommp101SfpPlusLaserState,
			ommp101SfpPlusHighTemperatureAlarmThreshold,
			ommp101SfpPlusLowTemperatureAlarmThreshold,
			ommp101SfpPlusHighTemperatureWarningThreshold,
			ommp101SfpPlusLowTemperatureWarningThreshold,
			ommp101SfpPlusHighBiasCurrentAlarmThreshold,
			ommp101SfpPlusLowBiasCurrentAlarmThreshold,
			ommp101SfpPlusHighBiasCurrentWarningThreshold,
			ommp101SfpPlusLowBiasCurrentWarningThreshold,
			ommp101SfpPlusInputHighPowerAlarmThreshold,
			ommp101SfpPlusInputLowPowerAlarmThreshold,
			ommp101SfpPlusInputHighPowerWarningThreshold,
			ommp101SfpPlusInputLowPowerWarningThreshold,
			ommp101SfpPlusOutputHighPowerAlarmThreshold,
			ommp101SfpPlusOutputLowPowerAlarmThreshold,
			ommp101SfpPlusOutputHighPowerWarningThreshold,
			ommp101SfpPlusOutputLowPowerWarningThreshold,
			ommp101SfpPlusHighSupplyVoltageAlarmThreshold,
			ommp101SfpPlusLowSupplyVoltageAlarmThreshold,
			ommp101SfpPlusHighSupplyVoltageWarningThreshold,
			ommp101SfpPlusLowSupplyVoltageWarningThreshold,
			ommp101Cfp2InputPowerFailureAlarmInhibit,
			ommp101Cfp2OutputPowerFailureAlarmInhibit,
			ommp101Cfp2HighTemperatureAlarmInhibit,
			ommp101Cfp2LowTemperatureAlarmInhibit,
			ommp101Cfp2HighTemperatureWarningInhibit,
			ommp101Cfp2LowTemperatureWarningInhibit,
			ommp101Cfp2InputHighPowerAlarmInhibit,
			ommp101Cfp2InputLowPowerAlarmInhibit,
			ommp101Cfp2InputHighPowerWarningInhibit,
			ommp101Cfp2InputLowPowerWarningInhibit,
			ommp101Cfp2OutputHighPowerAlarmInhibit,
			ommp101Cfp2OutputLowPowerAlarmInhibit,
			ommp101Cfp2OutputHighPowerWarningInhibit,
			ommp101Cfp2OutputLowPowerWarningInhibit,
			ommp101Cfp2HighSupplyVoltageAlarmInhibit,
			ommp101Cfp2LowSupplyVoltageAlarmInhibit,
			ommp101Cfp2HighSupplyVoltageWarningInhibit,
			ommp101Cfp2LowSupplyVoltageWarningInhibit,
			ommp101Cfp2PresenceAbsenceNotificationInhibit,
			ommp101SfpPlusInputPowerFailureAlarmInhibit,
			ommp101SfpPlusOutputPowerFailureAlarmInhibit,
			ommp101SfpPlusHighTemperatureAlarmInhibit,
			ommp101SfpPlusLowTemperatureAlarmInhibit,
			ommp101SfpPlusHighTemperatureWarningInhibit,
			ommp101SfpPlusLowTemperatureWarningInhibit,
			ommp101SfpPlusHighBiasCurrentAlarmInhibit,
			ommp101SfpPlusLowBiasCurrentAlarmInhibit,
			ommp101SfpPlusHighBiasCurrentWarningInhibit,
			ommp101SfpPlusLowBiasCurrentWarningInhibit,
			ommp101SfpPlusInputHighPowerAlarmInhibit,
			ommp101SfpPlusInputLowPowerAlarmInhibit,
			ommp101SfpPlusInputHighPowerWarningInhibit,
			ommp101SfpPlusInputLowPowerWarningInhibit,
			ommp101SfpPlusOutputHighPowerAlarmInhibit,
			ommp101SfpPlusOutputLowPowerAlarmInhibit,
			ommp101SfpPlusOutputHighPowerWarningInhibit,
			ommp101SfpPlusOutputLowPowerWarningInhibit,
			ommp101SfpPlusHighSupplyVoltageAlarmInhibit,
			ommp101SfpPlusLowSupplyVoltageAlarmInhibit,
			ommp101SfpPlusHighSupplyVoltageWarningInhibit,
			ommp101SfpPlusLowSupplyVoltageWarningInhibit,
			ommp101SfpPlusPresenceAbsenceNotificationInhibit,
			ommp101SfpPlusTransmitFaultPresenceAlarmInhibit,
			ommp101OtuLossOfSignalAlarmInhibit,
			ommp101OtuLossOfFrameAlarmInhibit,
			ommp101OtuOutOfFrameAlarmInhibit,
			ommp101OtuLossOfMultiFrameAlarmInhibit,
			ommp101OtuOutOfMultiFrameAlarmInhibit,
			ommp101OtuSignalFailAlarmInhibit,
			ommp101OtuSignalDegradeAlarmInhibit,
			ommp101OtuAlarmIndicationSignalAlarmInhibit,
			ommp101OtuIncomingAlignmentErrorAlarmInhibit,
			ommp101OtuBackwardIncomingAlignmentErrorAlarmInhibit,
			ommp101OtuBackwardDefectIndicationAlarmInhibit,
			ommp101OduSignalFailAlarmInhibit,
			ommp101OduSignalDegradeAlarmInhibit,
			ommp101OduAlarmIndicationSignalAlarmInhibit,
			ommp101OduTcm1IncomingAlignmentErrorAlarmInhibit,
			ommp101OduTcm2IncomingAlignmentErrorAlarmInhibit,
			ommp101OduTcm3IncomingAlignmentErrorAlarmInhibit,
			ommp101OduTcm4IncomingAlignmentErrorAlarmInhibit,
			ommp101OduTcm5IncomingAlignmentErrorAlarmInhibit,
			ommp101OduTcm6IncomingAlignmentErrorAlarmInhibit,
			ommp101OduLockedDefectAlarmInhibit,
			ommp101OduOpenConnectionIndicationAlarmInhibit,
			ommp101OduBackwardDefectIndicationAlarmInhibit,
			ommp101OduTcm1BackwardIncomingAlignmentErrorAlarmInhibit,
			ommp101OduTcm2BackwardIncomingAlignmentErrorAlarmInhibit,
			ommp101OduTcm3BackwardIncomingAlignmentErrorAlarmInhibit,
			ommp101OduTcm4BackwardIncomingAlignmentErrorAlarmInhibit,
			ommp101OduTcm5BackwardIncomingAlignmentErrorAlarmInhibit,
			ommp101OduTcm6BackwardIncomingAlignmentErrorAlarmInhibit,
			ommp101OduLossOfFrameLossOfMultiframeAlarmInhibit,
			ommp101OpuPayloadMismatchAlarmInhibit,
			ommp101SdhLossOfSignalAlarmInhibit,
			ommp101SdhOutOfFrameAlarmInhibit,
			ommp101SdhLossOfFrameAlarmInhibit,
			ommp101SdhRsTraceIdentifierMismatchAlarmInhibit,
			ommp101SdhMsAlarmIndicationSignalAlarmInhibit,
			ommp101SdhMsRemoteDefectIndicationAlarmInhibit,
			ommp101EthernetLossOfSignalAlarmInhibit,
			ommp101EthernetLinkFailureAlarmInhibit,
			ommp101EthernetHighBerAlarmInhibit,
			ommp101EthernetLocalFaultAlarmInhibit,
			ommp101EthernetRemoteFaultAlarmInhibit,
			ommp101Cfp2InputPowerFailureAlarmSeverity,
			ommp101Cfp2OutputPowerFailureAlarmSeverity,
			ommp101Cfp2HighTemperatureAlarmSeverity,
			ommp101Cfp2LowTemperatureAlarmSeverity,
			ommp101Cfp2HighTemperatureWarningSeverity,
			ommp101Cfp2LowTemperatureWarningSeverity,
			ommp101Cfp2InputHighPowerAlarmSeverity,
			ommp101Cfp2InputLowPowerAlarmSeverity,
			ommp101Cfp2InputHighPowerWarningSeverity,
			ommp101Cfp2InputLowPowerWarningSeverity,
			ommp101Cfp2OutputHighPowerAlarmSeverity,
			ommp101Cfp2OutputLowPowerAlarmSeverity,
			ommp101Cfp2OutputHighPowerWarningSeverity,
			ommp101Cfp2OutputLowPowerWarningSeverity,
			ommp101Cfp2HighSupplyVoltageAlarmSeverity,
			ommp101Cfp2LowSupplyVoltageAlarmSeverity,
			ommp101Cfp2HighSupplyVoltageWarningSeverity,
			ommp101Cfp2LowSupplyVoltageWarningSeverity,
			ommp101Cfp2PresenceAbsenceNotificationSeverity,
			ommp101SfpPlusInputPowerFailureAlarmSeverity,
			ommp101SfpPlusOutputPowerFailureAlarmSeverity,
			ommp101SfpPlusHighTemperatureAlarmSeverity,
			ommp101SfpPlusLowTemperatureAlarmSeverity,
			ommp101SfpPlusHighTemperatureWarningSeverity,
			ommp101SfpPlusLowTemperatureWarningSeverity,
			ommp101SfpPlusHighBiasCurrentAlarmSeverity,
			ommp101SfpPlusLowBiasCurrentAlarmSeverity,
			ommp101SfpPlusHighBiasCurrentWarningSeverity,
			ommp101SfpPlusLowBiasCurrentWarningSeverity,
			ommp101SfpPlusInputHighPowerAlarmSeverity,
			ommp101SfpPlusInputLowPowerAlarmSeverity,
			ommp101SfpPlusInputHighPowerWarningSeverity,
			ommp101SfpPlusInputLowPowerWarningSeverity,
			ommp101SfpPlusOutputHighPowerAlarmSeverity,
			ommp101SfpPlusOutputLowPowerAlarmSeverity,
			ommp101SfpPlusOutputHighPowerWarningSeverity,
			ommp101SfpPlusOutputLowPowerWarningSeverity,
			ommp101SfpPlusHighSupplyVoltageAlarmSeverity,
			ommp101SfpPlusLowSupplyVoltageAlarmSeverity,
			ommp101SfpPlusHighSupplyVoltageWarningSeverity,
			ommp101SfpPlusLowSupplyVoltageWarningSeverity,
			ommp101SfpPlusPresenceAbsenceNotificationSeverity,
			ommp101SfpPlusTransmitFaultPresenceAlarmSeverity,
			ommp101OtuLossOfSignalAlarmSeverity,
			ommp101OtuLossOfFrameAlarmSeverity,
			ommp101OtuOutOfFrameAlarmSeverity,
			ommp101OtuLossOfMultiFrameAlarmSeverity,
			ommp101OtuOutOfMultiFrameAlarmSeverity,
			ommp101OtuSignalFailAlarmSeverity,
			ommp101OtuSignalDegradeAlarmSeverity,
			ommp101OtuAlarmIndicationSignalAlarmSeverity,
			ommp101OtuIncomingAlignmentErrorAlarmSeverity,
			ommp101OtuBackwardIncomingAlignmentErrorAlarmSeverity,
			ommp101OtuBackwardDefectIndicationAlarmSeverity,
			ommp101OduSignalFailAlarmSeverity,
			ommp101OduSignalDegradeAlarmSeverity,
			ommp101OduAlarmIndicationSignalAlarmSeverity,
			ommp101OduTcm1IncomingAlignmentErrorAlarmSeverity,
			ommp101OduTcm2IncomingAlignmentErrorAlarmSeverity,
			ommp101OduTcm3IncomingAlignmentErrorAlarmSeverity,
			ommp101OduTcm4IncomingAlignmentErrorAlarmSeverity,
			ommp101OduTcm5IncomingAlignmentErrorAlarmSeverity,
			ommp101OduTcm6IncomingAlignmentErrorAlarmSeverity,
			ommp101OduLockedDefectAlarmSeverity,
			ommp101OduOpenConnectionIndicationAlarmSeverity,
			ommp101OduBackwardDefectIndicationAlarmSeverity,
			ommp101OduTcm1BackwardIncomingAlignmentErrorAlarmSeverity,
			ommp101OduTcm2BackwardIncomingAlignmentErrorAlarmSeverity,
			ommp101OduTcm3BackwardIncomingAlignmentErrorAlarmSeverity,
			ommp101OduTcm4BackwardIncomingAlignmentErrorAlarmSeverity,
			ommp101OduTcm5BackwardIncomingAlignmentErrorAlarmSeverity,
			ommp101OduTcm6BackwardIncomingAlignmentErrorAlarmSeverity,
			ommp101OduLossOfFrameLossOfMultiframeAlarmSeverity,
			ommp101OpuPayloadMismatchAlarmSeverity,
			ommp101SdhLossOfSignalAlarmSeverity,
			ommp101SdhOutOfFrameAlarmSeverity,
			ommp101SdhLossOfFrameAlarmSeverity,
			ommp101SdhRsTraceIdentifierMismatchAlarmSeverity,
			ommp101SdhMsAlarmIndicationSignalAlarmSeverity,
			ommp101SdhMsRemoteDefectIndicationAlarmSeverity,
			ommp101EthernetLossOfSignalAlarmSeverity,
			ommp101EthernetLinkFailureAlarmSeverity,
			ommp101EthernetHighBerAlarmSeverity,
			ommp101EthernetLocalFaultAlarmSeverity,
			ommp101EthernetRemoteFaultAlarmSeverity,
			ommp101TunableCfp2WavelengthGridSpacing,
			ommp101OduLockedDefectAlarmInsertion,
			ommp101OduOpenConnectionIndicationAlarmInsertion,
			ommp101OtuTraceIdentifierMismatchAlarmInhibit,
			ommp101OduTraceIdentifierMismatchAlarmInhibit,
			ommp101OtuTraceIdentifierMismatchAlarmSeverity,
			ommp101OduTraceIdentifierMismatchAlarmSeverity,
			ommp101EthernetLossOfAlignmentAlarmInhibit,
			ommp101EthernetLossOfBlockLockAlarmInhibit,
			ommp101EthernetNotAlignedInPcsAlarmInhibit,
			ommp101EthernetLossOfAlignmentAlarmSeverity,
			ommp101EthernetLossOfBlockLockAlarmSeverity,
			ommp101EthernetNotAlignedInPcsAlarmSeverity,
			ommp101ConfigurationTableRowStatus,
			ommp101Cfp2InputPowerFailureAlarm,
			ommp101Cfp2OutputPowerFailureAlarm,
			ommp101Cfp2HighTemperatureAlarm,
			ommp101Cfp2LowTemperatureAlarm,
			ommp101Cfp2HighTemperatureWarning,
			ommp101Cfp2LowTemperatureWarning,
			ommp101Cfp2InputHighPowerAlarm,
			ommp101Cfp2InputLowPowerAlarm,
			ommp101Cfp2InputHighPowerWarning,
			ommp101Cfp2InputLowPowerWarning,
			ommp101Cfp2OutputHighPowerAlarm,
			ommp101Cfp2OutputLowPowerAlarm,
			ommp101Cfp2OutputHighPowerWarning,
			ommp101Cfp2OutputLowPowerWarning,
			ommp101Cfp2HighSupplyVoltageAlarm,
			ommp101Cfp2LowSupplyVoltageAlarm,
			ommp101Cfp2HighSupplyVoltageWarning,
			ommp101Cfp2LowSupplyVoltageWarning,
			ommp101Cfp2PresenceAbsenceNotification,
			ommp101SfpPlusInputPowerFailureAlarm,
			ommp101SfpPlusOutputPowerFailureAlarm,
			ommp101SfpPlusHighTemperatureAlarm,
			ommp101SfpPlusLowTemperatureAlarm,
			ommp101SfpPlusHighTemperatureWarning,
			ommp101SfpPlusLowTemperatureWarning,
			ommp101SfpPlusHighBiasCurrentAlarm,
			ommp101SfpPlusLowBiasCurrentAlarm,
			ommp101SfpPlusHighBiasCurrentWarning,
			ommp101SfpPlusLowBiasCurrentWarning,
			ommp101SfpPlusInputHighPowerAlarm,
			ommp101SfpPlusInputLowPowerAlarm,
			ommp101SfpPlusInputHighPowerWarning,
			ommp101SfpPlusInputLowPowerWarning,
			ommp101SfpPlusOutputHighPowerAlarm,
			ommp101SfpPlusOutputLowPowerAlarm,
			ommp101SfpPlusOutputHighPowerWarning,
			ommp101SfpPlusOutputLowPowerWarning,
			ommp101SfpPlusHighSupplyVoltageAlarm,
			ommp101SfpPlusLowSupplyVoltageAlarm,
			ommp101SfpPlusHighSupplyVoltageWarning,
			ommp101SfpPlusLowSupplyVoltageWarning,
			ommp101SfpPlusPresenceAbsenceNotification,
			ommp101SfpPlusTransmitFaultPresenceAlarm,
			ommp101OtuLossOfSignalAlarm,
			ommp101OtuLossOfFrameAlarm,
			ommp101OtuOutOfFrameAlarm,
			ommp101OtuLossOfMultiFrameAlarm,
			ommp101OtuOutOfMultiFrameAlarm,
			ommp101OtuSignalFailAlarm,
			ommp101OtuSignalDegradeAlarm,
			ommp101OtuAlarmIndicationSignalAlarm,
			ommp101OtuIncomingAlignmentErrorAlarm,
			ommp101OtuBackwardIncomingAlignmentErrorAlarm,
			ommp101OtuBackwardDefectIndicationAlarm,
			ommp101OduSignalFailAlarm,
			ommp101OduSignalDegradeAlarm,
			ommp101OduAlarmIndicationSignalAlarm,
			ommp101OduTcm1IncomingAlignmentErrorAlarm,
			ommp101OduTcm2IncomingAlignmentErrorAlarm,
			ommp101OduTcm3IncomingAlignmentErrorAlarm,
			ommp101OduTcm4IncomingAlignmentErrorAlarm,
			ommp101OduTcm5IncomingAlignmentErrorAlarm,
			ommp101OduTcm6IncomingAlignmentErrorAlarm,
			ommp101OduLockedDefectAlarm,
			ommp101OduOpenConnectionIndicationAlarm,
			ommp101OduBackwardDefectIndicationAlarm,
			ommp101OduTcm1BackwardIncomingAlignmentErrorAlarm,
			ommp101OduTcm2BackwardIncomingAlignmentErrorAlarm,
			ommp101OduTcm3BackwardIncomingAlignmentErrorAlarm,
			ommp101OduTcm4BackwardIncomingAlignmentErrorAlarm,
			ommp101OduTcm5BackwardIncomingAlignmentErrorAlarm,
			ommp101OduTcm6BackwardIncomingAlignmentErrorAlarm,
			ommp101OduLossOfFrameLossOfMultiframeAlarm,
			ommp101OpuPayloadMismatchAlarm,
			ommp101SdhLossOfSignalAlarm,
			ommp101SdhOutOfFrameAlarm,
			ommp101SdhLossOfFrameAlarm,
			ommp101SdhMsAlarmIndicationSignalAlarm,
			ommp101SdhMsRemoteDefectIndicationAlarm,
			ommp101SdhMsB2ExcessiveErrorAlarm,
			ommp101SdhMsB2SignalDegradeAlarm,
			ommp101EthernetLossOfSignalAlarm,
			ommp101EthernetLinkFailureAlarm,
			ommp101EthernetHighBerAlarm,
			ommp101EthernetLocalFaultAlarm,
			ommp101EthernetRemoteFaultAlarm,
			ommp101OtuTraceIdentifierMismatchAlarm,
			ommp101OduTraceIdentifierMismatchAlarm,
			ommp101EthernetLossOfAlignmentAlarm,
			ommp101EthernetLossOfBlockLockAlarm,
			ommp101EthernetNotAlignedInPcsAlarm,
			ommp101AlarmQueryTableRowStatus,
			ommp101Cfp2InputPower,
			ommp101Cfp2OutputPower,
			ommp101Cfp2SupplyVoltage,
			ommp101Cfp2Temperature,
			ommp101SfpPlusInputPower,
			ommp101SfpPlusOutputPower,
			ommp101SfpPlusBiasCurrent,
			ommp101SfpPlusSupplyVoltage,
			ommp101SfpPlusTemperature,
			ommp101OtnFecUncorrectedWords,
			ommp101OtnFecCorrectedBits,
			ommp101OtnFecZerosCorrectedBits,
			ommp101OtnFecOnesCorrectedBits,
			ommp101OtuBitInterleavedParityErrors,
			ommp101OtuBackwardErrorIndicationErrorCount,
			ommp101OtuErrorFreeSeconds,
			ommp101OtuErrorSeconds,
			ommp101OtuBackgroundBlockErrors,
			ommp101OtuSevereErrorSeconds,
			ommp101OtuUnavailableSeconds,
			ommp101OtuBackgroundBlockErrorRatio,
			ommp101OtuSevereErrorSecondsErrorRatio,
			ommp101OtuFarEndErrorFreeSeconds,
			ommp101OtuFarEndErrorSeconds,
			ommp101OtuFarEndBackgroundBlockErrors,
			ommp101OtuFarEndSevereErrorSeconds,
			ommp101OtuFarEndUnavailableSeconds,
			ommp101OtuFarEndBackgroundBlockErrorRatio,
			ommp101OtuFarEndSevereErrorSecondsErrorRatio,
			ommp101OtuErrorRatio,
			ommp101OtuBitErrorRate,
			ommp101OduBitInterleavedParityErrors,
			ommp101OduTcm1BitInterleavedParityErrors,
			ommp101OduTcm2BitInterleavedParityErrors,
			ommp101OduTcm3BitInterleavedParityErrors,
			ommp101OduTcm4BitInterleavedParityErrors,
			ommp101OduTcm5BitInterleavedParityErrors,
			ommp101OduTcm6BitInterleavedParityErrors,
			ommp101OduTcm1IncomingAlignmentErrorSeconds,
			ommp101OduBackwardErrorIndicationErrorCount,
			ommp101OduTcm1BackwardErrorIndicationErrorCount,
			ommp101OduTcm2BackwardErrorIndicationErrorCount,
			ommp101OduTcm3BackwardErrorIndicationErrorCount,
			ommp101OduTcm4BackwardErrorIndicationErrorCount,
			ommp101OduTcm5BackwardErrorIndicationErrorCount,
			ommp101OduTcm6BackwardErrorIndicationErrorCount,
			ommp101OduTcm1BackwardIncomingAlignmentErrorSeconds,
			ommp101OduDelayMeasurement,
			ommp101OduErrorFreeSeconds,
			ommp101OduErrorSeconds,
			ommp101OduBackgroundBlockErrors,
			ommp101OduSevereErrorSeconds,
			ommp101OduUnavailableSeconds,
			ommp101OduBackgroundBlockErrorRatio,
			ommp101OduSevereErrorSecondsErrorRatio,
			ommp101OduFarEndErrorFreeSeconds,
			ommp101OduFarEndErrorSeconds,
			ommp101OduFarEndBackgroundBlockErrors,
			ommp101OduFarEndSevereErrorSeconds,
			ommp101OduFarEndUnavailableSeconds,
			ommp101OduFarEndBackgroundBlockErrorRatio,
			ommp101OduFarEndSevereErrorSecondsErrorRatio,
			ommp101SdhRsB1BitInterleavedParityErrors,
			ommp101SdhMsB2BitInterleavedParityErrors,
			ommp101SdhMsRemoteErrorIndicationErrorCount,
			ommp101SdhErrorFreeSeconds,
			ommp101SdhErrorSeconds,
			ommp101SdhBackgroundBlockErrors,
			ommp101SdhSevereErrorSeconds,
			ommp101SdhUnavailableSeconds,
			ommp101SdhErrorSecondsErrorRatio,
			ommp101SdhBackgroundBlockErrorRatio,
			ommp101SdhSevereErrorSecondsErrorRatio,
			ommp101EthernetTerminatedFramesTransmitted,		
			ommp101EthernetTerminatedFramesReceived,			
			ommp101EthernetTerminatedVlanTaggedFramesTransmitted,		
			ommp101EthernetTerminatedVlanTaggedFramesReceived,		
			ommp101EthernetTerminatedUnicastFramesTransmitted,		
			ommp101EthernetTerminatedUnicastFramesReceived,				
			ommp101EthernetTerminatedBroadcastFramesTransmitted,		
			ommp101EthernetTerminatedBroadcastFramesReceived,				
			ommp101EthernetTerminatedMulticastFramesTransmitted,		
			ommp101EthernetTerminatedMulticastFramesReceived,				
			ommp101EthernetTerminatedOverSizeFramesTransmitted,
			ommp101EthernetTerminatedOverSizeFramesReceived,		
			ommp101EthernetTerminatedUnderSizeFramesTransmitted,
			ommp101EthernetTerminatedUnderSizeFramesReceived,		
			ommp101EthernetTerminatedFrameCheckSequenceErrorsTransmitted,	
			ommp101EthernetTerminatedFrameCheckSequenceErrorsReceived,			
			ommp101EthernetTerminatedControlFramesTransmitted,		
			ommp101EthernetTerminatedControlFramesReceived,								
			ommp101EthernetStatsPkts64OctsTransmitted,		
			ommp101EthernetStatsPkts64OctsReceived,					
			ommp101EthernetStatsPkts65to127OctsTransmitted,		
			ommp101EthernetStatsPkts65to127OctsReceived,				
			ommp101EthernetStatsPkts128to255OctsTransmitted,		
			ommp101EthernetStatsPkts128to255OctsReceived,				
			ommp101EthernetStatsPkts256to511OctsTransmitted,		
			ommp101EthernetStatsPkts256to511OctsReceived,				
			ommp101EthernetStatsPkts512to1023OctsTransmitted,		
			ommp101EthernetStatsPkts512to1023OctsReceived,				
			ommp101EthernetStatsPkts1024to1518OctsTransmitted,		
			ommp101EthernetStatsPkts1024to1518OctsReceived,				
			ommp101EthernetStatsPkts1519toMaxOctsTransmitted,		
			ommp101EthernetStatsPkts1519toMaxOctsReceived,				
			ommp101EthernetStatsJabberTransmitted,			
			ommp101EthernetStatsJabberReceived,					
			ommp101EthernetStatsFragmentsTransmitted,
			ommp101EthernetStatsFragmentsReceived,	
			ommp101EthernetPauseControlFramesTransmitted,
			ommp101EthernetPauseControlFramesReceived,
			ommp101PerformanceTableRowStatus
		}
    STATUS  current
    DESCRIPTION
            "A collection of objects from RFC 1213 made current by this MIB module."
    ::= { utlrnd 2 }

	
END

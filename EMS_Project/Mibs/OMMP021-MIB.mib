--*****************************************************************************
--			MIB FILE FOR THE OMMP021 CARD
--*****************************************************************************

OMMP021-MIB DEFINITIONS ::= BEGIN
 
          IMPORTS
        	
		RowStatus      			FROM STANDARD-MIB
			
		DisplayString  			FROM RFC1213-MIB       
    	
    		OBJECT-IDENTITY,
    		NOTIFICATION-TYPE,
    		MODULE-IDENTITY,
    		Integer32,
    		Unsigned32,
    		IpAddress,
    		TimeTicks			FROM SNMPv2-SMI
	 
	 	OBJECT-TYPE    			FROM RFC-1212
	 		
		MODULE-COMPLIANCE,
		OBJECT-GROUP,
		NOTIFICATION-GROUP		FROM SNMPv2-CONF
	
		node,
		rack,
		subRack,
		slot				FROM SCC-MIB
    
		enterprises			FROM RFC1155-SMI
	;

 

	utl   MODULE-IDENTITY
            LAST-UPDATED    	"1807130630Z"
            ORGANIZATION    	"United Telecoms Limited, Bangalore-560048."
            CONTACT-INFO    	"Website: http://www.utlindia.com."                                           
            DESCRIPTION     	"MIB module for UTL 40/80 channel DWDM."
            REVISION 	    	"1807130630Z"
            DESCRIPTION    	"MIB module for OMMP021 Card."
            ::= { enterprises 18036 }

	utlrnd  OBJECT-IDENTITY
            STATUS  current
            DESCRIPTION "UTL Research and Development."
            ::= { utl 1 }

	dwdm 	OBJECT IDENTIFIER				::=	{ utlrnd 1 }
	indus 	OBJECT IDENTIFIER				::=	{ dwdm 1 }
	ommp021 	OBJECT IDENTIFIER 			::=	{ indus 91 }

	ommp021CardGeneralDetails OBJECT IDENTIFIER		::=	{ ommp021 1 }
	ommp021Configuration OBJECT IDENTIFIER 		::=	{ ommp021 2 }
	ommp021Alarm OBJECT IDENTIFIER 			::=	{ ommp021 3 }
	ommp021Performance OBJECT IDENTIFIER 		::=	{ ommp021 4 }
	ommp021Diagnostics OBJECT IDENTIFIER 		::=	{ ommp021 5 }

	ommp021AlarmQuery OBJECT IDENTIFIER			::=	{ ommp021Alarm 1 }
	ommp021AlarmNotification OBJECT IDENTIFIER		::=	{ ommp021Alarm 2 }

--*****************************************************************************
--				CARD GENERAL DETAILS
--*****************************************************************************

	ommp021CardGeneralDetailsTable OBJECT-TYPE
		SYNTAX  SEQUENCE OF Ommp021CardGeneralDetailsEntry 
		MAX-ACCESS  not-accessible
		STATUS  current
		DESCRIPTION
                     "Contains card general details' queries for the OMMP021 card"
		::= { ommp021CardGeneralDetails 1 }

	ommp021CardGeneralDetailsEntry  OBJECT-TYPE
		SYNTAX  Ommp021CardGeneralDetailsEntry 
		MAX-ACCESS  not-accessible
		STATUS  current
		DESCRIPTION 
              	""
		INDEX   { node, rack, subRack, slot, ommp021InterfaceNumber }
		::= { ommp021CardGeneralDetailsTable 1 }

	Ommp021CardGeneralDetailsEntry  ::= 
		SEQUENCE {
				ommp021InterfaceNumber					INTEGER,
				ommp021EepromCardId					        INTEGER,
				ommp021EepromCardName					DisplayString,
				ommp021EepromCardSerialNumber				DisplayString,
				ommp021EepromHardwareExternalReleaseVersion		        DisplayString,
				ommp021EepromHardwareInternalReleaseVersion		        DisplayString,
				ommp021SoftwareExternalReleaseVersion		        DisplayString,
				ommp021SoftwareInternalReleaseVersion		        DisplayString,
				ommp021CardGeneralDetailsTableRowStatus			RowStatus
			 }
	

	ommp021InterfaceNumber OBJECT-TYPE
		SYNTAX  INTEGER
		MAX-ACCESS  not-accessible
		STATUS  current
		DESCRIPTION
			"Interface number represents the port number.
			InterfaceNumber to port mapping is as follows:
			1 - CLIENT-1,
			2 - CLIENT-2,
			3 - CLIENT-3,
			4 - CLIENT-4,
			3 - LINE-
			-----------------------------
			For properties which do not apply on any interface,
			the interface number must be passed as 0
			-----------------------------"
		::= { ommp021CardGeneralDetailsEntry 1 }
	
	ommp021EepromCardId OBJECT-TYPE		 
		SYNTAX  INTEGER
		MAX-ACCESS  read-only
		STATUS current
		DESCRIPTION
			"Tells the card ID of the OMMP021 card, present in the EEPROM
			-----------------------------
			ommp021InterfaceNumber: 0
			-----------------------------"
		::= { ommp021CardGeneralDetailsEntry 2 }

	ommp021EepromCardName OBJECT-TYPE		 
		SYNTAX  DisplayString
		MAX-ACCESS  read-only
		STATUS current
		DESCRIPTION
			"Tells the card name of the OMMP021 card, present in the EEPROM
			-----------------------------
			ommp021InterfaceNumber: 0
			-----------------------------"
		::= { ommp021CardGeneralDetailsEntry 3 }

	ommp021EepromCardSerialNumber OBJECT-TYPE		 
		SYNTAX  DisplayString
		MAX-ACCESS  read-write
		STATUS current
		DESCRIPTION
			"This property get / set the information about 
			OMMP021 Card's Serial Number.
			-----------------------------
			ommp021InterfaceNumber: 0
			-----------------------------
			Values:
			eg: 123456
			-----------------------------"
		::= { ommp021CardGeneralDetailsEntry 4 }

	ommp021EepromHardwareExternalReleaseVersion OBJECT-TYPE		 
		SYNTAX  DisplayString
		MAX-ACCESS  read-only
		STATUS current
		DESCRIPTION
			"Gets the Card's Hardware External Release Version. 
			This detail will be displayed to the customer.
			This version will increment only if there are significant
			architectural changes in the product
			-----------------------------
			ommp021InterfaceNumber: 0
			-----------------------------
			Value:
			eg: 0.1
			-----------------------------"
		::= { ommp021CardGeneralDetailsEntry 5 }
	
	ommp021EepromHardwareInternalReleaseVersion OBJECT-TYPE		 
		SYNTAX  DisplayString
		MAX-ACCESS  read-only
		STATUS current
		DESCRIPTION
			"Gets the Card's Hardware Internal Release Version.
			This detail is used for development purposes only.
			It differs from the external hardware version.
			-----------------------------
			ommp101InterfaceNumber: 0
			-----------------------------
			Value:
			eg: 4.1
			-----------------------------"
		::= { ommp021CardGeneralDetailsEntry 6 }

	ommp021SoftwareExternalReleaseVersion OBJECT-TYPE		 
		SYNTAX  DisplayString
		MAX-ACCESS  read-only
		STATUS current
		DESCRIPTION
			"Gets the Card's Software External Release Version. 
			This detail will be displayed to the customer.
			This version will increment only if there are
			significant architectural changes in the product
			-----------------------------
			ommp021InterfaceNumber: 0
			-----------------------------
			Value:
			eg: 0.1
			-----------------------------"
		::= { ommp021CardGeneralDetailsEntry 7 }
		
	ommp021SoftwareInternalReleaseVersion OBJECT-TYPE		 
		SYNTAX  DisplayString
		MAX-ACCESS  read-only
		STATUS current
		DESCRIPTION
			"Gets the Card's Software Internal Release Version.
			This detail is used for development purposes only.
			It differs from the external software version.
		      	-----------------------------
			ommp101InterfaceNumber: 0
			-----------------------------
			Value:
			eg: 5.1
			-----------------------------"
		::= { ommp021CardGeneralDetailsEntry 8 }

	ommp021CardGeneralDetailsTableRowStatus OBJECT-TYPE
              SYNTAX      RowStatus
              MAX-ACCESS  read-write
              STATUS      current
              DESCRIPTION
			"*****************************
			This is MIB realted property,
			NOT to be considered as a card property
			*****************************"
              ::= { ommp021CardGeneralDetailsEntry 9 }

--*****************************************************************************
--				   CONFIGURATION
--*****************************************************************************

	ommp021ConfigurationTable OBJECT-TYPE
		SYNTAX  SEQUENCE OF Ommp021ConfigurationEntry 
		MAX-ACCESS  not-accessible
		STATUS  current
		DESCRIPTION
		      "Contains configuration queries of the OMMP021 card"
		::= { ommp021Configuration 1 }

	ommp021ConfigurationEntry  OBJECT-TYPE
              SYNTAX  Ommp021ConfigurationEntry 
              MAX-ACCESS  not-accessible
              STATUS  current
              DESCRIPTION 
              	""
		INDEX   { node, rack, subRack, slot, ommp021InterfaceNumber }
		::= { ommp021ConfigurationTable 1 }
	
	Ommp021ConfigurationEntry  ::= 
		SEQUENCE {
				ommp021CardSoftwareUpgrade					DisplayString,
				ommp021CardSoftReset						INTEGER,
				ommp021CardFactoryReset					INTEGER,
				ommp021SyncSystemTimeWithNtpServer				DisplayString,
				ommp021SyncRtcWithNtpServer						DisplayString,
				ommp021SyncRtcWithSystemTime						DisplayString,
				ommp021UpdateGivenTimeIntoSystem					DisplayString,
				ommp021UpdateGivenTimeIntoRtc					DisplayString,
				ommp021SystemTimeAndRtcTime						DisplayString,
				ommp021TrafficConfiguration					INTEGER,
				ommp021LoopbackState						INTEGER,
				ommp021ClearSignalPerformance				INTEGER,
				ommp021AlsState						INTEGER,
				ommp021AlsPulseRepetitionTime				INTEGER,
				ommp021OtuFecConfiguration					INTEGER,
				ommp021OtuSignalFailThreshold				INTEGER,
				ommp021OtuSignalDegradeThreshold				INTEGER,
				ommp021OtuSapiTransmitTraceMessage				DisplayString,
				ommp021OtuDapiTransmitTraceMessage				DisplayString,
				ommp021OtuOperatorSpecificTransmitTraceMessage		DisplayString,
				ommp021OtuSapiExpectedTraceMessage				DisplayString,
				ommp021OtuDapiExpectedTraceMessage				DisplayString,
				ommp021OtuOperatorSpecificExpectedTraceMessage		DisplayString,
				ommp021OduSignalFailThreshold				INTEGER,
				ommp021OduSignalDegradeThreshold				INTEGER,
				ommp021OduSapiTransmitTraceMessage				DisplayString,
				ommp021OduDapiTransmitTraceMessage				DisplayString,
				ommp021OduOperatorSpecificTransmitTraceMessage		DisplayString,
				ommp021OduSapiExpectedTraceMessage				DisplayString,
				ommp021OduDapiExpectedTraceMessage				DisplayString,
				ommp021OduOperatorSpecificExpectedTraceMessage		DisplayString,
				ommp021TunableCfp2LaserWavelength				INTEGER,
				ommp021Cfp2LaserState						INTEGER,	
				ommp021Qsfp28LaserState						INTEGER,
				ommp021TunableCfp2WavelengthGridSpacing				INTEGER,								
				ommp021Cfp2InputPowerFailureAlarmSeverity			DisplayString,
				ommp021Cfp2OutputPowerFailureAlarmSeverity			DisplayString,
				ommp021Cfp2HighTemperatureAlarmSeverity			DisplayString,
				ommp021Cfp2LowTemperatureAlarmSeverity			DisplayString,
				ommp021Cfp2InputHighPowerAlarmSeverity			DisplayString,
				ommp021Cfp2InputLowPowerAlarmSeverity				DisplayString,
				ommp021Cfp2OutputHighPowerAlarmSeverity			DisplayString,
				ommp021Cfp2OutputLowPowerAlarmSeverity			DisplayString,
				ommp021Cfp2HighSupplyVoltageAlarmSeverity			DisplayString,
				ommp021Cfp2LowSupplyVoltageAlarmSeverity			DisplayString,
				ommp021Cfp2PresenceAbsenceNotificationSeverity		DisplayString,
				ommp021Qsfp28InputPowerFailureAlarmSeverity			DisplayString,
				ommp021Qsfp28OutputPowerFailureAlarmSeverity			DisplayString,
				ommp021Qsfp28HighTemperatureAlarmSeverity			DisplayString,
				ommp021Qsfp28LowTemperatureAlarmSeverity			DisplayString,
				ommp021Qsfp28HighBiasCurrentAlarmSeverity			DisplayString,
				ommp021Qsfp28LowBiasCurrentAlarmSeverity			DisplayString,
				ommp021Qsfp28InputHighPowerAlarmSeverity			DisplayString,
				ommp021Qsfp28InputLowPowerAlarmSeverity				DisplayString,
				ommp021Qsfp28OutputHighPowerAlarmSeverity			DisplayString,
				ommp021Qsfp28OutputLowPowerAlarmSeverity			DisplayString,
				ommp021Qsfp28HighSupplyVoltageAlarmSeverity			DisplayString,
				ommp021Qsfp28LowSupplyVoltageAlarmSeverity			DisplayString,
				ommp021Qsfp28PresenceAbsenceNotificationSeverity		DisplayString,
				ommp021OtuLossOfSignalAlarmSeverity				DisplayString,
				ommp021OtuLossOfFrameAlarmSeverity				DisplayString,
				ommp021OtuOutOfFrameAlarmSeverity				DisplayString,
				ommp021OtuOutOfMultiFrameAlarmSeverity			DisplayString,
				ommp021OtuSignalDegradeAlarmSeverity				DisplayString,
				ommp021OtuAlarmIndicationSignalAlarmSeverity			DisplayString,
				ommp021OtuIncomingAlignmentErrorAlarmSeverity			DisplayString,
				ommp021OtuTrailTraceIdentifierMismatchAlarmSeverity		DisplayString,
				ommp021OtuBackwardIncomingAlignmentErrorAlarmSeverity		DisplayString,
				ommp021OtuBackwardDefectIndicationAlarmSeverity		DisplayString,
				ommp021OduSignalDegradeAlarmSeverity				DisplayString,
				ommp021OduAlarmIndicationSignalAlarmSeverity			DisplayString,
				ommp021OduTrailTraceIdentifierMismatchAlarmSeverity		DisplayString,
				ommp021OduLockedDefectAlarmSeverity				DisplayString,
				ommp021OduOpenConnectionIndicationAlarmSeverity		DisplayString,
				ommp021OduBackwardDefectIndicationAlarmSeverity		DisplayString,
				ommp021OpuPayloadMismatchAlarmSeverity				DisplayString,
				ommp021EthernetLossOfSignalAlarmSeverity				DisplayString,
				ommp021EthernetIngressRemoteFaultAlarmSeverity			DisplayString,
				ommp021EthernetEgressRemoteFaultAlarmSeverity			DisplayString,
				ommp021EthernetEgressHighBerAlarmSeverity			DisplayString,
				ommp021EthernetEgressLocalFaultAlarmSeverity			DisplayString,
				ommp021LineOtuSignalFailThreshold				INTEGER,
				ommp021LineOtuSignalDegradeThreshold				INTEGER,
				ommp021LineOtuSapiTransmitTraceMessage				DisplayString,
				ommp021LineOtuDapiTransmitTraceMessage				DisplayString,
				ommp021LineOtuOperatorSpecificTransmitTraceMessage		DisplayString,
				ommp021LineOtuSapiExpectedTraceMessage				DisplayString,
				ommp021LineOtuDapiExpectedTraceMessage				DisplayString,
				ommp021LineOtuOperatorSpecificExpectedTraceMessage		DisplayString,
				ommp021LineOduSignalFailThreshold				INTEGER,
				ommp021LineOduSignalDegradeThreshold				INTEGER,
				ommp021LineOduSapiTransmitTraceMessage				DisplayString,
				ommp021LineOduDapiTransmitTraceMessage				DisplayString,
				ommp021LineOduOperatorSpecificTransmitTraceMessage		DisplayString,
				ommp021LineOduSapiExpectedTraceMessage				DisplayString,
				ommp021LineOduDapiExpectedTraceMessage				DisplayString,
				ommp021LineOduOperatorSpecificExpectedTraceMessage		DisplayString,
				ommp021LineOtuLossOfSignalAlarmSeverity				DisplayString,
				ommp021LineOtuLossOfFrameAlarmSeverity				DisplayString,
				ommp021LineOtuOutOfFrameAlarmSeverity				DisplayString,
				ommp021LineOtuOutOfMultiFrameAlarmSeverity			DisplayString,
				ommp021LineOtuSignalDegradeAlarmSeverity				DisplayString,
				ommp021LineOtuAlarmIndicationSignalAlarmSeverity			DisplayString,
				ommp021LineOtuIncomingAlignmentErrorAlarmSeverity			DisplayString,
				ommp021LineOtuTrailTraceIdentifierMismatchAlarmSeverity		DisplayString,
				ommp021LineOtuBackwardIncomingAlignmentErrorAlarmSeverity		DisplayString,
				ommp021LineOtuBackwardDefectIndicationAlarmSeverity		DisplayString,
				ommp021LineOduSignalDegradeAlarmSeverity				DisplayString,
				ommp021LineOduAlarmIndicationSignalAlarmSeverity			DisplayString,
				ommp021LineOduTrailTraceIdentifierMismatchAlarmSeverity		DisplayString,
				ommp021LineOduLockedDefectAlarmSeverity				DisplayString,
				ommp021LineOduOpenConnectionIndicationAlarmSeverity		DisplayString,
				ommp021LineOduBackwardDefectIndicationAlarmSeverity		DisplayString,
				ommp021LineOpuPayloadMismatchAlarmSeverity			DisplayString,
				ommp021ConfigurationTableRowStatus				RowStatus
			}
		
	ommp021CardSoftwareUpgrade OBJECT-TYPE		 
		SYNTAX  DisplayString
		MAX-ACCESS read-write
		STATUS current
		DESCRIPTION
			"Valid only as SET command.
			This property upgrades the software of the OMMP021 card
			It takes the path of the software release as
			a value
			-----------------------------
			ommp021InterfaceNumber: 0
			-----------------------------
			Values:
			eg: /root/home/rel-2.0.0.tar.gz
			-----------------------------"
		::= { ommp021ConfigurationEntry 1 }

	ommp021CardSoftReset OBJECT-TYPE		 
		SYNTAX  INTEGER
		MAX-ACCESS read-write
		STATUS current
		DESCRIPTION
			"Valid only as a SET command.
			Reboots the Card, Reconfigures the Card 
			i.e All Configuration Parameter	like Laser State,
			Traffic configuration, Loopback, FEC, optical and 
			signal thresholds, switching mode,
			user choice of line path, auto-negotiation, 
			TTI messages will be restored to previous state
			-----------------------------
			ommp021InterfaceNumber: 0
			-----------------------------
			Values:
			Dont care, any value
			eg: 0
			-----------------------------"
		::= { ommp021ConfigurationEntry 2 }

	ommp021CardFactoryReset OBJECT-TYPE		 
		SYNTAX  INTEGER
		MAX-ACCESS read-write
		STATUS current
		DESCRIPTION
			"Valid only as a SET command.
			Sets the Card To Factory Default State
			i.e All User Configuration Parameters like Laser State,
			Traffic configuration, Loopback, FEC, optical and 
			signal thresholds, switching mode,
			user choice of line path, auto-negotiation, TTI messages
			will be set to default state
			-----------------------------
			ommp021InterfaceNumber: 0
			-----------------------------
			Values:
			Dont care, any value
			eg: 0
			-----------------------------"
		::= { ommp021ConfigurationEntry 3 }
		
	ommp021SyncSystemTimeWithNtpServer OBJECT-TYPE		 
		SYNTAX  DisplayString
		MAX-ACCESS read-write
		STATUS current
		DESCRIPTION
			" when we want to manually sync the time value
			present in linux kernel with the NTP server
			we can use this OID. We can provide NTP server
			ip address as a value to this OID and the time
			will be synced to that ilarticular server. 
			If we are not providing NTP server IP address 
			then the system will be synced with the NTP server 
			which is already been registered with card. 
			If both are absent then error message will be returned
			-----------------------------
			Interface : 0
			-----------------------------
			If we want to provide NTP server IP address then
			Value should be a valid IP address as shown below
			: 192.168.021.25
			
			If we don't want to provide NTP server address then no
			need to pass any value. 
			---------------------------"
		::= { ommp021ConfigurationEntry 4 }

	ommp021SyncRtcWithNtpServer OBJECT-TYPE		 
		SYNTAX  DisplayString
		MAX-ACCESS  read-write
		STATUS current
		DESCRIPTION
			" when we want to manually sync the time value
			present in RTC with the NTP server
			we can use this OID. We can provide NTP server
			ip address as a value to this OID and the time
			will be synced to that particular server. 
			If we are not providing NTP server IP address 
			then the system will be synced with the NTP server 
			which is already been registered with card. 
			If both are absent then error message will be returned.
			-----------------------------
			Interface : 0
			-----------------------------
			If we want to provide NTP server IP address then
			Value should be a valid IP address as shown below
			: 192.168.021.25
			
			If we don't want to provide NTP server address, then no
			need to ilass any value. 
			---------------------------"
		::= { ommp021ConfigurationEntry 5 }

	ommp021SyncRtcWithSystemTime OBJECT-TYPE		 
		SYNTAX  DisplayString
		MAX-ACCESS  read-write
		STATUS current
		DESCRIPTION
			" when we want to manually sync the time value
			present in RTC with the time value in linux kernel
			we can use this OID. With this set operation, 
			the time available with linux kernel will be updated
			into RTC. It is not required to provide any value for 
			this operation"
		::= { ommp021ConfigurationEntry 6 }

	ommp021UpdateGivenTimeIntoSystem OBJECT-TYPE		 
		SYNTAX  DisplayString
		MAX-ACCESS  read-write
		STATUS current
		DESCRIPTION
			" when we want to manually update system time
			with the user provided time, we can use this OID.
			With OID we need to provide time value which we
			want to update in the system.
			-----------------------------
			Interface : 0
			-----------------------------
			Value should be of given format:
			YYYY-MM-DD H:M:S
			
			Example: 2017-10-31 15:20:44
			---------------------------"
		::= { ommp021ConfigurationEntry 7 }

	ommp021UpdateGivenTimeIntoRtc OBJECT-TYPE		 
		SYNTAX  DisplayString
		MAX-ACCESS  read-write
		STATUS current
		DESCRIPTION
			" when we want to manually update RTC time
			with the user provided time, we can use this OID.
			With OID we need to provide time value which we
			want to update in RTC.
			-----------------------------
			Interface : 0
			-----------------------------
			Value should be of given format:
			YYYY-MM-DD H:M:S
			
			Example: 2017-10-31 15:20:44
			---------------------------"
		::= { ommp021ConfigurationEntry 8 }

	ommp021SystemTimeAndRtcTime OBJECT-TYPE		 
		SYNTAX  DisplayString
		MAX-ACCESS read-only
		STATUS current
		DESCRIPTION
			" get the system time and time value present in RTC.
			-----------------------------
			Interface : 0
			-----------------------------"
		::= { ommp021ConfigurationEntry 9 }

		
	ommp021TrafficConfiguration OBJECT-TYPE		 
		SYNTAX  INTEGER
		MAX-ACCESS read-write
		STATUS current
		DESCRIPTION
			"Set or get the traffic for the
			requested port
			----------------------------------------
			ommp021InterfaceNumber:
			CLIENT-1
			CLIENT-2
			LINE-3
			----------------------------------------			
			Value: 
			For client
			00 - Un-configure 
			01 - OTU4
			02 - 100GbE
			For line
			03 - OTUC2 (200G Line)
			-----------------------------"
		::= { ommp021ConfigurationEntry 10 }

	ommp021LoopbackState OBJECT-TYPE		 
		SYNTAX  INTEGER
		MAX-ACCESS read-write
		STATUS current
		DESCRIPTION
			"Set or get the loopback state for the
			requested port
			----------------------------------------
			If line side module is CFP2(Finisar-200G)
			Client Near end loopback can be configured
			Client Far end loopback is not supported
			Line near end loopback is not supported
			Line far end loopback can be configured
			----------------------------------------
			If line side module is CFP2-DCO(Lumentum,etc)
			Both near end loopback and far end loopback can be configured on client
			Both near end loopback and far end loopback can be configured on line			
			-----------------------------
			ommp021InterfaceNumber:
			CLIENT-1
			CLIENT-2
			LINE-3
			-----------------------------
			Values: 
			00 - No Loopback   
			01 - Near End Loopback
			02 - Far End Loopback
			-----------------------------"
		::= { ommp021ConfigurationEntry 11 }

	ommp021ClearSignalPerformance OBJECT-TYPE		 
		SYNTAX  INTEGER
		MAX-ACCESS read-write
		STATUS current
		DESCRIPTION
			"Valid only as a SET command.
			Clears signal performance for the requested port
			-----------------------------
			ommp021InterfaceNumber:
			CLIENT-1
			CLIENT-2
			LINE-3
			-----------------------------
			Values:
			Dont care, any value
			eg: 0
			-----------------------------"
		::= { ommp021ConfigurationEntry 12 }

	ommp021AlsState OBJECT-TYPE		 
		SYNTAX  INTEGER
		MAX-ACCESS read-write
		STATUS current
		DESCRIPTION
			"Set the Automatic Laser Switching(ALS) mode for
			for requested port. Based on the RX LOS state of the
			port, the transmit LASER state will be controlled
			according to the algorithm defined for ALS in
			ITUT 664 Standard
			-----------------------------
			ommp021InterfaceNumber:
			CLIENT-1
			CLIENT-2
			LINE-3
			-----------------------------
			Values: 
			1 - Enable ALS state
			0 - Disable ALS state
			-----------------------------" 
		::= { ommp021ConfigurationEntry 13 }

	ommp021AlsPulseRepetitionTime OBJECT-TYPE		 
		SYNTAX  INTEGER
		MAX-ACCESS read-write
		STATUS current
		DESCRIPTION
			"Pulse repetition time is the time for automatic 
			restart of CFP2 LASER once the ALS algorithm starts.
			-----------------------------
			ommp021InterfaceNumber:
			CLIENT-1
			CLIENT-2
			LINE-3
			-----------------------------
			Values: 
			1 seconds to 300 seconds
			-----------------------------"
		::= { ommp021ConfigurationEntry 14 }

	ommp021OtuFecConfiguration OBJECT-TYPE		 
		SYNTAX  INTEGER
		MAX-ACCESS read-write
		STATUS current
		DESCRIPTION
			"Set or Get FEC type for requested port configured with
			 OTU4/OTUC2 traffic.  
			----------------------------------------
			If line side module is CFP2(Finisar-200G)
			Fec O-FEC supported on line side(OpenRoadm)
			Fec G-FEC supported on client side
			-----------------------------
			ommp021InterfaceNumber:
			CLIENT-1
			CLIENT-2
			LINE-3
			-----------------------------
			Values: 
			01 - OTU-4 G.709 FEC
			02 - O-FEC
			-----------------------------"
		::= { ommp021ConfigurationEntry 15 }

	ommp021OtuSignalFailThreshold OBJECT-TYPE		 
		SYNTAX  INTEGER
		MAX-ACCESS read-write
		STATUS current
		DESCRIPTION
			"Set or Get SM Signal Failure 
			Threshold value for the requested port configured with 
			OTU4/OTUC2 traffic.
			-----------------------------
			ommp021InterfaceNumber:
			CLIENT-1
			CLIENT-2
			LINE-3
			-----------------------------
			Values: 
			03 - 1.E -03
			04 - 1.E -04
			05 - 1.E -05
			-----------------------------" 
		::= { ommp021ConfigurationEntry 16 }

	ommp021OtuSignalDegradeThreshold OBJECT-TYPE		 
		SYNTAX  INTEGER
		MAX-ACCESS read-write
		STATUS current
		DESCRIPTION
			"Set or Get SM Signal Degrade 
			Threshold value for the requested port configured with 
			OTU4/OTUC2 traffic.
			-----------------------------
			ommp021InterfaceNumber:
			CLIENT-1
			CLIENT-2
			LINE-3
			-----------------------------
			Values:
			06 - 1.E -06
			07 - 1.E -07
			08 - 1.E -08
			09 - 1.E -09
			10 - 1.E -10(for line only)
			-----------------------------"
		::= { ommp021ConfigurationEntry 17 }

	ommp021OtuSapiTransmitTraceMessage OBJECT-TYPE
		SYNTAX DisplayString
		MAX-ACCESS read-write
		STATUS current
		DESCRIPTION
			"Set or get the 15 characters SAPI Transmit TTI message
			which is put into the outgoing OTU4/OTUC2 frame. 
			-----------------------------
			ommp021InterfaceNumber:
			CLIENT-1
			CLIENT-2
			LINE-3
			-----------------------------
			Values:
			eg: 123451234512345
			-----------------------------" 
		::= { ommp021ConfigurationEntry 18 }

	ommp021OtuDapiTransmitTraceMessage OBJECT-TYPE
		SYNTAX DisplayString
		MAX-ACCESS read-write
		STATUS current
		DESCRIPTION
			"Set or get the 15 characters DAPI Transmit TTI message
			which is put into the outgoing OTU4/OTUC2 frame. 
			-----------------------------
			ommp021InterfaceNumber:
			CLIENT-1
			CLIENT-2
			LINE-3
			-----------------------------
			Values:
			eg: 123451234512345
			-----------------------------" 
		::= { ommp021ConfigurationEntry 19 }
		
	ommp021OtuOperatorSpecificTransmitTraceMessage OBJECT-TYPE
		SYNTAX DisplayString
		MAX-ACCESS read-write
		STATUS current
		DESCRIPTION
			"Set or get the 32 characters Operator Specific Transmit
			TTI message which is put into the outgoing OTU4/OTUC2
			frame. 
			-----------------------------
			ommp021InterfaceNumber:
			CLIENT-1
			CLIENT-2
			LINE-3
			-----------------------------
			Values:
			eg: 12345123451234512345123451234500
			-----------------------------" 
		::= { ommp021ConfigurationEntry 20 }
		
	ommp021OtuSapiExpectedTraceMessage OBJECT-TYPE
		SYNTAX DisplayString
		MAX-ACCESS read-write
		STATUS current
		DESCRIPTION
			"15 characters SM SAPI Expected TTI message - Message
			set here is used for comparison with the message present
			in SM SAPI field of the incoming OTU4/OTUC2 frames.
			-----------------------------
			ommp021InterfaceNumber:
			CLIENT-1
			CLIENT-2
			LINE-3
			-----------------------------
			Values:
			eg: 123451234512345
			-----------------------------" 
		::= { ommp021ConfigurationEntry 21 }
		
	ommp021OtuDapiExpectedTraceMessage OBJECT-TYPE
		SYNTAX DisplayString
		MAX-ACCESS read-write
		STATUS current
		DESCRIPTION
			"15 characters SM DAPI Expected TTI message - Message
			set here is used for comparison with the message present
			in SM DAPI field of the incoming OTU4/OTUC2 frames.
			-----------------------------
			ommp021InterfaceNumber:
			CLIENT-1
			CLIENT-2
			LINE-3
			-----------------------------
			Values:
			eg: 123451234512345
			-----------------------------" 
		::= { ommp021ConfigurationEntry 22 }

	ommp021OtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU4/OTUC2 frames.
			-----------------------------
			ommp021InterfaceNumber:
			CLIENT-1
			CLIENT-2
			LINE-3
			-----------------------------
			Values:
			eg: 12345123451234512345123451234500
			-----------------------------" 
		::= { ommp021ConfigurationEntry 23 }

	ommp021OduSignalFailThreshold OBJECT-TYPE		 
		SYNTAX  INTEGER
		MAX-ACCESS read-write
		STATUS current
		DESCRIPTION
			"Set or Get PM Signal Failure 
			Threshold value for the requested port configured with 
			OTU4/OTUC2 traffic.
			-----------------------------
			ommp021InterfaceNumber:
			CLIENT-1
			CLIENT-2
			LINE-3
			-----------------------------
			Values: 
			03 - 1.E -03
			04 - 1.E -04
			05 - 1.E -05
			-----------------------------" 
		::= { ommp021ConfigurationEntry 24 }

	ommp021OduSignalDegradeThreshold OBJECT-TYPE		 
		SYNTAX  INTEGER
		MAX-ACCESS read-write
		STATUS current
		DESCRIPTION
			"Set or Get PM Signal Degrade 
			Threshold value for the requested port configured with 
			OTU4/OTUC2 traffic.
			-----------------------------
			ommp021InterfaceNumber:
			CLIENT-1
			CLIENT-2
			LINE-3
			-----------------------------
			Values: 
			06 - 1.E -06
			07 - 1.E -07
			08 - 1.E -08
			09 - 1.E -09
			10 - 1.E -10(for line only)
			-----------------------------" 
		::= { ommp021ConfigurationEntry 25 }

	ommp021OduSapiTransmitTraceMessage OBJECT-TYPE
		SYNTAX DisplayString
		MAX-ACCESS read-write
		STATUS current
		DESCRIPTION
			"Set or get the 15 characters SAPI Transmit TTI message
			which is put into the outgoing OTU4/OTUC2
			frame at the PM level. 
			-----------------------------
			ommp021InterfaceNumber:
			CLIENT-1
			CLIENT-2
			LINE-3
			-----------------------------
			Values:
			eg: 123451234512345
			-----------------------------" 
		::= { ommp021ConfigurationEntry 26 }
		
	ommp021OduDapiTransmitTraceMessage OBJECT-TYPE
		SYNTAX DisplayString
		MAX-ACCESS read-write
		STATUS current
		DESCRIPTION
			"Set or get the 15 characters DAPI Transmit TTI message
			which is put into the outgoing OTU4/OTUC2
			frame at the PM level. 
			-----------------------------
			ommp021InterfaceNumber:
			CLIENT-1
			CLIENT-2
			LINE-3
			-----------------------------
			Values:
			eg: 123451234512345
			-----------------------------" 
		::= { ommp021ConfigurationEntry 27 }
		
	ommp021OduOperatorSpecificTransmitTraceMessage OBJECT-TYPE
		SYNTAX DisplayString
		MAX-ACCESS read-write
		STATUS current
		DESCRIPTION
			"Set or get the 32 characters Operator Specific Transmit
			TTI message which is put into the outgoing OTU4/OTUC2
			frame at the PM level. 
			-----------------------------
			ommp021InterfaceNumber:
			CLIENT-1
			CLIENT-2
			LINE-3
			-----------------------------
			Values:
			eg: 12345123451234512345123451234500
			-----------------------------" 
		::= { ommp021ConfigurationEntry 28 }
		
	ommp021OduSapiExpectedTraceMessage OBJECT-TYPE
		SYNTAX DisplayString
		MAX-ACCESS read-write
		STATUS current
		DESCRIPTION
			"15 characters PM SAPI Expected TTI message - Message
			set here is used for comparison with the message present
			in PM SAPI field of the incoming OTU4/OTUC2 frames.
			-----------------------------
			ommp021InterfaceNumber:
			CLIENT-1
			CLIENT-2
			LINE-3
			-----------------------------
			Values:
			eg: 123451234512345
			-----------------------------" 
		::= { ommp021ConfigurationEntry 29 }

	ommp021OduDapiExpectedTraceMessage OBJECT-TYPE
		SYNTAX DisplayString
		MAX-ACCESS read-write
		STATUS current
		DESCRIPTION
			"15 characters PM DAPI Expected TTI message - Message
			set here is used for comparison with the message present
			in PM DAPI field of the incoming OTU4/OTUC2 frames.
			-----------------------------
			ommp021InterfaceNumber:
			CLIENT-1
			CLIENT-2
			LINE-3
			-----------------------------
			Values:
			eg: 123451234512345
			-----------------------------" 
		::= { ommp021ConfigurationEntry 30 }
		
	ommp021OduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU4/OTUC2 frames.
			-----------------------------
			ommp021InterfaceNumber:
			CLIENT-1
			CLIENT-2
			LINE-3
			-----------------------------
			Values:
			eg: 12345123451234512345123451234500
			-----------------------------" 
		::= { ommp021ConfigurationEntry 31 }

	ommp021TunableCfp2LaserWavelength OBJECT-TYPE		 
		SYNTAX  INTEGER
		MAX-ACCESS read-write
		STATUS current
		DESCRIPTION
			"Set or Get the CFP2 wavelength for the requested port
			-----------------------------
			ommp021InterfaceNumber:
			3 - LINE-
			-----------------------------
			Values:
			eg: 1529.944
			-----------------------------"
		::= { ommp021ConfigurationEntry 32 }

	ommp021Cfp2LaserState OBJECT-TYPE		 
		SYNTAX  INTEGER
		MAX-ACCESS read-write
		STATUS current
		DESCRIPTION
			"Set or Get the CFP2 LASER state for the the requested
			port
			-----------------------------
			ommp021InterfaceNumber:
			3 - LINE-
			-----------------------------
			Values: 
			00 - Laser OFF
			01 - Laser ON
			-----------------------------"
		::= { ommp021ConfigurationEntry 33 }

	ommp021Qsfp28LaserState OBJECT-TYPE		 
		SYNTAX  INTEGER
		MAX-ACCESS read-write
		STATUS current
		DESCRIPTION
			"Set or Get the QSFP28 LASER state for the the requested
			port
			-----------------------------
			ommp021InterfaceNumber:
			CLIENT-1
			CLIENT-2
			LINE-3
			-----------------------------
			Values: 
			01 - Laser ON
			00 - Laser OFF
			-----------------------------" 
		::= { ommp021ConfigurationEntry 34 }
		
	ommp021TunableCfp2WavelengthGridSpacing  OBJECT-TYPE
		SYNTAX  INTEGER
		MAX-ACCESS  read-write
		STATUS  current
		DESCRIPTION
			"This property gives difference in the wavelength
			between two channels In GHz.
			-----------------------------
			ommp021InterfaceNumber:
			3 - LINE-
			-----------------------------
			Values:
			eg: 100
			-----------------------------"
	::= { ommp021ConfigurationEntry 35 }

	ommp021Cfp2InputPowerFailureAlarmSeverity OBJECT-TYPE
		SYNTAX  DisplayString
		MAX-ACCESS  read-write
		STATUS  current
		DESCRIPTION
			"Set or Get the alarm severity level of the
			OMMP021 CFP2 Input Power Failure Alarm   
			for requested port
			-----------------------------
			ommp021InterfaceNumber:
			3 - LINE-
			-----------------------------
			Value:
			critical
			major
			minor
			deferred
			---------------------------"
	::= { ommp021ConfigurationEntry 36 }

	ommp021Cfp2OutputPowerFailureAlarmSeverity OBJECT-TYPE
		SYNTAX  DisplayString
		MAX-ACCESS  read-write
		STATUS  current
		DESCRIPTION
			"Set or Get the alarm severity level of the
			OMMP021 CFP2 Output Power Failure Alarm   
			for requested port
			-----------------------------
			ommp021InterfaceNumber:
			3 - LINE-
			-----------------------------
			Value:
			critical
			major
			minor
			deferred
			---------------------------"
	::= { ommp021ConfigurationEntry 37 }

	ommp021Cfp2HighTemperatureAlarmSeverity OBJECT-TYPE
		SYNTAX  DisplayString
		MAX-ACCESS  read-write
		STATUS  current
		DESCRIPTION
			"Set or Get the alarm severity level of the
			OMMP021 CFP2 High Temperature Alarm   
			for requested port
			-----------------------------
			ommp021InterfaceNumber:
			3 - LINE-
			-----------------------------
			Value:
			critical
			major
			minor
			deferred
			---------------------------"
	::= { ommp021ConfigurationEntry 38 }

	ommp021Cfp2LowTemperatureAlarmSeverity OBJECT-TYPE
		SYNTAX  DisplayString
		MAX-ACCESS  read-write
		STATUS  current
		DESCRIPTION
			"Set or Get the alarm severity level of the
			OMMP021 CFP2 Low Temperature Alarm   
			for requested port
			-----------------------------
			ommp021InterfaceNumber:
			3 - LINE-
			-----------------------------
			Value:
			critical
			major
			minor
			deferred
			---------------------------"
	::= { ommp021ConfigurationEntry 39 }

	ommp021Cfp2InputHighPowerAlarmSeverity OBJECT-TYPE
		SYNTAX  DisplayString
		MAX-ACCESS  read-write
		STATUS  current
		DESCRIPTION
			"Set or Get the alarm severity level of the
			OMMP021 CFP2 Input High Power Alarm   
			for requested port
			-----------------------------
			ommp021InterfaceNumber:
			3 - LINE-
			-----------------------------
			Value:
			critical
			major
			minor
			deferred
			---------------------------"
	::= { ommp021ConfigurationEntry 40 }

	ommp021Cfp2InputLowPowerAlarmSeverity OBJECT-TYPE
		SYNTAX  DisplayString
		MAX-ACCESS  read-write
		STATUS  current
		DESCRIPTION
			"Set or Get the alarm severity level of the
			OMMP021 CFP2 Input Low Power Alarm   
			for requested port
			-----------------------------
			ommp021InterfaceNumber:
			3 - LINE-
			-----------------------------
			Value:
			critical
			major
			minor
			deferred
			---------------------------"
	::= { ommp021ConfigurationEntry 41 }

	ommp021Cfp2OutputHighPowerAlarmSeverity OBJECT-TYPE
		SYNTAX  DisplayString
		MAX-ACCESS  read-write
		STATUS  current
		DESCRIPTION
			"Set or Get the alarm severity level of the
			OMMP021 CFP2 Output High Power Alarm   
			for requested port
			-----------------------------
			ommp021InterfaceNumber:
			3 - LINE-
			-----------------------------
			Value:
			critical
			major
			minor
			deferred
			---------------------------"
	::= { ommp021ConfigurationEntry 42 }

	ommp021Cfp2OutputLowPowerAlarmSeverity OBJECT-TYPE
		SYNTAX  DisplayString
		MAX-ACCESS  read-write
		STATUS  current
		DESCRIPTION
			"Set or Get the alarm severity level of the
			OMMP021 CFP2 Output Low Power Alarm   
			for requested port
			-----------------------------
			ommp021InterfaceNumber:
			3 - LINE-
			-----------------------------
			Value:
			critical
			major
			minor
			deferred
			---------------------------"
	::= { ommp021ConfigurationEntry 43 }

	ommp021Cfp2HighSupplyVoltageAlarmSeverity OBJECT-TYPE
		SYNTAX  DisplayString
		MAX-ACCESS  read-write
		STATUS  current
		DESCRIPTION
			"Set or Get the alarm severity level of the
			OMMP021 CFP2 High Supply Voltage Alarm   
			for requested port
			-----------------------------
			ommp021InterfaceNumber:
			3 - LINE-
			-----------------------------
			Value:
			critical
			major
			minor
			deferred
			---------------------------"
	::= { ommp021ConfigurationEntry 44 }

	ommp021Cfp2LowSupplyVoltageAlarmSeverity OBJECT-TYPE
		SYNTAX  DisplayString
		MAX-ACCESS  read-write
		STATUS  current
		DESCRIPTION
			"Set or Get the alarm severity level of the
			OMMP021 CFP2 Low Supply Voltage Alarm   
			for requested port
			-----------------------------
			ommp021InterfaceNumber:
			3 - LINE-
			-----------------------------
			Value:
			critical
			major
			minor
			deferred
			---------------------------"
	::= { ommp021ConfigurationEntry 45 }

	ommp021Cfp2PresenceAbsenceNotificationSeverity OBJECT-TYPE
		SYNTAX  DisplayString
		MAX-ACCESS  read-write
		STATUS  current
		DESCRIPTION
			"Set or Get the alarm severity level of the
			OMMP021 CFP2 Presence Absence Notification   
			for requested port
			-----------------------------
			ommp021InterfaceNumber:
			3 - LINE-
			-----------------------------
			Value:
			critical
			major
			minor
			deferred
			---------------------------"
	::= { ommp021ConfigurationEntry 46 }

	ommp021Qsfp28InputPowerFailureAlarmSeverity OBJECT-TYPE
		SYNTAX  DisplayString
		MAX-ACCESS  read-write
		STATUS  current
		DESCRIPTION
			"Set or Get the alarm severity level of the
			OMMP021 QSFP28 Input Power Failure Alarm   
			for requested port
			-----------------------------
			ommp021InterfaceNumber:
			CLIENT-1
			CLIENT-2
			-----------------------------
			Value:
			critical
			major
			minor
			deferred
			---------------------------"
	::= { ommp021ConfigurationEntry 47 }

	ommp021Qsfp28OutputPowerFailureAlarmSeverity OBJECT-TYPE
		SYNTAX  DisplayString
		MAX-ACCESS  read-write
		STATUS  current
		DESCRIPTION
			"Set or Get the alarm severity level of the
			OMMP021 QSFP28 Output Power Failure Alarm   
			for requested port
			-----------------------------
			ommp021InterfaceNumber:
			CLIENT-1
			CLIENT-2
			-----------------------------
			Value:
			critical
			major
			minor
			deferred
			---------------------------"
	::= { ommp021ConfigurationEntry 48 }

	ommp021Qsfp28HighTemperatureAlarmSeverity OBJECT-TYPE
		SYNTAX  DisplayString
		MAX-ACCESS  read-write
		STATUS  current
		DESCRIPTION
			"Set or Get the alarm severity level of the
			OMMP021 QSFP28 High Temperature Alarm   
			for requested port
			-----------------------------
			ommp021InterfaceNumber:
			CLIENT-1
			CLIENT-2
			-----------------------------
			Value:
			critical
			major
			minor
			deferred
			---------------------------"
	::= { ommp021ConfigurationEntry 49 }

	ommp021Qsfp28LowTemperatureAlarmSeverity OBJECT-TYPE
		SYNTAX  DisplayString
		MAX-ACCESS  read-write
		STATUS  current
		DESCRIPTION
			"Set or Get the alarm severity level of the
			OMMP021 QSFP28 Low Temperature Alarm   
			for requested port
			-----------------------------
			ommp021InterfaceNumber:
			CLIENT-1
			CLIENT-2
			-----------------------------
			Value:
			critical
			major
			minor
			deferred
			---------------------------"
	::= { ommp021ConfigurationEntry 50 }

	ommp021Qsfp28HighBiasCurrentAlarmSeverity OBJECT-TYPE
		SYNTAX  DisplayString
		MAX-ACCESS  read-write
		STATUS  current
		DESCRIPTION
			"Set or Get the alarm severity level of the
			OMMP021 QSFP28 High Bias Current Alarm   
			for requested port
			-----------------------------
			ommp021InterfaceNumber:
			CLIENT-1
			CLIENT-2
			-----------------------------
			Value:
			critical
			major
			minor
			deferred
			---------------------------"
	::= { ommp021ConfigurationEntry 51 }

	ommp021Qsfp28LowBiasCurrentAlarmSeverity OBJECT-TYPE
		SYNTAX  DisplayString
		MAX-ACCESS  read-write
		STATUS  current
		DESCRIPTION
			"Set or Get the alarm severity level of the
			OMMP021 QSFP28 Low Bias Current Alarm   
			for requested port
			-----------------------------
			ommp021InterfaceNumber:
			CLIENT-1
			CLIENT-2
			-----------------------------
			Value:
			critical
			major
			minor
			deferred
			---------------------------"
	::= { ommp021ConfigurationEntry 52 }

	ommp021Qsfp28InputHighPowerAlarmSeverity OBJECT-TYPE
		SYNTAX  DisplayString
		MAX-ACCESS  read-write
		STATUS  current
		DESCRIPTION
			"Set or Get the alarm severity level of the
			OMMP021 QSFP28 Input High Power Alarm   
			for requested port
			-----------------------------
			ommp021InterfaceNumber:
			CLIENT-1
			CLIENT-2
			-----------------------------
			Value:
			critical
			major
			minor
			deferred
			---------------------------"
	::= { ommp021ConfigurationEntry 53 }

	ommp021Qsfp28InputLowPowerAlarmSeverity OBJECT-TYPE
		SYNTAX  DisplayString
		MAX-ACCESS  read-write
		STATUS  current
		DESCRIPTION
			"Set or Get the alarm severity level of the
			OMMP021 QSFP28 Input Low Power Alarm   
			for requested port
			-----------------------------
			ommp021InterfaceNumber:
			CLIENT-1
			CLIENT-2
			-----------------------------
			Value:
			critical
			major
			minor
			deferred
			---------------------------"
	::= { ommp021ConfigurationEntry 54 }

	ommp021Qsfp28OutputHighPowerAlarmSeverity OBJECT-TYPE
		SYNTAX  DisplayString
		MAX-ACCESS  read-write
		STATUS  current
		DESCRIPTION
			"Set or Get the alarm severity level of the
			OMMP021 QSFP28 Output High Power Alarm   
			for requested port
			-----------------------------
			ommp021InterfaceNumber:
			CLIENT-1
			CLIENT-2
			-----------------------------
			Value:
			critical
			major
			minor
			deferred
			---------------------------"
	::= { ommp021ConfigurationEntry 55 }

	ommp021Qsfp28OutputLowPowerAlarmSeverity OBJECT-TYPE
		SYNTAX  DisplayString
		MAX-ACCESS  read-write
		STATUS  current
		DESCRIPTION
			"Set or Get the alarm severity level of the
			OMMP021 QSFP28 Output Low Power Alarm   
			for requested port
			-----------------------------
			ommp021InterfaceNumber:
			CLIENT-1
			CLIENT-2
			-----------------------------
			Value:
			critical
			major
			minor
			deferred
			---------------------------"
	::= { ommp021ConfigurationEntry 56 }

	ommp021Qsfp28HighSupplyVoltageAlarmSeverity OBJECT-TYPE
		SYNTAX  DisplayString
		MAX-ACCESS  read-write
		STATUS  current
		DESCRIPTION
			"Set or Get the alarm severity level of the
			OMMP021 QSFP28 High Supply Voltage Alarm   
			for requested port
			-----------------------------
			ommp021InterfaceNumber:
			CLIENT-1
			CLIENT-2
			-----------------------------
			Value:
			critical
			major
			minor
			deferred
			---------------------------"
	::= { ommp021ConfigurationEntry 57 }

	ommp021Qsfp28LowSupplyVoltageAlarmSeverity OBJECT-TYPE
		SYNTAX  DisplayString
		MAX-ACCESS  read-write
		STATUS  current
		DESCRIPTION
			"Set or Get the alarm severity level of the
			OMMP021 QSFP28 Low Supply Voltage Alarm   
			for requested port
			-----------------------------
			ommp021InterfaceNumber:
			CLIENT-1
			CLIENT-2
			-----------------------------
			Value:
			critical
			major
			minor
			deferred
			---------------------------"
	::= { ommp021ConfigurationEntry 58 }

	ommp021Qsfp28PresenceAbsenceNotificationSeverity OBJECT-TYPE
		SYNTAX  DisplayString
		MAX-ACCESS  read-write
		STATUS  current
		DESCRIPTION
			"Set or Get the alarm severity level of the
			OMMP021 QSFP28 Presence Absence Notification   
			for requested port
			-----------------------------
			ommp021InterfaceNumber:
			CLIENT-1
			CLIENT-2
			-----------------------------
			Value:
			critical
			major
			minor
			deferred
			---------------------------"
	::= { ommp021ConfigurationEntry 59 }

	ommp021OtuLossOfSignalAlarmSeverity  OBJECT-TYPE
		SYNTAX  DisplayString
		MAX-ACCESS  read-write
		STATUS  current
		DESCRIPTION
			"Set or Get the alarm severity level of the OMMP021 OTU Loss Of Signal Alarm
			for the requested port
			-----------------------------
			ommp021InterfaceNumber:
			CLIENT-1
			CLIENT-2
			LINE-3
			-----------------------------
			Value:
			critical
			major
			minor
			deferred
			-----------------------------"
	::= { ommp021ConfigurationEntry 60 }

	ommp021OtuLossOfFrameAlarmSeverity  OBJECT-TYPE
		SYNTAX  DisplayString
		MAX-ACCESS  read-write
		STATUS  current
		DESCRIPTION
			"Set or Get the alarm severity level of the OMMP021 OTU Loss Of Frame Alarm
			for the requested port
			-----------------------------
			ommp021InterfaceNumber:
			CLIENT-1
			CLIENT-2
			LINE-3
			-----------------------------
			Value:
			critical
			major
			minor
			deferred
			-----------------------------"
	::= { ommp021ConfigurationEntry 61 }

	ommp021OtuOutOfFrameAlarmSeverity  OBJECT-TYPE
		SYNTAX  DisplayString
		MAX-ACCESS  read-write
		STATUS  current
		DESCRIPTION
			"Set or Get the alarm severity level of the OMMP021 OTU Out Of Frame Alarm
			for the requested port
			-----------------------------
			ommp021InterfaceNumber:
			CLIENT-1
			CLIENT-2
			LINE-3
			-----------------------------
			Value:
			critical
			major
			minor
			deferred
			-----------------------------"
	::= { ommp021ConfigurationEntry 62 }

	ommp021OtuOutOfMultiFrameAlarmSeverity  OBJECT-TYPE
		SYNTAX  DisplayString
		MAX-ACCESS  read-write
		STATUS  current
		DESCRIPTION
			"Set or Get the alarm severity level of the OMMP021 OTU Out Of Multi Frame Alarm
			for the requested port
			-----------------------------
			ommp021InterfaceNumber:
			CLIENT-1
			CLIENT-2
			LINE-3
			-----------------------------
			Value:
			critical
			major
			minor
			deferred
			-----------------------------"
	::= { ommp021ConfigurationEntry 63 }

	ommp021OtuSignalDegradeAlarmSeverity  OBJECT-TYPE
		SYNTAX  DisplayString
		MAX-ACCESS  read-write
		STATUS  current
		DESCRIPTION
			"Set or Get the alarm severity level of the OMMP021 OTU Signal Degrade Alarm
			for the requested port
			-----------------------------
			ommp021InterfaceNumber:
			CLIENT-1
			CLIENT-2
			LINE-3
			-----------------------------
			Value:
			critical
			major
			minor
			deferred
			-----------------------------"
	::= { ommp021ConfigurationEntry 64 }

	ommp021OtuAlarmIndicationSignalAlarmSeverity  OBJECT-TYPE
		SYNTAX  DisplayString
		MAX-ACCESS  read-write
		STATUS  current
		DESCRIPTION
			"Set or Get the alarm severity level of the OMMP021 OTU Alarm Indication Signal Alarm
			for the requested port
			-----------------------------
			ommp021InterfaceNumber:
			CLIENT-1
			CLIENT-2
			LINE-3
			-----------------------------
			Value:
			critical
			major
			minor
			deferred
			-----------------------------"
	::= { ommp021ConfigurationEntry 65 }

	ommp021OtuIncomingAlignmentErrorAlarmSeverity  OBJECT-TYPE
		SYNTAX  DisplayString
		MAX-ACCESS  read-write
		STATUS  current
		DESCRIPTION
			"Set or Get the alarm severity level of the OMMP021 OTU Incoming Alignment Error Alarm
			for the requested port
			-----------------------------
			ommp021InterfaceNumber:
			CLIENT-1
			CLIENT-2
			LINE-3
			-----------------------------
			Value:
			critical
			major
			minor
			deferred
			-----------------------------"
	::= { ommp021ConfigurationEntry 66 }

	ommp021OtuTrailTraceIdentifierMismatchAlarmSeverity  OBJECT-TYPE
		SYNTAX  DisplayString
		MAX-ACCESS  read-write
		STATUS  current
		DESCRIPTION
			"Set or Get the alarm severity level of the OMMP021 OTU Sapi Trace Identifier Mismatch Alarm
			for the requested port
			-----------------------------
			ommp021InterfaceNumber:
			CLIENT-1
			CLIENT-2
			LINE-3
			-----------------------------
			Value:
			critical
			major
			minor
			deferred
			-----------------------------"
	::= { ommp021ConfigurationEntry 67 }
	
	ommp021OtuBackwardIncomingAlignmentErrorAlarmSeverity  OBJECT-TYPE
		SYNTAX  DisplayString
		MAX-ACCESS  read-write
		STATUS  current
		DESCRIPTION
			"Set or Get the alarm severity level of the OMMP021 OTU Backward Incoming Alignment Error Alarm
			for the requested port
			-----------------------------
			ommp021InterfaceNumber:
			CLIENT-1
			CLIENT-2
			LINE-3
			-----------------------------
			Value:
			critical
			major
			minor
			deferred
			-----------------------------"
	::= { ommp021ConfigurationEntry 68 }

	ommp021OtuBackwardDefectIndicationAlarmSeverity  OBJECT-TYPE
		SYNTAX  DisplayString
		MAX-ACCESS  read-write
		STATUS  current
		DESCRIPTION
			"Set or Get the alarm severity level of the OMMP021 OTU Backward Defect Indication Alarm
			for the requested port
			-----------------------------
			ommp021InterfaceNumber:
			CLIENT-1
			CLIENT-2
			LINE-3
			-----------------------------
			Value:
			critical
			major
			minor
			deferred
			-----------------------------"
	::= { ommp021ConfigurationEntry 69 }

	ommp021OduSignalDegradeAlarmSeverity  OBJECT-TYPE
		SYNTAX  DisplayString
		MAX-ACCESS  read-write
		STATUS  current
		DESCRIPTION
			"Set or Get the alarm severity level of the OMMP021 ODU Signal Degrade Alarm
			for the requested port
			-----------------------------
			ommp021InterfaceNumber:
			CLIENT-1
			CLIENT-2
			LINE-3
			-----------------------------
			Value:
			critical
			major
			minor
			deferred
			-----------------------------"
	::= { ommp021ConfigurationEntry 70 }

	ommp021OduAlarmIndicationSignalAlarmSeverity  OBJECT-TYPE
		SYNTAX  DisplayString
		MAX-ACCESS  read-write
		STATUS  current
		DESCRIPTION
			"Set or Get the alarm severity level of the OMMP021 ODU Alarm Indication Signal Alarm
			for the requested port
			-----------------------------
			ommp021InterfaceNumber:
			CLIENT-1
			CLIENT-2
			LINE-3
			-----------------------------
			Value:
			critical
			major
			minor
			deferred
			-----------------------------"
	::= { ommp021ConfigurationEntry 71 }

	ommp021OduTrailTraceIdentifierMismatchAlarmSeverity  OBJECT-TYPE
		SYNTAX  DisplayString
		MAX-ACCESS  read-write
		STATUS  current
		DESCRIPTION
			"Set or Get the alarm severity level of the OMMP021 OTU Sapi Trace Identifier Mismatch Alarm
			for the requested port
			-----------------------------
			ommp021InterfaceNumber:
			CLIENT-1
			CLIENT-2
			LINE-3
			-----------------------------
			Value:
			critical
			major
			minor
			deferred
			-----------------------------"
	::= { ommp021ConfigurationEntry 72 }

	ommp021OduLockedDefectAlarmSeverity  OBJECT-TYPE
		SYNTAX  DisplayString
		MAX-ACCESS  read-write
		STATUS  current
		DESCRIPTION
			"Set or Get the alarm severity level of the OMMP021 ODU Locked Defect Alarm
			for the requested port
			-----------------------------
			ommp021InterfaceNumber:
			CLIENT-1
			CLIENT-2
			LINE-3
			-----------------------------
			Value:
			critical
			major
			minor
			deferred
			-----------------------------"
	::= { ommp021ConfigurationEntry 73 }

	ommp021OduOpenConnectionIndicationAlarmSeverity  OBJECT-TYPE
		SYNTAX  DisplayString
		MAX-ACCESS  read-write
		STATUS  current
		DESCRIPTION
			"Set or Get the alarm severity level of the OMMP021 ODU Open Connection Indication
			Alarm for the requested port
			-----------------------------
			ommp021InterfaceNumber:
			CLIENT-1
			CLIENT-2
			LINE-3
			-----------------------------
			Value:
			critical
			major
			minor
			deferred
			-----------------------------"
	::= { ommp021ConfigurationEntry 74 }

	ommp021OduBackwardDefectIndicationAlarmSeverity  OBJECT-TYPE
		SYNTAX  DisplayString
		MAX-ACCESS  read-write
		STATUS  current
		DESCRIPTION
			"Set or Get the alarm severity level of the OMMP021 ODU Backward Defect Indication
			Alarm for the requested port
			-----------------------------
			ommp021InterfaceNumber:
			CLIENT-1
			CLIENT-2
			LINE-3
			-----------------------------
			Value:
			critical
			major
			minor
			deferred
			-----------------------------"
	::= { ommp021ConfigurationEntry 75 }

	ommp021OpuPayloadMismatchAlarmSeverity  OBJECT-TYPE
		SYNTAX  DisplayString
		MAX-ACCESS  read-write
		STATUS  current
		DESCRIPTION
			"Set or Get the alarm severity level of the OMMP021 OPU Payload Mismatch Alarm
			for the requested port
			-----------------------------
			ommp021InterfaceNumber:
			CLIENT-1
			CLIENT-2
			LINE-3
			-----------------------------
			Value:
			critical
			major
			minor
			deferred
			-----------------------------"
	::= { ommp021ConfigurationEntry 76 }

	ommp021EthernetLossOfSignalAlarmSeverity  OBJECT-TYPE
		SYNTAX  DisplayString
		MAX-ACCESS  read-write
		STATUS  current
		DESCRIPTION
			"Set or Get the alarm severity level of the OMMP021 Ethernet Loss Of Signal Alarm
			for the requested port
			-----------------------------
			ommp021InterfaceNumber:
			CLIENT-1
			CLIENT-2
			LINE-3
			-----------------------------
			Value:
			Critical
			major
			minor
			deferred
			-----------------------------"
	::= { ommp021ConfigurationEntry 77 }

	ommp021EthernetIngressRemoteFaultAlarmSeverity  OBJECT-TYPE
		SYNTAX  DisplayString
		MAX-ACCESS  read-write
		STATUS  current
		DESCRIPTION
			"Set or Get the alarm severity level of the OMMP021 Ethernet Ingress Remote Fault 
			Alarm for the requested port
			-----------------------------
			ommp021InterfaceNumber:
			CLIENT-1
			CLIENT-2
			LINE-3
			-----------------------------
			Value:
			critical
			major
			minor
			deferred
			-----------------------------"
	::= { ommp021ConfigurationEntry 78 }

	ommp021EthernetEgressRemoteFaultAlarmSeverity  OBJECT-TYPE
		SYNTAX  DisplayString
		MAX-ACCESS  read-write
		STATUS  current
		DESCRIPTION
			"Set or Get the alarm severity level of the OMMP021 Ethernet Egress Remote Fault Alarm
			for the requested port
			-----------------------------
			ommp021InterfaceNumber:
			CLIENT-1
			CLIENT-2
			LINE-3
			-----------------------------
			Value:
			critical
			major
			minor
			deferred
			-----------------------------"
	::= { ommp021ConfigurationEntry 79 }

	ommp021EthernetEgressHighBerAlarmSeverity  OBJECT-TYPE
		SYNTAX  DisplayString
		MAX-ACCESS  read-write
		STATUS  current
		DESCRIPTION
			"Set or Get the alarm severity level of the OMMP021 Ethernet Egress High BER Alarm
			for the requested port
			-----------------------------
			ommp021InterfaceNumber:
			CLIENT-1
			CLIENT-2
			LINE-3
			-----------------------------
			Value:
			critical
			major
			minor
			deferred
			-----------------------------"
	::= { ommp021ConfigurationEntry 80 }

	ommp021EthernetEgressLocalFaultAlarmSeverity  OBJECT-TYPE
		SYNTAX  DisplayString
		MAX-ACCESS  read-write
		STATUS  current
		DESCRIPTION
			"Set or Get the alarm severity level of the OMMP021 Ethernet Egress Local Fault Alarm
			for the requested port
			-----------------------------
			ommp021InterfaceNumber:
			CLIENT-1
			CLIENT-2
			LINE-3
			-----------------------------
			Value:
			critical
			major
			minor
			deferred
			-----------------------------"
	::= { ommp021ConfigurationEntry 81 }
	
	ommp021LineOtuSignalFailThreshold OBJECT-TYPE		 
		SYNTAX  INTEGER
		MAX-ACCESS read-write
		STATUS current
		DESCRIPTION
			"Set or Get SM Signal Failure 
			Threshold value for the requested port configured with 
			OTU4/OTUC2 traffic.
			-----------------------------
			ommp021InterfaceNumber:
			CLIENT-1
			CLIENT-2
			LINE-3
			-----------------------------
			Values: 
			03 - 1.E -03
			04 - 1.E -04
			05 - 1.E -05
			-----------------------------" 
		::= { ommp021ConfigurationEntry 82 }

	ommp021LineOtuSignalDegradeThreshold OBJECT-TYPE		 
		SYNTAX  INTEGER
		MAX-ACCESS read-write
		STATUS current
		DESCRIPTION
			"Set or Get SM Signal Degrade 
			Threshold value for the requested port configured with 
			OTU4/OTUC2 traffic.
			-----------------------------
			ommp021InterfaceNumber:
			CLIENT-1
			CLIENT-2
			LINE-3
			-----------------------------
			Values:
			06 - 1.E -06
			07 - 1.E -07
			08 - 1.E -08
			09 - 1.E -09
			10 - 1.E -10(for line only)
			-----------------------------"
		::= { ommp021ConfigurationEntry 83 }

	ommp021LineOtuSapiTransmitTraceMessage OBJECT-TYPE
		SYNTAX DisplayString
		MAX-ACCESS read-write
		STATUS current
		DESCRIPTION
			"Set or get the 15 characters SAPI Transmit TTI message
			which is put into the outgoing OTU4/OTUC2 frame. 
			-----------------------------
			ommp021InterfaceNumber:
			CLIENT-1
			CLIENT-2
			LINE-3
			-----------------------------
			Values:
			eg: 123451234512345
			-----------------------------" 
		::= { ommp021ConfigurationEntry 84 }

	ommp021LineOtuDapiTransmitTraceMessage OBJECT-TYPE
		SYNTAX DisplayString
		MAX-ACCESS read-write
		STATUS current
		DESCRIPTION
			"Set or get the 15 characters DAPI Transmit TTI message
			which is put into the outgoing OTU4/OTUC2 frame. 
			-----------------------------
			ommp021InterfaceNumber:
			CLIENT-1
			CLIENT-2
			LINE-3
			-----------------------------
			Values:
			eg: 123451234512345
			-----------------------------" 
		::= { ommp021ConfigurationEntry 85 }
		
	ommp021LineOtuOperatorSpecificTransmitTraceMessage OBJECT-TYPE
		SYNTAX DisplayString
		MAX-ACCESS read-write
		STATUS current
		DESCRIPTION
			"Set or get the 32 characters Operator Specific Transmit
			TTI message which is put into the outgoing OTU4/OTUC2
			frame. 
			-----------------------------
			ommp021InterfaceNumber:
			CLIENT-1
			CLIENT-2
			LINE-3
			-----------------------------
			Values:
			eg: 12345123451234512345123451234500
			-----------------------------" 
		::= { ommp021ConfigurationEntry 86 }
		
	ommp021LineOtuSapiExpectedTraceMessage OBJECT-TYPE
		SYNTAX DisplayString
		MAX-ACCESS read-write
		STATUS current
		DESCRIPTION
			"15 characters SM SAPI Expected TTI message - Message
			set here is used for comparison with the message present
			in SM SAPI field of the incoming OTU4/OTUC2 frames.
			-----------------------------
			ommp021InterfaceNumber:
			CLIENT-1
			CLIENT-2
			LINE-3
			-----------------------------
			Values:
			eg: 123451234512345
			-----------------------------" 
		::= { ommp021ConfigurationEntry 87 }
		
	ommp021LineOtuDapiExpectedTraceMessage OBJECT-TYPE
		SYNTAX DisplayString
		MAX-ACCESS read-write
		STATUS current
		DESCRIPTION
			"15 characters SM DAPI Expected TTI message - Message
			set here is used for comparison with the message present
			in SM DAPI field of the incoming OTU4/OTUC2 frames.
			-----------------------------
			ommp021InterfaceNumber:
			CLIENT-1
			CLIENT-2
			LINE-3
			-----------------------------
			Values:
			eg: 123451234512345
			-----------------------------" 
		::= { ommp021ConfigurationEntry 88 }

	ommp021LineOtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU4/OTUC2 frames.
			-----------------------------
			ommp021InterfaceNumber:
			CLIENT-1
			CLIENT-2
			LINE-3
			-----------------------------
			Values:
			eg: 12345123451234512345123451234500
			-----------------------------" 
		::= { ommp021ConfigurationEntry 89 }

	ommp021LineOduSignalFailThreshold OBJECT-TYPE		 
		SYNTAX  INTEGER
		MAX-ACCESS read-write
		STATUS current
		DESCRIPTION
			"Set or Get PM Signal Failure 
			Threshold value for the requested port configured with 
			OTU4/OTUC2 traffic.
			-----------------------------
			ommp021InterfaceNumber:
			CLIENT-1
			CLIENT-2
			LINE-3
			-----------------------------
			Values: 
			03 - 1.E -03
			04 - 1.E -04
			05 - 1.E -05
			-----------------------------" 
		::= { ommp021ConfigurationEntry 90 }

	ommp021LineOduSignalDegradeThreshold OBJECT-TYPE		 
		SYNTAX  INTEGER
		MAX-ACCESS read-write
		STATUS current
		DESCRIPTION
			"Set or Get PM Signal Degrade 
			Threshold value for the requested port configured with 
			OTU4/OTUC2 traffic.
			-----------------------------
			ommp021InterfaceNumber:
			CLIENT-1
			CLIENT-2
			LINE-3
			-----------------------------
			Values: 
			06 - 1.E -06
			07 - 1.E -07
			08 - 1.E -08
			09 - 1.E -09
			10 - 1.E -10(for line only)
			-----------------------------" 
		::= { ommp021ConfigurationEntry 91 }

	ommp021LineOduSapiTransmitTraceMessage OBJECT-TYPE
		SYNTAX DisplayString
		MAX-ACCESS read-write
		STATUS current
		DESCRIPTION
			"Set or get the 15 characters SAPI Transmit TTI message
			which is put into the outgoing OTU4/OTUC2
			frame at the PM level. 
			-----------------------------
			ommp021InterfaceNumber:
			CLIENT-1
			CLIENT-2
			LINE-3
			-----------------------------
			Values:
			eg: 123451234512345
			-----------------------------" 
		::= { ommp021ConfigurationEntry 92 }
		
	ommp021LineOduDapiTransmitTraceMessage OBJECT-TYPE
		SYNTAX DisplayString
		MAX-ACCESS read-write
		STATUS current
		DESCRIPTION
			"Set or get the 15 characters DAPI Transmit TTI message
			which is put into the outgoing OTU4/OTUC2
			frame at the PM level. 
			-----------------------------
			ommp021InterfaceNumber:
			CLIENT-1
			CLIENT-2
			LINE-3
			-----------------------------
			Values:
			eg: 123451234512345
			-----------------------------" 
		::= { ommp021ConfigurationEntry 93 }
		
	ommp021LineOduOperatorSpecificTransmitTraceMessage OBJECT-TYPE
		SYNTAX DisplayString
		MAX-ACCESS read-write
		STATUS current
		DESCRIPTION
			"Set or get the 32 characters Operator Specific Transmit
			TTI message which is put into the outgoing OTU4/OTUC2
			frame at the PM level. 
			-----------------------------
			ommp021InterfaceNumber:
			CLIENT-1
			CLIENT-2
			LINE-3
			-----------------------------
			Values:
			eg: 12345123451234512345123451234500
			-----------------------------" 
		::= { ommp021ConfigurationEntry 94 }
		
	ommp021LineOduSapiExpectedTraceMessage OBJECT-TYPE
		SYNTAX DisplayString
		MAX-ACCESS read-write
		STATUS current
		DESCRIPTION
			"15 characters PM SAPI Expected TTI message - Message
			set here is used for comparison with the message present
			in PM SAPI field of the incoming OTU4/OTUC2 frames.
			-----------------------------
			ommp021InterfaceNumber:
			CLIENT-1
			CLIENT-2
			LINE-3
			-----------------------------
			Values:
			eg: 123451234512345
			-----------------------------" 
		::= { ommp021ConfigurationEntry 95 }

	ommp021LineOduDapiExpectedTraceMessage OBJECT-TYPE
		SYNTAX DisplayString
		MAX-ACCESS read-write
		STATUS current
		DESCRIPTION
			"15 characters PM DAPI Expected TTI message - Message
			set here is used for comparison with the message present
			in PM DAPI field of the incoming OTU4/OTUC2 frames.
			-----------------------------
			ommp021InterfaceNumber:
			CLIENT-1
			CLIENT-2
			LINE-3
			-----------------------------
			Values:
			eg: 123451234512345
			-----------------------------" 
		::= { ommp021ConfigurationEntry 96 }
		
	ommp021LineOduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU4/OTUC2 frames.
			-----------------------------
			ommp021InterfaceNumber:
			CLIENT-1
			CLIENT-2
			LINE-3
			-----------------------------
			Values:
			eg: 12345123451234512345123451234500
			-----------------------------" 
		::= { ommp021ConfigurationEntry 97 }
	
	ommp021LineOtuLossOfSignalAlarmSeverity  OBJECT-TYPE
		SYNTAX  DisplayString
		MAX-ACCESS  read-write
		STATUS  current
		DESCRIPTION
			"Set or Get the alarm severity level of the OMMP021 OTU Loss Of Signal Alarm
			for the requested port
			-----------------------------
			ommp021InterfaceNumber:
			CLIENT-1
			CLIENT-2
			LINE-3
			-----------------------------
			Value:
			critical
			major
			minor
			deferred
			-----------------------------"
	::= { ommp021ConfigurationEntry 98 }

	ommp021LineOtuLossOfFrameAlarmSeverity  OBJECT-TYPE
		SYNTAX  DisplayString
		MAX-ACCESS  read-write
		STATUS  current
		DESCRIPTION
			"Set or Get the alarm severity level of the OMMP021 OTU Loss Of Frame Alarm
			for the requested port
			-----------------------------
			ommp021InterfaceNumber:
			CLIENT-1
			CLIENT-2
			LINE-3
			-----------------------------
			Value:
			critical
			major
			minor
			deferred
			-----------------------------"
	::= { ommp021ConfigurationEntry 99 }

	ommp021LineOtuOutOfFrameAlarmSeverity  OBJECT-TYPE
		SYNTAX  DisplayString
		MAX-ACCESS  read-write
		STATUS  current
		DESCRIPTION
			"Set or Get the alarm severity level of the OMMP021 OTU Out Of Frame Alarm
			for the requested port
			-----------------------------
			ommp021InterfaceNumber:
			CLIENT-1
			CLIENT-2
			LINE-3
			-----------------------------
			Value:
			critical
			major
			minor
			deferred
			-----------------------------"
	::= { ommp021ConfigurationEntry 100 }

	ommp021LineOtuOutOfMultiFrameAlarmSeverity  OBJECT-TYPE
		SYNTAX  DisplayString
		MAX-ACCESS  read-write
		STATUS  current
		DESCRIPTION
			"Set or Get the alarm severity level of the OMMP021 OTU Out Of Multi Frame Alarm
			for the requested port
			-----------------------------
			ommp021InterfaceNumber:
			CLIENT-1
			CLIENT-2
			LINE-3
			-----------------------------
			Value:
			critical
			major
			minor
			deferred
			-----------------------------"
	::= { ommp021ConfigurationEntry 101 }

	ommp021LineOtuSignalDegradeAlarmSeverity  OBJECT-TYPE
		SYNTAX  DisplayString
		MAX-ACCESS  read-write
		STATUS  current
		DESCRIPTION
			"Set or Get the alarm severity level of the OMMP021 OTU Signal Degrade Alarm
			for the requested port
			-----------------------------
			ommp021InterfaceNumber:
			CLIENT-1
			CLIENT-2
			LINE-3
			-----------------------------
			Value:
			critical
			major
			minor
			deferred
			-----------------------------"
	::= { ommp021ConfigurationEntry 102 }

	ommp021LineOtuAlarmIndicationSignalAlarmSeverity  OBJECT-TYPE
		SYNTAX  DisplayString
		MAX-ACCESS  read-write
		STATUS  current
		DESCRIPTION
			"Set or Get the alarm severity level of the OMMP021 OTU Alarm Indication Signal Alarm
			for the requested port
			-----------------------------
			ommp021InterfaceNumber:
			CLIENT-1
			CLIENT-2
			LINE-3
			-----------------------------
			Value:
			critical
			major
			minor
			deferred
			-----------------------------"
	::= { ommp021ConfigurationEntry 103 }

	ommp021LineOtuIncomingAlignmentErrorAlarmSeverity  OBJECT-TYPE
		SYNTAX  DisplayString
		MAX-ACCESS  read-write
		STATUS  current
		DESCRIPTION
			"Set or Get the alarm severity level of the OMMP021 OTU Incoming Alignment Error Alarm
			for the requested port
			-----------------------------
			ommp021InterfaceNumber:
			CLIENT-1
			CLIENT-2
			LINE-3
			-----------------------------
			Value:
			critical
			major
			minor
			deferred
			-----------------------------"
	::= { ommp021ConfigurationEntry 104 }

	ommp021LineOtuTrailTraceIdentifierMismatchAlarmSeverity  OBJECT-TYPE
		SYNTAX  DisplayString
		MAX-ACCESS  read-write
		STATUS  current
		DESCRIPTION
			"Set or Get the alarm severity level of the OMMP021 OTU Sapi Trace Identifier Mismatch Alarm
			for the requested port
			-----------------------------
			ommp021InterfaceNumber:
			CLIENT-1
			CLIENT-2
			LINE-3
			-----------------------------
			Value:
			critical
			major
			minor
			deferred
			-----------------------------"
	::= { ommp021ConfigurationEntry 105 }
	
	ommp021LineOtuBackwardIncomingAlignmentErrorAlarmSeverity  OBJECT-TYPE
		SYNTAX  DisplayString
		MAX-ACCESS  read-write
		STATUS  current
		DESCRIPTION
			"Set or Get the alarm severity level of the OMMP021 OTU Backward Incoming Alignment Error Alarm
			for the requested port
			-----------------------------
			ommp021InterfaceNumber:
			CLIENT-1
			CLIENT-2
			LINE-3
			-----------------------------
			Value:
			critical
			major
			minor
			deferred
			-----------------------------"
	::= { ommp021ConfigurationEntry 106 }

	ommp021LineOtuBackwardDefectIndicationAlarmSeverity  OBJECT-TYPE
		SYNTAX  DisplayString
		MAX-ACCESS  read-write
		STATUS  current
		DESCRIPTION
			"Set or Get the alarm severity level of the OMMP021 OTU Backward Defect Indication Alarm
			for the requested port
			-----------------------------
			ommp021InterfaceNumber:
			CLIENT-1
			CLIENT-2
			LINE-3
			-----------------------------
			Value:
			critical
			major
			minor
			deferred
			-----------------------------"
	::= { ommp021ConfigurationEntry 107 }

	ommp021LineOduSignalDegradeAlarmSeverity  OBJECT-TYPE
		SYNTAX  DisplayString
		MAX-ACCESS  read-write
		STATUS  current
		DESCRIPTION
			"Set or Get the alarm severity level of the OMMP021 ODU Signal Degrade Alarm
			for the requested port
			-----------------------------
			ommp021InterfaceNumber:
			CLIENT-1
			CLIENT-2
			LINE-3
			-----------------------------
			Value:
			critical
			major
			minor
			deferred
			-----------------------------"
	::= { ommp021ConfigurationEntry 108 }

	ommp021LineOduAlarmIndicationSignalAlarmSeverity  OBJECT-TYPE
		SYNTAX  DisplayString
		MAX-ACCESS  read-write
		STATUS  current
		DESCRIPTION
			"Set or Get the alarm severity level of the OMMP021 ODU Alarm Indication Signal Alarm
			for the requested port
			-----------------------------
			ommp021InterfaceNumber:
			CLIENT-1
			CLIENT-2
			LINE-3
			-----------------------------
			Value:
			critical
			major
			minor
			deferred
			-----------------------------"
	::= { ommp021ConfigurationEntry 109 }

	ommp021LineOduTrailTraceIdentifierMismatchAlarmSeverity  OBJECT-TYPE
		SYNTAX  DisplayString
		MAX-ACCESS  read-write
		STATUS  current
		DESCRIPTION
			"Set or Get the alarm severity level of the OMMP021 OTU Sapi Trace Identifier Mismatch Alarm
			for the requested port
			-----------------------------
			ommp021InterfaceNumber:
			CLIENT-1
			CLIENT-2
			LINE-3
			-----------------------------
			Value:
			critical
			major
			minor
			deferred
			-----------------------------"
	::= { ommp021ConfigurationEntry 110 }

	ommp021LineOduLockedDefectAlarmSeverity  OBJECT-TYPE
		SYNTAX  DisplayString
		MAX-ACCESS  read-write
		STATUS  current
		DESCRIPTION
			"Set or Get the alarm severity level of the OMMP021 ODU Locked Defect Alarm
			for the requested port
			-----------------------------
			ommp021InterfaceNumber:
			CLIENT-1
			CLIENT-2
			LINE-3
			-----------------------------
			Value:
			critical
			major
			minor
			deferred
			-----------------------------"
	::= { ommp021ConfigurationEntry 111 }

	ommp021LineOduOpenConnectionIndicationAlarmSeverity  OBJECT-TYPE
		SYNTAX  DisplayString
		MAX-ACCESS  read-write
		STATUS  current
		DESCRIPTION
			"Set or Get the alarm severity level of the OMMP021 ODU Open Connection Indication
			Alarm for the requested port
			-----------------------------
			ommp021InterfaceNumber:
			CLIENT-1
			CLIENT-2
			LINE-3
			-----------------------------
			Value:
			critical
			major
			minor
			deferred
			-----------------------------"
	::= { ommp021ConfigurationEntry 112 }

	ommp021LineOduBackwardDefectIndicationAlarmSeverity  OBJECT-TYPE
		SYNTAX  DisplayString
		MAX-ACCESS  read-write
		STATUS  current
		DESCRIPTION
			"Set or Get the alarm severity level of the OMMP021 ODU Backward Defect Indication
			Alarm for the requested port
			-----------------------------
			ommp021InterfaceNumber:
			CLIENT-1
			CLIENT-2
			LINE-3
			-----------------------------
			Value:
			critical
			major
			minor
			deferred
			-----------------------------"
	::= { ommp021ConfigurationEntry 113 }

	ommp021LineOpuPayloadMismatchAlarmSeverity  OBJECT-TYPE
		SYNTAX  DisplayString
		MAX-ACCESS  read-write
		STATUS  current
		DESCRIPTION
			"Set or Get the alarm severity level of the OMMP021 OPU Payload Mismatch Alarm
			for the requested port
			-----------------------------
			ommp021InterfaceNumber:
			CLIENT-1
			CLIENT-2
			LINE-3
			-----------------------------
			Value:
			critical
			major
			minor
			deferred
			-----------------------------"
	::= { ommp021ConfigurationEntry 114 }

	ommp021ConfigurationTableRowStatus OBJECT-TYPE
              SYNTAX      RowStatus
              MAX-ACCESS  read-write
              STATUS      current
              DESCRIPTION
			"*****************************
			This is MIB realted property,
			NOT to be considered as a card property
			*****************************"
              ::= { ommp021ConfigurationEntry 115 }	


--*****************************************************************************
--				    ALARMS
--*****************************************************************************
                 
	ommp021AlarmQueryTable OBJECT-TYPE
	      SYNTAX  SEQUENCE OF Ommp021AlarmQueryEntry 
              MAX-ACCESS  not-accessible
              STATUS  current
              DESCRIPTION
                      "Gives Optical and Signal Alarms status of the OMMP021 card"
		::= { ommp021AlarmQuery 1 }	

	ommp021AlarmQueryEntry   OBJECT-TYPE
              SYNTAX  Ommp021AlarmQueryEntry 
              MAX-ACCESS  not-accessible
              STATUS  current
              DESCRIPTION 
              	""
		INDEX   { node, rack , subRack , slot , ommp021InterfaceNumber }
		::= { ommp021AlarmQueryTable 1 }
	
	Ommp021AlarmQueryEntry ::= 
			SEQUENCE {					
					ommp021Cfp2InputPowerFailureAlarm					DisplayString,
					ommp021Cfp2OutputPowerFailureAlarm					DisplayString,
					ommp021Cfp2HighTemperatureAlarm					DisplayString,
					ommp021Cfp2LowTemperatureAlarm					DisplayString,
					ommp021Cfp2InputHighPowerAlarm					DisplayString,
					ommp021Cfp2InputLowPowerAlarm						DisplayString,
					ommp021Cfp2OutputHighPowerAlarm					DisplayString,
					ommp021Cfp2OutputLowPowerAlarm					DisplayString,
					ommp021Cfp2HighSupplyVoltageAlarm					DisplayString,
					ommp021Cfp2LowSupplyVoltageAlarm					DisplayString,
					ommp021Cfp2PresenceAbsenceNotification				DisplayString,
					ommp021Qsfp28InputPowerFailureAlarm					DisplayString,
					ommp021Qsfp28OutputPowerFailureAlarm					DisplayString,
					ommp021Qsfp28HighTemperatureAlarm					DisplayString,
					ommp021Qsfp28LowTemperatureAlarm					DisplayString,
					ommp021Qsfp28HighBiasCurrentAlarm					DisplayString,
					ommp021Qsfp28LowBiasCurrentAlarm					DisplayString,
					ommp021Qsfp28InputHighPowerAlarm					DisplayString,
					ommp021Qsfp28InputLowPowerAlarm						DisplayString,
					ommp021Qsfp28OutputHighPowerAlarm					DisplayString,
					ommp021Qsfp28OutputLowPowerAlarm					DisplayString,
					ommp021Qsfp28HighSupplyVoltageAlarm					DisplayString,
					ommp021Qsfp28LowSupplyVoltageAlarm					DisplayString,
					ommp021Qsfp28PresenceAbsenceNotification				DisplayString,
					ommp021OtuLossOfSignalAlarm				DisplayString,
					ommp021OtuLossOfFrameAlarm				DisplayString,
					ommp021OtuOutOfFrameAlarm				DisplayString,
					ommp021OtuLossOfMultiFrameAlarm			DisplayString,
					ommp021OtuOutOfMultiFrameAlarm			DisplayString,
					ommp021OtuSignalFailAlarm				DisplayString,
					ommp021OtuSignalDegradeAlarm				DisplayString,
					ommp021OtuAlarmIndicationSignalAlarm			DisplayString,
					ommp021OtuIncomingAlignmentErrorAlarm			DisplayString,
					ommp021OtuTrailTraceIdentifierMismatchAlarm		DisplayString,
					ommp021OtuBackwardIncomingAlignmentErrorAlarm		DisplayString,
					ommp021OtuBackwardDefectIndicationAlarm		DisplayString,
					ommp021OduSignalFailAlarm				DisplayString,
					ommp021OduSignalDegradeAlarm				DisplayString,
					ommp021OduAlarmIndicationSignalAlarm			DisplayString,
					ommp021OduTrailTraceIdentifierMismatchAlarm		DisplayString,
					ommp021OduLockedDefectAlarm				DisplayString,
					ommp021OduOpenConnectionIndicationAlarm		DisplayString,
					ommp021OduBackwardDefectIndicationAlarm		DisplayString,					
					ommp021OpuPayloadMismatchAlarm				DisplayString,
					ommp021EthernetLossOfSignalAlarm				DisplayString,
					ommp021EthernetIngressRemoteFaultAlarm			DisplayString,
					ommp021EthernetEgressRemoteFaultAlarm			DisplayString,
					ommp021EthernetEgressHighBerAlarm			DisplayString,
					ommp021EthernetEgressLocalFaultAlarm			DisplayString,
					ommp021LineOtuLossOfSignalAlarm		DisplayString,
					ommp021LineOtuLossOfFrameAlarm		DisplayString,
					ommp021LineOtuOutOfFrameAlarm		DisplayString,
					ommp021LineOtuLossOfMultiFrameAlarm		DisplayString,
					ommp021LineOtuOutOfMultiFrameAlarm		DisplayString,
					ommp021LineOtuSignalDegradeAlarm		DisplayString,
					ommp021LineOtuAlarmIndicationSignalAlarm		DisplayString,
					ommp021LineOtuIncomingAlignmentErrorAlarm		DisplayString,
					ommp021LineOtuTrailTraceIdentifierMismatchAlarm		DisplayString,
					ommp021LineOtuBackwardIncomingAlignmentErrorAlarm		DisplayString,
					ommp021LineOtuBackwardDefectIndicationAlarm		DisplayString,
					ommp021LineOduSignalDegradeAlarm		DisplayString,
					ommp021LineOduAlarmIndicationSignalAlarm		DisplayString,
					ommp021LineOduTrailTraceIdentifierMismatchAlarm		DisplayString,
					ommp021LineOduLockedDefectAlarm		DisplayString,
					ommp021LineOduOpenConnectionIndicationAlarm		DisplayString,
					ommp021LineOduBackwardDefectIndicationAlarm		DisplayString,
					ommp021LineOpuPayloadMismatchAlarm		DisplayString,
					ommp021AlarmQueryTableRowStatus					RowStatus
		}

--*****************************************************************************
--				OPTICAL	ALARMS
--***************************************************************************** 

	ommp021Cfp2InputPowerFailureAlarm OBJECT-TYPE
              SYNTAX  DisplayString
              MAX-ACCESS  read-only
              STATUS  current
              DESCRIPTION
			"If optical input power at requested interface is less than
			-20dbm, this alarm will be generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 1 }

	ommp021Cfp2OutputPowerFailureAlarm OBJECT-TYPE
              SYNTAX  DisplayString
              MAX-ACCESS  read-only
              STATUS  current
              DESCRIPTION
			"If optical output power at requested interface is less than
			-10dbm, this alarm will be generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 2 }

	ommp021Cfp2HighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 3 }

	ommp021Cfp2LowTemperatureAlarm OBJECT-TYPE
              SYNTAX  DisplayString
              MAX-ACCESS  read-only
              STATUS  current
              DESCRIPTION
			"If optical temperature at requested interface is lower 
			than the Low Temperature Alarm Threshold, alarm will be 
			generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 4 }

	ommp021Cfp2InputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 5 }

	ommp021Cfp2InputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 6 }

	ommp021Cfp2OutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 7 }

	ommp021Cfp2OutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 8 }

	ommp021Cfp2HighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 9 }

	ommp021Cfp2LowSupplyVoltageAlarm OBJECT-TYPE
              SYNTAX  DisplayString
              MAX-ACCESS  read-only
              STATUS  current
              DESCRIPTION
			"If optical Supply Voltage at requested interface is 
			lesser than the Low Supply Voltage Alarm Threshold, 
			this alarm will be generated
			-----------------------------
			ommp021InterfaceNumber:
			3 - LINE-
			-----------------------------
			Values :
			If Alarm is Present - Date and Time Stamp
				    eg:2017-5-18,9:47:20.0,+5:30
			If Alarm is Absent  - 0
			-----------------------------"
		::= { ommp021AlarmQueryEntry 10 }

	ommp021Cfp2PresenceAbsenceNotification OBJECT-TYPE
              SYNTAX  DisplayString
              MAX-ACCESS  read-only
              STATUS  current
              DESCRIPTION
			"Whenever the CFP2 is jacked in or jacked out, this 
			notification is generated.
			-----------------------------
			ommp021InterfaceNumber:
			3 - LINE-
			-----------------------------
			Values :
			If Alarm is Present(module absent) - Date and Time Stamp
				    eg:2017-5-18,9:47:20.0,+5:30
			If Alarm is Absent(module present) - 0
			-----------------------------"
		::= { ommp021AlarmQueryEntry 11 }

	ommp021Qsfp28InputPowerFailureAlarm OBJECT-TYPE
              SYNTAX  DisplayString
              MAX-ACCESS  read-only
              STATUS  current
              DESCRIPTION
			"If optical input power at requested interface is less than
			-20dbm, this alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 12 }

	ommp021Qsfp28OutputPowerFailureAlarm OBJECT-TYPE
              SYNTAX  DisplayString
              MAX-ACCESS  read-only
              STATUS  current
              DESCRIPTION
			"If optical output power at requested interface is less than
			-10dbm, this alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 13 }

	ommp021Qsfp28HighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 14 }

	ommp021Qsfp28LowTemperatureAlarm OBJECT-TYPE
              SYNTAX  DisplayString
              MAX-ACCESS  read-only
              STATUS  current
              DESCRIPTION
			"If optical temperature at requested interface is lesser 
			than the Low Temperature Alarm Threshold, alarm will be 
			generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 15 }

	ommp021Qsfp28HighBiasCurrentAlarm OBJECT-TYPE
              SYNTAX  DisplayString
              MAX-ACCESS  read-only
              STATUS  current
              DESCRIPTION
			"If optical transmit bias current at requested interface
			is greater than the High Bias Current Alarm Threshold, 
			this alarm will be generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 16 }

	ommp021Qsfp28LowBiasCurrentAlarm OBJECT-TYPE
              SYNTAX  DisplayString
              MAX-ACCESS  read-only
              STATUS  current
              DESCRIPTION
			"If optical transmit bias current at requested interface
			is lesser than the Low Bias Current Alarm Threshold, 
			this alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 17 }

	ommp021Qsfp28InputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 18 }

	ommp021Qsfp28InputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 19 }

	ommp021Qsfp28OutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 20 }

	ommp021Qsfp28OutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 21 }

	ommp021Qsfp28HighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 22 }

	ommp021Qsfp28LowSupplyVoltageAlarm OBJECT-TYPE
              SYNTAX  DisplayString
              MAX-ACCESS  read-only
              STATUS  current
              DESCRIPTION
			"If optical Supply Voltage at requested interface is 
			lesser than the Low Supply Voltage Alarm Threshold, this
			alarm will be generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 23 }

	ommp021Qsfp28PresenceAbsenceNotification OBJECT-TYPE
              SYNTAX  DisplayString
              MAX-ACCESS  read-only
              STATUS  current
              DESCRIPTION
			"Whenever the QSFP28 is jacked in or jacked out, this 
			notification is generated.
			-----------------------------
			ommp021InterfaceNumber:
			CLIENT-1
			CLIENT-2
			LINE-3
			-----------------------------
			Values :
			If Alarm is Present(module absent) - Date and Time Stamp
				    eg:2017-5-18,9:47:20.0,+5:30
			If Alarm is Absent(module present) - 0
			-----------------------------"
		::= { ommp021AlarmQueryEntry 24 }

	ommp021OtuLossOfSignalAlarm OBJECT-TYPE
              SYNTAX  DisplayString
              MAX-ACCESS  read-only
              STATUS  current
              DESCRIPTION
			"For port configured with OTU4/OTUC2 traffic,
			if there is no signal received then OTU-LOS Alarm
			is generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 25 }

	ommp021OtuLossOfFrameAlarm OBJECT-TYPE
              SYNTAX  DisplayString
              MAX-ACCESS  read-only
              STATUS  current
              DESCRIPTION
			"For port configured with OTU4/OTUC2 traffic, if
			OTU4/OTUC2 frame received are in out-of-frame (OOF)
			state for 3 ms, then OTU-LOF Alarm is generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 26 }

	ommp021OtuOutOfFrameAlarm OBJECT-TYPE
              SYNTAX  DisplayString
              MAX-ACCESS  read-only
              STATUS  current
              DESCRIPTION
			"For port configured with OTU4/OTUC2 traffic, if 5
			consecutive OTU4/OTUC2 frames are received with
			invalid framing patterns then OOF Alarm is
			generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 27 }

	ommp021OtuLossOfMultiFrameAlarm OBJECT-TYPE
              SYNTAX  DisplayString
              MAX-ACCESS  read-only
              STATUS  current
              DESCRIPTION
			"For port configured with OTU4/OTUC2 traffic, if 
			OTU4/OTUC2 frame received are in Out-of-multiframe
			(OOM) state for 3 ms then LOM Alarm is generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 28 }

	ommp021OtuOutOfMultiFrameAlarm OBJECT-TYPE
              SYNTAX  DisplayString
              MAX-ACCESS  read-only
              STATUS  current
              DESCRIPTION
			"For port configured with OTU4/OTUC2 traffic, if the
			received MFAS does not match with the expected multi
			frame number for five consecutive frames then
			OOM Alarm is generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 29 }

	ommp021OtuSignalFailAlarm OBJECT-TYPE
              SYNTAX  DisplayString
              MAX-ACCESS  read-only
              STATUS  current
              DESCRIPTION
			"For port configured with OTU4/OTUC2 traffic, 
			OTU SF alarm is generated when BIP errors evaluated by 
			SM field of OTU4/OTUC2 frame exceeds the 
			'ommp021OtuSignalFailThreshold' threshold
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 30 }

	ommp021OtuSignalDegradeAlarm OBJECT-TYPE
              SYNTAX  DisplayString
              MAX-ACCESS  read-only
              STATUS  current
              DESCRIPTION
			"For port configured with OTU4/OTUC2 traffic, 
			OTU SD alarm is generated when BIP errors evaluated by 
			SM field of OTU4/OTUC2 frame exceeds the 
			'ommp021OtuSignalDegradeThreshold' threshold.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 31 }

	ommp021OtuAlarmIndicationSignalAlarm OBJECT-TYPE
              SYNTAX  DisplayString
              MAX-ACCESS  read-only
              STATUS  current
              DESCRIPTION
			"For port configured with OTU4/OTUC2 traffic,
			OTU-AIS is generated and transmitted in forward 
			direction, when LOS has been detected at far-end port.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 32 }

	ommp021OtuIncomingAlignmentErrorAlarm OBJECT-TYPE
              SYNTAX  DisplayString
              MAX-ACCESS  read-only
              STATUS  current
              DESCRIPTION
			"For port configured with OTU4/OTUC2 traffic, IAE alarms
			shall be declared if the IAE bit in the SM overhead
			field (byte 3, bit 6) is 1 for 5 consecutive frames. 
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 33 }

	ommp021OtuTrailTraceIdentifierMismatchAlarm OBJECT-TYPE
              SYNTAX  DisplayString
              MAX-ACCESS  read-only
              STATUS  current
              DESCRIPTION
			"For port configured with OTU4/OTUC2 traffic, when there
			is a mismatch between the incoming and the expected
			Sapi(TTI) at the SM section,
			OTU-Sapi alarm is generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 34 }

	ommp021OtuBackwardIncomingAlignmentErrorAlarm OBJECT-TYPE
              SYNTAX  DisplayString
              MAX-ACCESS  read-only
              STATUS  current
              DESCRIPTION
			"For port configured with OTU4/OTUC2 traffic, 
			the presence of this alarm conveys that an incoming
			alignment error(IAE) condition is detected
			by the far-end card.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 35 }

	ommp021OtuBackwardDefectIndicationAlarm OBJECT-TYPE
              SYNTAX  DisplayString
              MAX-ACCESS  read-only
              STATUS  current
              DESCRIPTION
			"For port configured with OTU4/OTUC2 traffic,
			the presence of this alarm conveys that a
			a defect like LOS, LOF, LOM has been detected in the
			by the far-end card.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 36 }

	ommp021OduSignalFailAlarm OBJECT-TYPE
              SYNTAX  DisplayString
              MAX-ACCESS  read-only
              STATUS  current
              DESCRIPTION
			"For port configured with OTU4/OTUC2 traffic, ODU-SF
			alarm is generated when BIP errors evaluated by 
			PM field of OTU4 frame exceeds the 
			'ommp021OduSignalFailThreshold' threshold.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 37 }

	ommp021OduSignalDegradeAlarm OBJECT-TYPE
              SYNTAX  DisplayString
              MAX-ACCESS  read-only
              STATUS  current
              DESCRIPTION
			"For port configured with OTU4/OTUC2 traffic,ODU-SD
			alarm is generated when BIP errors evaluated by 
			PM field of OTU4 frame exceeds the 	
			'ommp021OduSignalDegradeThreshold' threshold.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 38 }

	ommp021OduAlarmIndicationSignalAlarm OBJECT-TYPE
              SYNTAX  DisplayString
              MAX-ACCESS  read-only
              STATUS  current
              DESCRIPTION
			"For port configured with OTU4/OTUC2 traffic, when the incoming
			OTU4 frame has all 1s in the entire ODUk signal,
			excluding the frame alignment overhead (FA OH),
			OTUk overhead (OTUk OH) and ODUk FTFL, this alarm is
			generated
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 39 }

	ommp021OduTrailTraceIdentifierMismatchAlarm OBJECT-TYPE
              SYNTAX  DisplayString
              MAX-ACCESS  read-only
              STATUS  current
              DESCRIPTION
			"For port configured with OTU4/OTUC2 traffic, when there
			is a mismatch between the incoming and the expected
			Sapi(TTI) at the PM section,
			ODU-Sapi alarm is generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 40 }

	ommp021OduLockedDefectAlarm OBJECT-TYPE
              SYNTAX  DisplayString
              MAX-ACCESS  read-only
              STATUS  current
              DESCRIPTION
			"For port configured with OTU4/OTUC2 traffic, 
			the locked maintenance signal is generated on operator
			request in order to lock the signal from user access. It
			consists of a repeating 0b0101 0101 pattern in the
			entire ODUk signal, which excludes the Frame Alignment
			overhead and the OTUk overhead.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 41 }

	ommp021OduOpenConnectionIndicationAlarm OBJECT-TYPE
              SYNTAX  DisplayString
              MAX-ACCESS  read-only
              STATUS  current
              DESCRIPTION
			"For port configured with OTU4/OTUC2 traffic, 
			an open connection indication is sent downstream when
			no signal is detected from upstream. It consists of a
			repeating 0b0110 0110 pattern in the entire ODUk signal,
			which excludes the Frame Alignment overhead and the
			OTUk overhead.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 42 }

	ommp021OduBackwardDefectIndicationAlarm OBJECT-TYPE
              SYNTAX  DisplayString
              MAX-ACCESS  read-only
              STATUS  current
              DESCRIPTION
			"For port configured with OTU4/OTUC2 traffic, 
			the presence of this alarm conveys that either of
			OTU-LOS or OTU-LOF or OTU-LOM or OTU-AIS or ODU-AIS
			or ODU-OCI or ODU-LCK condition is detected
			by the far-end card.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 43 }

	ommp021OpuPayloadMismatchAlarm OBJECT-TYPE
              SYNTAX  DisplayString
              MAX-ACCESS  read-only
              STATUS  current
              DESCRIPTION
			"For port configured with OTU4/OTUC2 traffic, 
			OPU-PLM Alarm is declared if the accepted payload type
			is not equal to the expected payload type.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 44 }

	ommp021EthernetLossOfSignalAlarm OBJECT-TYPE
              SYNTAX  DisplayString
              MAX-ACCESS  read-only
              STATUS  current
              DESCRIPTION
			"For port configured with 
			GE-GFP-F/FE-GFP-F/GE-GFP-T/FE-GFP-T traffic,
			if there is no signal received then LOS Alarm is 
			generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 45 }

	ommp021EthernetIngressRemoteFaultAlarm OBJECT-TYPE
              SYNTAX  DisplayString
              MAX-ACCESS  read-only
              STATUS  current
              DESCRIPTION
			"For port configured with Ethernet traffic,
			if fault is detected on the transmit data path then 
			Remote Fault Alarm is generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 46 }

	ommp021EthernetEgressRemoteFaultAlarm OBJECT-TYPE
              SYNTAX  DisplayString
              MAX-ACCESS  read-only
              STATUS  current
              DESCRIPTION
			"For port configured with Ethernet traffic,
			if fault is detected on the transmit data path then 
			Remote Fault Alarm is generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 47 }

	ommp021EthernetEgressHighBerAlarm OBJECT-TYPE
              SYNTAX  DisplayString
              MAX-ACCESS  read-only
              STATUS  current
              DESCRIPTION
			"For port configured with Ethernet traffic,
			this alarm is generated when signal BER is
			greater than 1e−4. 
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 48 }

	ommp021EthernetEgressLocalFaultAlarm OBJECT-TYPE
              SYNTAX  DisplayString
              MAX-ACCESS  read-only
              STATUS  current
              DESCRIPTION
			"For port configured with Ethernet traffic,
			if fault is detected on the receive data path then Local
			Fault Alarm is generated.
			-----------------------------
			ommp021InterfaceNumber:
			CLIENT-1
			CLIENT-2
			LINE-3
			-----------------------------
			Values :
			If Alarm is Present - Date and Time Stamp
				    eg:2017-5-18,9:47:20.0,+5:30
			If Alarm is Absent  - 0
			-----------------------------"
		::= { ommp021AlarmQueryEntry 49 }
		
	ommp021LineOtuLossOfSignalAlarm OBJECT-TYPE
              SYNTAX  DisplayString
              MAX-ACCESS  read-only
              STATUS  current
              DESCRIPTION
			"For port configured with OTU4/OTUC2 traffic,
			if there is no signal received then OTU-LOS Alarm
			is generated.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 50 }

	ommp021LineOtuLossOfFrameAlarm OBJECT-TYPE
              SYNTAX  DisplayString
              MAX-ACCESS  read-only
              STATUS  current
              DESCRIPTION
			"For port configured with OTU4/OTUC2 traffic, if
			OTU4/OTUC2 frame received are in out-of-frame (OOF)
			state for 3 ms, then OTU-LOF Alarm is generated
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 51 }

	ommp021LineOtuOutOfFrameAlarm OBJECT-TYPE
              SYNTAX  DisplayString
              MAX-ACCESS  read-only
              STATUS  current
              DESCRIPTION
			"For port configured with OTU4/OTUC2 traffic, if 5
			consecutive OTU4/OTUC2 frames are received with
			invalid framing patterns then OOF Alarm is
			generated
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 52 }

	ommp021LineOtuLossOfMultiFrameAlarm OBJECT-TYPE
              SYNTAX  DisplayString
              MAX-ACCESS  read-only
              STATUS  current
              DESCRIPTION
			"For port configured with OTU4/OTUC2 traffic, if 
			OTU4/OTUC2 frame received are in Out-of-multiframe
			(OOM) state for 3 ms then LOM Alarm is generated.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 53 }

	ommp021LineOtuOutOfMultiFrameAlarm OBJECT-TYPE
              SYNTAX  DisplayString
              MAX-ACCESS  read-only
              STATUS  current
              DESCRIPTION
			"For port configured with OTU4/OTUC2 traffic, if the
			received MFAS does not match with the expected multi
			frame number for five consecutive frames then
			OOM Alarm is generated.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 54 }

	ommp021LineOtuSignalDegradeAlarm OBJECT-TYPE
              SYNTAX  DisplayString
              MAX-ACCESS  read-only
              STATUS  current
              DESCRIPTION
			"For port configured with OTU4/OTUC2 traffic, 
			OTU SD alarm is generated when BIP errors evaluated by 
			SM field of OTU4/OTUC2 frame exceeds the 
			'ommp021LineOtuSignalDegradeThreshold' threshold.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 55 }

	ommp021LineOtuAlarmIndicationSignalAlarm OBJECT-TYPE
              SYNTAX  DisplayString
              MAX-ACCESS  read-only
              STATUS  current
              DESCRIPTION
			"For port configured with OTU4/OTUC2 traffic,
			OTU-AIS is generated and transmitted in forward 
			direction, when LOS has been detected at far-end port.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 56 }

	ommp021LineOtuIncomingAlignmentErrorAlarm OBJECT-TYPE
              SYNTAX  DisplayString
              MAX-ACCESS  read-only
              STATUS  current
              DESCRIPTION
			"For port configured with OTU4/OTUC2 traffic, IAE alarms
			shall be declared if the IAE bit in the SM overhead
			field (byte 3, bit 6) is 1 for 5 consecutive frames. 
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 57 }

	ommp021LineOtuTrailTraceIdentifierMismatchAlarm OBJECT-TYPE
              SYNTAX  DisplayString
              MAX-ACCESS  read-only
              STATUS  current
              DESCRIPTION
			"For port configured with OTU4/OTUC2 traffic, when there
			is a mismatch between the incoming and the expected
			Sapi(TTI) at the SM section,
			OTU-Sapi alarm is generated.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 58 }

	ommp021LineOtuBackwardIncomingAlignmentErrorAlarm OBJECT-TYPE
              SYNTAX  DisplayString
              MAX-ACCESS  read-only
              STATUS  current
              DESCRIPTION
			"For port configured with OTU4/OTUC2 traffic, 
			the presence of this alarm conveys that an incoming
			alignment error(IAE) condition is detected
			by the far-end card.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 59 }

	ommp021LineOtuBackwardDefectIndicationAlarm OBJECT-TYPE
              SYNTAX  DisplayString
              MAX-ACCESS  read-only
              STATUS  current
              DESCRIPTION
			"For port configured with OTU4/OTUC2 traffic,
			the presence of this alarm conveys that a
			a defect like LOS, LOF, LOM has been detected in the
			by the far-end card.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 60 }

	ommp021LineOduSignalDegradeAlarm OBJECT-TYPE
              SYNTAX  DisplayString
              MAX-ACCESS  read-only
              STATUS  current
              DESCRIPTION
			"For port configured with OTU4/OTUC2 traffic,ODU-SD
			alarm is generated when BIP errors evaluated by 
			PM field of OTU4 frame exceeds the 	
			'ommp021LineOduSignalDegradeThreshold' threshold.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 61 }

	ommp021LineOduAlarmIndicationSignalAlarm OBJECT-TYPE
              SYNTAX  DisplayString
              MAX-ACCESS  read-only
              STATUS  current
              DESCRIPTION
			"For port configured with OTU4/OTUC2 traffic, when the incoming
			OTU4 frame has all 1s in the entire ODUk signal,
			excluding the frame alignment overhead (FA OH),
			OTUk overhead (OTUk OH) and ODUk FTFL, this alarm is
			generated
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 62 }

	ommp021LineOduTrailTraceIdentifierMismatchAlarm OBJECT-TYPE
              SYNTAX  DisplayString
              MAX-ACCESS  read-only
              STATUS  current
              DESCRIPTION
			"For port configured with OTU4/OTUC2 traffic, when there
			is a mismatch between the incoming and the expected
			Sapi(TTI) at the PM section,
			ODU-Sapi alarm is generated.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 63 }

	ommp021LineOduLockedDefectAlarm OBJECT-TYPE
              SYNTAX  DisplayString
              MAX-ACCESS  read-only
              STATUS  current
              DESCRIPTION
			"For port configured with OTU4/OTUC2 traffic, 
			the locked maintenance signal is generated on operator
			request in order to lock the signal from user access. It
			consists of a repeating 0b0101 0101 pattern in the
			entire ODUk signal, which excludes the Frame Alignment
			overhead and the OTUk overhead.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 64 }

	ommp021LineOduOpenConnectionIndicationAlarm OBJECT-TYPE
              SYNTAX  DisplayString
              MAX-ACCESS  read-only
              STATUS  current
              DESCRIPTION
			"For port configured with OTU4/OTUC2 traffic, 
			an open connection indication is sent downstream when
			no signal is detected from upstream. It consists of a
			repeating 0b0110 0110 pattern in the entire ODUk signal,
			which excludes the Frame Alignment overhead and the
			OTUk overhead.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 65 }

	ommp021LineOduBackwardDefectIndicationAlarm OBJECT-TYPE
              SYNTAX  DisplayString
              MAX-ACCESS  read-only
              STATUS  current
              DESCRIPTION
			"For port configured with OTU4/OTUC2 traffic, 
			the presence of this alarm conveys that either of
			OTU-LOS or OTU-LOF or OTU-LOM or OTU-AIS or ODU-AIS
			or ODU-OCI or ODU-LCK condition is detected
			by the far-end card.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 66 }

	ommp021LineOpuPayloadMismatchAlarm OBJECT-TYPE
              SYNTAX  DisplayString
              MAX-ACCESS  read-only
              STATUS  current
              DESCRIPTION
			"For port configured with OTU4/OTUC2 traffic, 
			OPU-PLM Alarm is declared if the accepted payload type
			is not equal to the expected payload type.
			-----------------------------
			ommp021 InterfaceNumber:
			1 to 2 - CLIENT-1 and CLIENT-2
			-----------------------------
			Values :
			If Alarm is Present - Date and Time Stamp
				    eg:2017-5-18,9:47:20.0,+5:30
			If Alarm is Absent  - 0
			-----------------------------"
		::= { ommp021AlarmQueryEntry 67 }

	ommp021AlarmQueryTableRowStatus OBJECT-TYPE
              SYNTAX      RowStatus
              MAX-ACCESS  read-write
              STATUS      current
              DESCRIPTION
			"*****************************
			This is MIB realted property,
			NOT to be considered as a card property
			*****************************"
              ::= { ommp021AlarmQueryEntry 68 }	                                

--*****************************************************************************
--				    ALARM Notification Table
--*****************************************************************************
	ommp021Cfp2InputPowerFailureAlarmTrap NOTIFICATION-TYPE
		OBJECTS { ommp021Cfp2InputPowerFailureAlarm  }
		STATUS  current
		DESCRIPTION
                        "OMMP021 CFP2 Input Power Failure Alarm Trap"
        ::= { ommp021AlarmNotification 1 }

	ommp021Cfp2OutputPowerFailureAlarmTrap NOTIFICATION-TYPE
		OBJECTS { ommp021Cfp2OutputPowerFailureAlarm  }
		STATUS  current
		DESCRIPTION
                        "OMMP021 CFP2 Output Power Failure Alarm Trap" 
        ::= { ommp021AlarmNotification 2 }

	ommp021Cfp2HighTemperatureAlarmTrap NOTIFICATION-TYPE
		OBJECTS { ommp021Cfp2HighTemperatureAlarm  }
		STATUS  current
		DESCRIPTION
                        "OMMP021 CFP2 High Temperature Alarm Trap" 
        ::= { ommp021AlarmNotification 3 }

	ommp021Cfp2LowTemperatureAlarmTrap NOTIFICATION-TYPE
		OBJECTS { ommp021Cfp2LowTemperatureAlarm  }
		STATUS  current
		DESCRIPTION
                        "OMMP021 CFP2 Low Temperature Alarm Trap" 
        ::= { ommp021AlarmNotification 4 }

	ommp021Cfp2InputHighPowerAlarmTrap NOTIFICATION-TYPE
		OBJECTS { ommp021Cfp2InputHighPowerAlarm  }
		STATUS  current
		DESCRIPTION
                        "OMMP021 CFP2 Input High Power Alarm Trap" 
        ::= { ommp021AlarmNotification 5 }

	ommp021Cfp2InputLowPowerAlarmTrap NOTIFICATION-TYPE
		OBJECTS { ommp021Cfp2InputLowPowerAlarm  }
		STATUS  current
		DESCRIPTION
                        "OMMP021 CFP2 Input Low Power Alarm Trap" 
        ::= { ommp021AlarmNotification 6 }

	ommp021Cfp2OutputHighPowerAlarmTrap NOTIFICATION-TYPE
		OBJECTS { ommp021Cfp2OutputHighPowerAlarm  }
		STATUS  current
		DESCRIPTION
                        "OMMP021 CFP2 Output High Power Alarm Trap" 
        ::= { ommp021AlarmNotification 7 }

	ommp021Cfp2OutputLowPowerAlarmTrap NOTIFICATION-TYPE
		OBJECTS { ommp021Cfp2OutputLowPowerAlarm  }
		STATUS  current
		DESCRIPTION
                        "OMMP021 CFP2 Output Low Power Alarm Trap" 
        ::= { ommp021AlarmNotification 8 }

	ommp021Cfp2HighSupplyVoltageAlarmTrap NOTIFICATION-TYPE
		OBJECTS { ommp021Cfp2HighSupplyVoltageAlarm  }
		STATUS  current
		DESCRIPTION
                        "OMMP021 CFP2 High Supply Voltage Alarm Trap" 
        ::= { ommp021AlarmNotification 9 }

	ommp021Cfp2LowSupplyVoltageAlarmTrap NOTIFICATION-TYPE
		OBJECTS { ommp021Cfp2LowSupplyVoltageAlarm  }
		STATUS  current
		DESCRIPTION
                        "OMMP021 CFP2 Low Supply Voltage Alarm Trap" 
        ::= { ommp021AlarmNotification 10 }

	ommp021Cfp2PresenceAbsenceNotificationTrap NOTIFICATION-TYPE
		OBJECTS { ommp021Cfp2PresenceAbsenceNotification  }
		STATUS  current
		DESCRIPTION
                        "OMMP021 CFP2 Presence Absence Notification Trap" 
        ::= { ommp021AlarmNotification 11 }

	ommp021Qsfp28InputPowerFailureAlarmTrap NOTIFICATION-TYPE
		OBJECTS { ommp021Qsfp28InputPowerFailureAlarm  }
		STATUS  current
		DESCRIPTION
                        "OMMP021 QSFP28 Input Power Failure Alarm Trap" 
        ::= { ommp021AlarmNotification 12 }

	ommp021Qsfp28OutputPowerFailureAlarmTrap NOTIFICATION-TYPE
		OBJECTS { ommp021Qsfp28OutputPowerFailureAlarm  }
		STATUS  current
		DESCRIPTION
                        "OMMP021 QSFP28 Output Power Failure Alarm Trap" 
        ::= { ommp021AlarmNotification 13 }

	ommp021Qsfp28HighTemperatureAlarmTrap NOTIFICATION-TYPE
		OBJECTS { ommp021Qsfp28HighTemperatureAlarm  }
		STATUS  current
		DESCRIPTION
                        "OMMP021 QSFP28 High Temperature Alarm Trap" 
        ::= { ommp021AlarmNotification 14 }

	ommp021Qsfp28LowTemperatureAlarmTrap NOTIFICATION-TYPE
		OBJECTS { ommp021Qsfp28LowTemperatureAlarm  }
		STATUS  current
		DESCRIPTION
                        "OMMP021 QSFP28 Low Temperature Alarm Trap" 
        ::= { ommp021AlarmNotification 15 }

	ommp021Qsfp28HighBiasCurrentAlarmTrap NOTIFICATION-TYPE
		OBJECTS { ommp021Qsfp28HighBiasCurrentAlarm  }
		STATUS  current
		DESCRIPTION
                        "OMMP021 QSFP28 High Bias Current Alarm Trap" 
        ::= { ommp021AlarmNotification 16 }

	ommp021Qsfp28LowBiasCurrentAlarmTrap NOTIFICATION-TYPE
		OBJECTS { ommp021Qsfp28LowBiasCurrentAlarm  }
		STATUS  current
		DESCRIPTION
                        "OMMP021 QSFP28 Low Bias Current Alarm Trap" 
        ::= { ommp021AlarmNotification 17 }

	ommp021Qsfp28InputHighPowerAlarmTrap NOTIFICATION-TYPE
		OBJECTS { ommp021Qsfp28InputHighPowerAlarm  }
		STATUS  current
		DESCRIPTION
                        "OMMP021 QSFP28 Input High Power Alarm Trap" 
        ::= { ommp021AlarmNotification 18 }

	ommp021Qsfp28InputLowPowerAlarmTrap NOTIFICATION-TYPE
		OBJECTS { ommp021Qsfp28InputLowPowerAlarm  }
		STATUS  current
		DESCRIPTION
                        "OMMP021 QSFP28 Input Low Power Alarm Trap" 
        ::= { ommp021AlarmNotification 19 }

	ommp021Qsfp28OutputHighPowerAlarmTrap NOTIFICATION-TYPE
		OBJECTS { ommp021Qsfp28OutputHighPowerAlarm  }
		STATUS  current
		DESCRIPTION
                        "OMMP021 QSFP28 Output High Power Alarm Trap" 
        ::= { ommp021AlarmNotification 20 }

	ommp021Qsfp28OutputLowPowerAlarmTrap NOTIFICATION-TYPE
		OBJECTS { ommp021Qsfp28OutputLowPowerAlarm  }
		STATUS  current
		DESCRIPTION
                        "OMMP021 QSFP28 Output Low Power Alarm Trap" 
        ::= { ommp021AlarmNotification 21 }

	ommp021Qsfp28HighSupplyVoltageAlarmTrap NOTIFICATION-TYPE
		OBJECTS { ommp021Qsfp28HighSupplyVoltageAlarm  }
		STATUS  current
		DESCRIPTION
                        "OMMP021 QSFP28 High Supply Voltage Alarm Trap" 
        ::= { ommp021AlarmNotification 22 }

	ommp021Qsfp28LowSupplyVoltageAlarmTrap NOTIFICATION-TYPE
		OBJECTS { ommp021Qsfp28LowSupplyVoltageAlarm  }
		STATUS  current
		DESCRIPTION
                        "OMMP021 QSFP28 Low Supply Voltage Alarm Trap" 
        ::= { ommp021AlarmNotification 23 }

	ommp021Qsfp28PresenceAbsenceNotificationTrap NOTIFICATION-TYPE
		OBJECTS { ommp021Qsfp28PresenceAbsenceNotification  }
		STATUS  current
		DESCRIPTION
                        "OMMP021 QSFP28 Presence Absence Notification Trap" 
        ::= { ommp021AlarmNotification 24 }

	ommp021OtuLossOfSignalAlarmTrap NOTIFICATION-TYPE
		OBJECTS { ommp021OtuLossOfSignalAlarm  }
		STATUS  current
		DESCRIPTION
                        "OMMP021 OTU Loss Of Signal Alarm Trap" 
        ::= { ommp021AlarmNotification 25 }

	ommp021OtuLossOfFrameAlarmTrap NOTIFICATION-TYPE
		OBJECTS { ommp021OtuLossOfFrameAlarm  }
		STATUS  current
		DESCRIPTION
                        "OMMP021 OTU Loss Of Frame Alarm Trap" 
        ::= { ommp021AlarmNotification 26 }

	ommp021OtuOutOfFrameAlarmTrap NOTIFICATION-TYPE
		OBJECTS { ommp021OtuOutOfFrameAlarm  }
		STATUS  current
		DESCRIPTION
                        "OMMP021 OTU Out Of Frame Alarm Trap" 
        ::= { ommp021AlarmNotification 27 }

	ommp021OtuLossOfMultiFrameAlarmTrap NOTIFICATION-TYPE
		OBJECTS { ommp021OtuLossOfMultiFrameAlarm  }
		STATUS  current
		DESCRIPTION
                        "OMMP021 OTU Loss Of Multi Frame Alarm Trap" 
        ::= { ommp021AlarmNotification 28 }

	ommp021OtuOutOfMultiFrameAlarmTrap NOTIFICATION-TYPE
		OBJECTS { ommp021OtuOutOfMultiFrameAlarm  }
		STATUS  current
		DESCRIPTION
                        "OMMP021 OTU Out Of Multi Frame Alarm Trap" 
        ::= { ommp021AlarmNotification 29 }

	ommp021OtuSignalFailAlarmTrap NOTIFICATION-TYPE
		OBJECTS { ommp021OtuSignalFailAlarm  }
		STATUS  current
		DESCRIPTION
                        "OMMP021 OTU Signal Fail Alarm Trap" 
        ::= { ommp021AlarmNotification 30 }

	ommp021OtuSignalDegradeAlarmTrap NOTIFICATION-TYPE
		OBJECTS { ommp021OtuSignalDegradeAlarm  }
		STATUS  current
		DESCRIPTION
                        "OMMP021 OTU Signal Degrade Alarm Trap" 
        ::= { ommp021AlarmNotification 31 }

	ommp021OtuAlarmIndicationSignalAlarmTrap NOTIFICATION-TYPE
		OBJECTS { ommp021OtuAlarmIndicationSignalAlarm  }
		STATUS  current
		DESCRIPTION
                        "OMMP021 OTU Alarm Indication Signal Alarm Trap" 
        ::= { ommp021AlarmNotification 32 }

	ommp021OtuIncomingAlignmentErrorAlarmTrap NOTIFICATION-TYPE
		OBJECTS { ommp021OtuIncomingAlignmentErrorAlarm  }
		STATUS  current
		DESCRIPTION
                        "OMMP021 OTU Incoming Alignment Error Alarm Trap" 
        ::= { ommp021AlarmNotification 33 }

	ommp021OtuTrailTraceIdentifierMismatchAlarmTrap NOTIFICATION-TYPE
		OBJECTS { ommp021OtuTrailTraceIdentifierMismatchAlarm  }
		STATUS  current
		DESCRIPTION
                        "OMMP021 OTU Sapi Alarm Trap" 
        ::= { ommp021AlarmNotification 34 }

	ommp021OtuBackwardIncomingAlignmentErrorAlarmTrap NOTIFICATION-TYPE
		OBJECTS { ommp021OtuBackwardIncomingAlignmentErrorAlarm  }
		STATUS  current
		DESCRIPTION
                        "OMMP021 OTU Backward Incoming Alignment Error Alarm Trap" 
        ::= { ommp021AlarmNotification 35 }

	ommp021OtuBackwardDefectIndicationAlarmTrap NOTIFICATION-TYPE
		OBJECTS { ommp021OtuBackwardDefectIndicationAlarm  }
		STATUS  current
		DESCRIPTION
                        "OMMP021 OTU Backward Defect Indication Alarm Trap" 
        ::= { ommp021AlarmNotification 36 }

	ommp021OduSignalFailAlarmTrap NOTIFICATION-TYPE
		OBJECTS { ommp021OduSignalFailAlarm  }
		STATUS  current
		DESCRIPTION
                        "OMMP021 ODU Signal Fail Alarm Trap" 
        ::= { ommp021AlarmNotification 37 }

	ommp021OduSignalDegradeAlarmTrap NOTIFICATION-TYPE
		OBJECTS { ommp021OduSignalDegradeAlarm  }
		STATUS  current
		DESCRIPTION
                        "OMMP021 ODU Signal Degrade Alarm Trap" 
        ::= { ommp021AlarmNotification 38 }

	ommp021OduAlarmIndicationSignalAlarmTrap NOTIFICATION-TYPE
		OBJECTS { ommp021OduAlarmIndicationSignalAlarm  }
		STATUS  current
		DESCRIPTION
                        "OMMP021 ODU Alarm Indication Signal Alarm Trap" 
        ::= { ommp021AlarmNotification 39 }

	ommp021OduTrailTraceIdentifierMismatchAlarmTrap NOTIFICATION-TYPE
		OBJECTS { ommp021OtuTrailTraceIdentifierMismatchAlarm  }
		STATUS  current
		DESCRIPTION
                        "OMMP021 ODU Sapi Alarm Trap" 
        ::= { ommp021AlarmNotification 40 }

	ommp021OduLockedDefectAlarmTrap NOTIFICATION-TYPE
		OBJECTS { ommp021OduLockedDefectAlarm  }
		STATUS  current
		DESCRIPTION
                        "OMMP021 ODU Locked Defect Alarm Trap" 
        ::= { ommp021AlarmNotification 41 }

	ommp021OduOpenConnectionIndicationAlarmTrap NOTIFICATION-TYPE
		OBJECTS { ommp021OduOpenConnectionIndicationAlarm  }
		STATUS  current
		DESCRIPTION
                        "OMMP021 ODU Open Connection Indication Alarm Trap" 
        ::= { ommp021AlarmNotification 42 }

	ommp021OduBackwardDefectIndicationAlarmTrap NOTIFICATION-TYPE
		OBJECTS { ommp021OduBackwardDefectIndicationAlarm  }
		STATUS  current
		DESCRIPTION
                        "OMMP021 ODU Backward Defect Indication Alarm Trap" 
        ::= { ommp021AlarmNotification 43 }

	ommp021OpuPayloadMismatchAlarmTrap NOTIFICATION-TYPE
		OBJECTS { ommp021OpuPayloadMismatchAlarm  }
		STATUS  current
		DESCRIPTION
                        "OMMP021 OPU Payload Mismatch Alarm Trap" 
        ::= { ommp021AlarmNotification 44 }

	ommp021EthernetLossOfSignalAlarmTrap NOTIFICATION-TYPE
		OBJECTS { ommp021EthernetLossOfSignalAlarm  }
		STATUS  current
		DESCRIPTION
                        "OMMP021 Ethernet Loss Of Signal Alarm Trap" 
        ::= { ommp021AlarmNotification 45 }

	ommp021EthernetIngressRemoteFaultAlarmTrap NOTIFICATION-TYPE
		OBJECTS { ommp021EthernetIngressRemoteFaultAlarm  }
		STATUS  current
		DESCRIPTION
                        "OMMP021 Ethernet Ingress Remote Fault Alarm Trap" 
        ::= { ommp021AlarmNotification 46 }

	ommp021EthernetEgressRemoteFaultAlarmTrap NOTIFICATION-TYPE
		OBJECTS { ommp021EthernetEgressRemoteFaultAlarm  }
		STATUS  current
		DESCRIPTION
                        "OMMP021 Ethernet Egress Remote Fault Alarm Trap" 
        ::= { ommp021AlarmNotification 47 }

	ommp021EthernetEgressHighBerAlarmTrap NOTIFICATION-TYPE
		OBJECTS { ommp021EthernetEgressHighBerAlarm  }
		STATUS  current
		DESCRIPTION
                        "OMMP021 Ethernet Egress High BER Alarm Trap" 
        ::= { ommp021AlarmNotification 48 }

	ommp021EthernetEgressLocalFaultAlarmTrap NOTIFICATION-TYPE
		OBJECTS { ommp021EthernetEgressLocalFaultAlarm  }
		STATUS  current
		DESCRIPTION
                        "OMMP021 Ethernet Egress Local Fault Alarm Trap" 
        ::= { ommp021AlarmNotification 49 }
        
        ommp021LineOtuLossOfSignalAlarmTrap NOTIFICATION-TYPE
		OBJECTS { ommp021LineOtuLossOfSignalAlarm  }
		STATUS  current
		DESCRIPTION
                        "OMMP021 OTU Loss Of Signal Alarm Trap" 
        ::= { ommp021AlarmNotification 50 }

	ommp021LineOtuLossOfFrameAlarmTrap NOTIFICATION-TYPE
		OBJECTS { ommp021LineOtuLossOfFrameAlarm  }
		STATUS  current
		DESCRIPTION
                        "OMMP021 OTU Loss Of Frame Alarm Trap" 
        ::= { ommp021AlarmNotification 51 }

	ommp021LineOtuOutOfFrameAlarmTrap NOTIFICATION-TYPE
		OBJECTS { ommp021LineOtuOutOfFrameAlarm  }
		STATUS  current
		DESCRIPTION
                        "OMMP021 OTU Out Of Frame Alarm Trap" 
        ::= { ommp021AlarmNotification 52 }

	ommp021LineOtuLossOfMultiFrameAlarmTrap NOTIFICATION-TYPE
		OBJECTS { ommp021LineOtuLossOfMultiFrameAlarm  }
		STATUS  current
		DESCRIPTION
                        "OMMP021 OTU Loss Of Multi Frame Alarm Trap" 
        ::= { ommp021AlarmNotification 53 }

	ommp021LineOtuOutOfMultiFrameAlarmTrap NOTIFICATION-TYPE
		OBJECTS { ommp021LineOtuOutOfMultiFrameAlarm  }
		STATUS  current
		DESCRIPTION
                        "OMMP021 OTU Out Of Multi Frame Alarm Trap" 
        ::= { ommp021AlarmNotification 54 }

	ommp021LineOtuSignalDegradeAlarmTrap NOTIFICATION-TYPE
		OBJECTS { ommp021LineOtuSignalDegradeAlarm  }
		STATUS  current
		DESCRIPTION
                        "OMMP021 OTU Signal Degrade Alarm Trap" 
        ::= { ommp021AlarmNotification 55 }

	ommp021LineOtuAlarmIndicationSignalAlarmTrap NOTIFICATION-TYPE
		OBJECTS { ommp021LineOtuAlarmIndicationSignalAlarm  }
		STATUS  current
		DESCRIPTION
                        "OMMP021 OTU Alarm Indication Signal Alarm Trap" 
        ::= { ommp021AlarmNotification 56 }

	ommp021LineOtuIncomingAlignmentErrorAlarmTrap NOTIFICATION-TYPE
		OBJECTS { ommp021LineOtuIncomingAlignmentErrorAlarm  }
		STATUS  current
		DESCRIPTION
                        "OMMP021 OTU Incoming Alignment Error Alarm Trap" 
        ::= { ommp021AlarmNotification 57 }

	ommp021LineOtuTrailTraceIdentifierMismatchAlarmTrap NOTIFICATION-TYPE
		OBJECTS { ommp021LineOtuTrailTraceIdentifierMismatchAlarm  }
		STATUS  current
		DESCRIPTION
                        "OMMP021 OTU Sapi Alarm Trap" 
        ::= { ommp021AlarmNotification 58 }

	ommp021LineOtuBackwardIncomingAlignmentErrorAlarmTrap NOTIFICATION-TYPE
		OBJECTS { ommp021LineOtuBackwardIncomingAlignmentErrorAlarm  }
		STATUS  current
		DESCRIPTION
                        "OMMP021 OTU Backward Incoming Alignment Error Alarm Trap" 
        ::= { ommp021AlarmNotification 59 }

	ommp021LineOtuBackwardDefectIndicationAlarmTrap NOTIFICATION-TYPE
		OBJECTS { ommp021LineOtuBackwardDefectIndicationAlarm  }
		STATUS  current
		DESCRIPTION
                        "OMMP021 OTU Backward Defect Indication Alarm Trap" 
        ::= { ommp021AlarmNotification 60 }

	ommp021LineOduSignalDegradeAlarmTrap NOTIFICATION-TYPE
		OBJECTS { ommp021LineOduSignalDegradeAlarm  }
		STATUS  current
		DESCRIPTION
                        "OMMP021 ODU Signal Degrade Alarm Trap" 
        ::= { ommp021AlarmNotification 61 }

	ommp021LineOduAlarmIndicationSignalAlarmTrap NOTIFICATION-TYPE
		OBJECTS { ommp021LineOduAlarmIndicationSignalAlarm  }
		STATUS  current
		DESCRIPTION
                        "OMMP021 ODU Alarm Indication Signal Alarm Trap" 
        ::= { ommp021AlarmNotification 62 }

	ommp021LineOduTrailTraceIdentifierMismatchAlarmTrap NOTIFICATION-TYPE
		OBJECTS { ommp021LineOtuTrailTraceIdentifierMismatchAlarm  }
		STATUS  current
		DESCRIPTION
                        "OMMP021 ODU Sapi Alarm Trap" 
        ::= { ommp021AlarmNotification 63 }

	ommp021LineOduLockedDefectAlarmTrap NOTIFICATION-TYPE
		OBJECTS { ommp021LineOduLockedDefectAlarm  }
		STATUS  current
		DESCRIPTION
                        "OMMP021 ODU Locked Defect Alarm Trap" 
        ::= { ommp021AlarmNotification 64 }

	ommp021LineOduOpenConnectionIndicationAlarmTrap NOTIFICATION-TYPE
		OBJECTS { ommp021LineOduOpenConnectionIndicationAlarm  }
		STATUS  current
		DESCRIPTION
                        "OMMP021 ODU Open Connection Indication Alarm Trap" 
        ::= { ommp021AlarmNotification 65 }

	ommp021LineOduBackwardDefectIndicationAlarmTrap NOTIFICATION-TYPE
		OBJECTS { ommp021LineOduBackwardDefectIndicationAlarm  }
		STATUS  current
		DESCRIPTION
                        "OMMP021 ODU Backward Defect Indication Alarm Trap" 
        ::= { ommp021AlarmNotification 66 }

	ommp021LineOpuPayloadMismatchAlarmTrap NOTIFICATION-TYPE
		OBJECTS { ommp021LineOpuPayloadMismatchAlarm  }
		STATUS  current
		DESCRIPTION
                        "OMMP021 OPU Payload Mismatch Alarm Trap" 
        ::= { ommp021AlarmNotification 67 }

--*****************************************************************************
--				    PERFORMANCE
--*****************************************************************************        

	ommp021PerformanceTable OBJECT-TYPE
	      SYNTAX  SEQUENCE OF Ommp021PerformanceEntry
              MAX-ACCESS  not-accessible
              STATUS  current
              DESCRIPTION
                      "Gives Optical and Signal performance status of the OMMP021 card"
		::= { ommp021Performance 1 }	

	ommp021PerformanceEntry   OBJECT-TYPE
              SYNTAX  Ommp021PerformanceEntry 
              MAX-ACCESS  not-accessible
              STATUS  current
              DESCRIPTION 
              	""
		INDEX   { node, rack , subRack , slot , ommp021InterfaceNumber}
		::= { ommp021PerformanceTable 1 }
	
	Ommp021PerformanceEntry ::= 
		SEQUENCE {
				ommp021Cfp2InputPower							DisplayString,
				ommp021Cfp2OutputPower						DisplayString,
				ommp021Cfp2SupplyVoltage						DisplayString,
				ommp021Cfp2Temperature						DisplayString,
				ommp021Qsfp28InputPower							DisplayString,
				ommp021Qsfp28OutputPower						DisplayString,
				ommp021Qsfp28BiasCurrent						DisplayString,
				ommp021Qsfp28SupplyVoltage						DisplayString,
				ommp021Qsfp28Temperature						DisplayString,
				ommp021OtnFecUncorrectedWords					DisplayString,
				ommp021OtnFecCorrectedBits					DisplayString,
				ommp021OtuBitInterleavedParityErrors					DisplayString,
				ommp021OtuBackwardErrorIndicationErrorCount					DisplayString,
				ommp021OtuErrorFreeSeconds					DisplayString,
				ommp021OtuErrorSeconds					DisplayString,
				ommp021OtuBackgroundBlockErrors					DisplayString,
				ommp021OtuSevereErrorSeconds					DisplayString,
				ommp021OtuUnavailableSeconds					DisplayString,
				ommp021OtuFarEndErrorFreeSeconds					DisplayString,
				ommp021OtuFarEndBackgroundBlockErrors					DisplayString,
				ommp021OtuFarEndSevereErrorSeconds					DisplayString,
				ommp021OtuFarEndUnavailableSeconds					DisplayString,
				ommp021OtuFarEndErrorSeconds					DisplayString,
				ommp021OduBitInterleavedParityErrors					DisplayString,			
				ommp021OduBackwardErrorIndicationErrorCount					DisplayString,
				ommp021OduErrorFreeSeconds					DisplayString,
				ommp021OduErrorSeconds					DisplayString,
				ommp021OduBackgroundBlockErrors					DisplayString,
				ommp021OduSevereErrorSeconds					DisplayString,
				ommp021OduUnavailableSeconds					DisplayString,
				ommp021OduFarEndErrorFreeSeconds					DisplayString,
				ommp021OduFarEndErrorSeconds					DisplayString,
				ommp021OduFarEndBackgroundBlockErrors					DisplayString,
				ommp021OduFarEndSevereErrorSeconds					DisplayString,
				ommp021OduFarEndUnavailableSeconds					DisplayString,			
				ommp021EthernetMacTerminatedFramesTransmitted					DisplayString,
				ommp021EthernetMacTerminatedFramesReceived					DisplayString,
				ommp021EthernetMacTerminatedUnicastFramesReceived					DisplayString,
				ommp021EthernetMacTerminatedMulticastFramesReceived					DisplayString,
				ommp021EthernetMacTerminatedBroadcastFramesReceived					DisplayString,
				ommp021EthernetMacTerminatedUnderSizeFramesReceived					DisplayString,
				ommp021EthernetMacTerminatedOverSizeFramesReceived					DisplayString,
				ommp021EthernetMacTerminatedFrameCheckSequenceErrorsReceived					DisplayString,	
				ommp021LineOtnFecUncorrectedWords					DisplayString,
				ommp021LineOtnFecCorrectedBits					DisplayString,
				ommp021LineOtuBitInterleavedParityErrors					DisplayString,
				ommp021LineOtuBackwardErrorIndicationErrorCount					DisplayString,
				ommp021LineOtuErrorFreeSeconds					DisplayString,
				ommp021LineOtuErrorSeconds					DisplayString,
				ommp021LineOtuBackgroundBlockErrors					DisplayString,
				ommp021LineOtuSevereErrorSeconds					DisplayString,
				ommp021LineOtuUnavailableSeconds					DisplayString,
				ommp021LineOtuFarEndErrorFreeSeconds					DisplayString,
				ommp021LineOtuFarEndBackgroundBlockErrors					DisplayString,
				ommp021LineOtuFarEndSevereErrorSeconds					DisplayString,
				ommp021LineOtuFarEndUnavailableSeconds					DisplayString,
				ommp021LineOtuFarEndErrorSeconds					DisplayString,
				ommp021LineOduBitInterleavedParityErrors					DisplayString,
				ommp021LineOduBackwardErrorIndicationErrorCount					DisplayString,
				ommp021LineOduErrorFreeSeconds					DisplayString,
				ommp021LineOduErrorSeconds					DisplayString,
				ommp021LineOduBackgroundBlockErrors					DisplayString,
				ommp021LineOduSevereErrorSeconds					DisplayString,
				ommp021LineOduUnavailableSeconds					DisplayString,
				ommp021LineOduFarEndErrorFreeSeconds					DisplayString,
				ommp021LineOduFarEndErrorSeconds					DisplayString,
				ommp021LineOduFarEndBackgroundBlockErrors					DisplayString,
				ommp021LineOduFarEndSevereErrorSeconds					DisplayString,
				ommp021LineOduFarEndUnavailableSeconds					DisplayString,			
				ommp021PerformanceTableRowStatus					RowStatus
			}	           

	ommp021Cfp2InputPower OBJECT-TYPE
		SYNTAX  DisplayString
		MAX-ACCESS  read-only
		STATUS  current
		DESCRIPTION
			"Gives the current Input power(dbm) received at the port
			-----------------------------
			ommp021InterfaceNumber:
			3 - LINE-
			-----------------------------
			Values:
			eg: -9.0
			-----------------------------"
	::= { ommp021PerformanceEntry 1 }

	ommp021Cfp2OutputPower OBJECT-TYPE
		SYNTAX  DisplayString
		MAX-ACCESS  read-only
		STATUS  current
		DESCRIPTION
			"Gives the current Output power(dbm) transmitted at the port
			-----------------------------
			ommp021InterfaceNumber:
			3 - LINE-
			-----------------------------
			Values:
			eg: -0.6
			-----------------------------"
	::= { ommp021PerformanceEntry 2 }

	ommp021Cfp2SupplyVoltage OBJECT-TYPE
		SYNTAX  DisplayString
		MAX-ACCESS  read-only
		STATUS  current
		DESCRIPTION
			"Gives the Supply Voltage of the port
			-----------------------------
			ommp021InterfaceNumber:
			3 - LINE-
			-----------------------------
			Values:
			eg: 3.3
			-----------------------------"
	::= { ommp021PerformanceEntry 3 }

	ommp021Cfp2Temperature OBJECT-TYPE
		SYNTAX  DisplayString
		MAX-ACCESS  read-only
		STATUS  current
		DESCRIPTION
			"Gives the temperature(degree celcius) of the transmitter
			at  the port
			-----------------------------
			ommp021InterfaceNumber:
			3 - LINE-
			-----------------------------
			Values:
			eg: 33.35
			-----------------------------"
	::= { ommp021PerformanceEntry 4 }

	ommp021Qsfp28InputPower OBJECT-TYPE
		SYNTAX  DisplayString
		MAX-ACCESS  read-only
		STATUS  current
		DESCRIPTION
			"Gives the current Input power(dbm) received at the port
			-----------------------------
			ommp021InterfaceNumber:
			CLIENT-1
			CLIENT-2
			LINE-3
			-----------------------------
			Values:
			eg: -9.0
			-----------------------------"
	::= { ommp021PerformanceEntry 5 }

	ommp021Qsfp28OutputPower OBJECT-TYPE
		SYNTAX  DisplayString
		MAX-ACCESS  read-only
		STATUS  current
		DESCRIPTION
			"Gives the current Output power(dbm) transmitted at the port
			-----------------------------
			ommp021InterfaceNumber:
			CLIENT-1
			CLIENT-2
			LINE-3
			-----------------------------
			Values:
			eg: -6.0
			-----------------------------"
	::= { ommp021PerformanceEntry 6 }

	ommp021Qsfp28BiasCurrent OBJECT-TYPE
		SYNTAX  DisplayString
		MAX-ACCESS  read-only
		STATUS  current
		DESCRIPTION
			"Gives the bias current(mA) thats transmitted at the port
			-----------------------------
			ommp021InterfaceNumber:
			CLIENT-1
			CLIENT-2
			LINE-3
			-----------------------------
			Values:
			eg: 55
			-----------------------------"
	::= { ommp021PerformanceEntry 7 }

	ommp021Qsfp28SupplyVoltage OBJECT-TYPE
		SYNTAX  DisplayString
		MAX-ACCESS  read-only
		STATUS  current
		DESCRIPTION
			"Gives the Supply Voltage of the port
			-----------------------------
			ommp021InterfaceNumber:
			CLIENT-1
			CLIENT-2
			LINE-3
			-----------------------------
			Values:
			eg: 3.3
			-----------------------------"
	::= { ommp021PerformanceEntry 8 }

	ommp021Qsfp28Temperature OBJECT-TYPE
		SYNTAX  DisplayString
		MAX-ACCESS  read-only
		STATUS  current
		DESCRIPTION
			"Gives the temperature(degree celcius) of the transmitter
			at the port
			-----------------------------
			ommp021InterfaceNumber:
			CLIENT-1
			CLIENT-2
			LINE-3
			-----------------------------
			Values:
			eg: 33.35
			-----------------------------"
	::= { ommp021PerformanceEntry 9 }

	ommp021OtnFecUncorrectedWords OBJECT-TYPE
		SYNTAX  DisplayString
		MAX-ACCESS  read-only
		STATUS  current
		DESCRIPTION
			"For port configured with OTU4/OTUC2 traffic,
			OTU Uncorrected Word Error Counter counts the number of
			FEC errored code words that could not be corrected.
			-----------------------------
			ommp021InterfaceNumber:
			CLIENT-1
			CLIENT-2
			LINE-3
			-----------------------------
			Values:
			eg: 1234
			-----------------------------"
	::= { ommp021PerformanceEntry 10 }

	ommp021OtnFecCorrectedBits OBJECT-TYPE
		SYNTAX  DisplayString
		MAX-ACCESS  read-only
		STATUS  current
		DESCRIPTION
			"For port configured with OTU4/OTUC2 traffic,
			OTU Corrected Bit Error Counter counts the number of
			FEC error bits that could be corrected(sum of ones
			corrected and zeros corrected bits).
			-----------------------------
			ommp021InterfaceNumber:
			CLIENT-1
			CLIENT-2
			LINE-3
			-----------------------------
			Values:
			eg: 1234
			-----------------------------"
	::= { ommp021PerformanceEntry 11 }

	ommp021OtuBitInterleavedParityErrors OBJECT-TYPE
		SYNTAX  DisplayString
		MAX-ACCESS  read-only
		STATUS  current
		DESCRIPTION
			"For port configured with OTU4/OTUC2 traffic,
			OTU-BIP Counter counts the Parity errors evaluated by
			SM field of an OTU4 frame.
			-----------------------------
			ommp021InterfaceNumber:
			CLIENT-1
			CLIENT-2
			LINE-3
			-----------------------------
			Values:
			eg: 1234
			-----------------------------"
	::= { ommp021PerformanceEntry 12 }

	ommp021OtuBackwardErrorIndicationErrorCount OBJECT-TYPE
		SYNTAX  DisplayString
		MAX-ACCESS  read-only
		STATUS  current
		DESCRIPTION
			"For port configured with OTU4/OTUC2 traffic,
			this signal is used to convey in the upstream direction 
			the count of interleaved bit blocks that have 
			been detected in error using the BIP-8 code.
			-----------------------------
			ommp021InterfaceNumber:
			CLIENT-1
			CLIENT-2
			LINE-3
			-----------------------------
			Values:
			eg: 1234
			-----------------------------"
	::= { ommp021PerformanceEntry 13 }

	ommp021OtuErrorFreeSeconds OBJECT-TYPE
		SYNTAX  DisplayString
		MAX-ACCESS  read-only
		STATUS  current
		DESCRIPTION
			"For port configured with OTU4/OTUC2 traffic,
			OTU Error Free Seconds increases when no BIP errors
			or defects are detected
			-----------------------------
			ommp021InterfaceNumber:
			CLIENT-1
			CLIENT-2
			LINE-3
			-----------------------------
			Values:
			eg: 1234
			-----------------------------"
	::= { ommp021PerformanceEntry 14 }

	ommp021OtuErrorSeconds OBJECT-TYPE
		SYNTAX  DisplayString
		MAX-ACCESS  read-only
		STATUS  current
		DESCRIPTION
			"For port configured with OTU4/OTUC2 traffic,
			OTU Error Seconds increases when any defects like 
			OTU-AIS, SM-TIM etc are detected at the
			section monitoring level
			-----------------------------
			ommp021InterfaceNumber:
			CLIENT-1
			CLIENT-2
			LINE-3
			-----------------------------
			Values:
			eg: 1234
			-----------------------------"
	::= { ommp021PerformanceEntry 15 }

	ommp021OtuBackgroundBlockErrors OBJECT-TYPE
		SYNTAX  DisplayString
		MAX-ACCESS  read-only
		STATUS  current
		DESCRIPTION
			"For port configured with OTU4/OTUC2 traffic,
			OTU Background Block Errors increases on defects 
			detected and when BIP errors are less than 15% errored
			blocks received 
			-----------------------------
			ommp021InterfaceNumber:
			CLIENT-1
			CLIENT-2
			LINE-3
			-----------------------------
			Values:
			eg: 1234
			-----------------------------"
	::= { ommp021PerformanceEntry 16 }

	ommp021OtuSevereErrorSeconds OBJECT-TYPE
		SYNTAX  DisplayString
		MAX-ACCESS  read-only
		STATUS  current
		DESCRIPTION
			"For port configured with OTU4/OTUC2 traffic,
			OTU Severe Error Seconds increases on defects
			detected and when BIP errors are greater than or
			equal to 15% errored blocks received 
			-----------------------------
			ommp021InterfaceNumber:
			CLIENT-1
			CLIENT-2
			LINE-3
			-----------------------------
			Values:
			eg: 1234
			-----------------------------"
	::= { ommp021PerformanceEntry 17 }

	ommp021OtuUnavailableSeconds OBJECT-TYPE
		SYNTAX  DisplayString
		MAX-ACCESS  read-only
		STATUS  current
		DESCRIPTION
			"For port configured with OTU4/OTUC2 traffic,
			OTU Unavailable Seconds increases,
			when 10 consecutive OTU Severe Error seconds
			are detected
			-----------------------------
			ommp021InterfaceNumber:
			CLIENT-1
			CLIENT-2
			LINE-3
			-----------------------------
			Values:
			eg: 1234
			-----------------------------"
	::= { ommp021PerformanceEntry 18 }

	ommp021OtuFarEndErrorFreeSeconds OBJECT-TYPE
		SYNTAX  DisplayString
		MAX-ACCESS  read-only
		STATUS  current
		DESCRIPTION
			"For port configured with OTU4/OTUC2 traffic,
			OTU Far end Error Free Seconds, increases when no
			backward errors or defects like BDI or BEI
			are detected in the incoming OTU signal.
			-----------------------------
			ommp021InterfaceNumber:
			CLIENT-1
			CLIENT-2
			LINE-3
			-----------------------------
			Values:
			eg: 1234
			-----------------------------"
	::= { ommp021PerformanceEntry 19 }

	ommp021OtuFarEndBackgroundBlockErrors OBJECT-TYPE
		SYNTAX  DisplayString
		MAX-ACCESS  read-only
		STATUS  current
		DESCRIPTION
			"For port configured with OTU4/OTUC2 traffic,
			OTU Far End Background Block Errors increases when BEI
			errors are less than 15% Errored Blocks in incoming
			OTU signal.
			-----------------------------
			ommp021InterfaceNumber:
			CLIENT-1
			CLIENT-2
			LINE-3
			-----------------------------
			Values:
			eg: 1234
			-----------------------------"
	::= { ommp021PerformanceEntry 20 }

	ommp021OtuFarEndSevereErrorSeconds OBJECT-TYPE
		SYNTAX  DisplayString
		MAX-ACCESS  read-only
		STATUS  current
		DESCRIPTION
			"For port configured with OTU4/OTUC2 traffic,
			OTU Far End Severe Error Seconds increases on defects
			like BDI are detected and when BEI errors are greater
			than or equal to 15% Errored Blocks in incoming OTU 
			signal.
			-----------------------------
			ommp021InterfaceNumber:
			CLIENT-1
			CLIENT-2
			LINE-3
			-----------------------------
			Values:
			eg: 1234
			-----------------------------"
	::= { ommp021PerformanceEntry 21 }

	ommp021OtuFarEndUnavailableSeconds OBJECT-TYPE
		SYNTAX  DisplayString
		MAX-ACCESS  read-only
		STATUS  current
		DESCRIPTION
			"For port configured with OTU4/OTUC2 traffic,
			OTU Far End Unavailable Seconds increases, 
			after 9 consecutive OTU Far End Severe Error
			seconds are detected
			-----------------------------
			ommp021InterfaceNumber:
			CLIENT-1
			CLIENT-2
			LINE-3
			-----------------------------
			Values:
			eg: 1234
			-----------------------------"
	::= { ommp021PerformanceEntry 22 }

	ommp021OtuFarEndErrorSeconds OBJECT-TYPE
		SYNTAX  DisplayString
		MAX-ACCESS  read-only
		STATUS  current
		DESCRIPTION
			"For port configured with OTU4/OTUC2 traffic,
			OTU Far End Error Seconds increases on
			detection of defects like BDI in incoming
			OTU signal.
			-----------------------------
			ommp021InterfaceNumber:
			CLIENT-1
			CLIENT-2
			LINE-3
			-----------------------------
			Values:
			eg: 1234
			-----------------------------"
	::= { ommp021PerformanceEntry 23 }

	ommp021OduBitInterleavedParityErrors OBJECT-TYPE
		SYNTAX  DisplayString
		MAX-ACCESS  read-only
		STATUS  current
		DESCRIPTION
			"For port configured with OTU4/OTUC2 traffic,
			ODU-BIP Counter counts the Parity errors evaluated by
			PM field of an OTU4 frame
			-----------------------------
			ommp021InterfaceNumber:
			CLIENT-1
			CLIENT-2
			LINE-3
			-----------------------------
			Values:
			eg: 1234
			-----------------------------"
	::= { ommp021PerformanceEntry 24 }

	ommp021OduBackwardErrorIndicationErrorCount OBJECT-TYPE
		SYNTAX  DisplayString
		MAX-ACCESS  read-only
		STATUS  current
		DESCRIPTION
			"For port configured with OTU4/OTUC2 traffic,
			this signal is used to convey in the upstream direction 
			the count of interleaved bit blocks that have 
			been detected in error using the BIP-8 code.
			-----------------------------
			ommp021InterfaceNumber:
			CLIENT-1
			CLIENT-2
			LINE-3
			-----------------------------
			Values:
			eg: 1234
			-----------------------------"
	::= { ommp021PerformanceEntry 25 }

	ommp021OduErrorFreeSeconds OBJECT-TYPE
		SYNTAX  DisplayString
		MAX-ACCESS  read-only
		STATUS  current
		DESCRIPTION
			"For port configured with OTU4/OTUC2 traffic,
			ODU Error Free Seconds increases,
			when no BIP errors or defects are detected at the
			path monitoring level
			-----------------------------
			ommp021InterfaceNumber:
			CLIENT-1
			CLIENT-2
			LINE-3
			-----------------------------
			Values:
			eg: 1234
			-----------------------------"
	::= { ommp021PerformanceEntry 26 }

	ommp021OduErrorSeconds OBJECT-TYPE
		SYNTAX  DisplayString
		MAX-ACCESS  read-only
		STATUS  current
		DESCRIPTION
			"For port configured with OTU4/OTUC2 traffic,
			ODU Error Seconds increases on defects detected at the
			path monitoring level
			-----------------------------
			ommp021InterfaceNumber:
			CLIENT-1
			CLIENT-2
			LINE-3
			-----------------------------
			Values:
			eg: 1234
			-----------------------------"
	::= { ommp021PerformanceEntry 27 }

	ommp021OduBackgroundBlockErrors OBJECT-TYPE
		SYNTAX  DisplayString
		MAX-ACCESS  read-only
		STATUS  current
		DESCRIPTION
			"For port configured with OTU4/OTUC2 traffic,
			ODU Background Block Errors increases on defects 
			detected and when BIP errors are less than 15% 
			Errored Blocks in incoming OTU signal.
			-----------------------------
			ommp021InterfaceNumber:
			CLIENT-1
			CLIENT-2
			LINE-3
			-----------------------------
			Values:
			eg: 1234
			-----------------------------"
	::= { ommp021PerformanceEntry 28 }

	ommp021OduSevereErrorSeconds OBJECT-TYPE
		SYNTAX  DisplayString
		MAX-ACCESS  read-only
		STATUS  current
		DESCRIPTION
			"For port configured with OTU4/OTUC2 traffic,
			ODU Severe Error Seconds increases on defects detected
			and when BIP errors are more than 15% Errored Blocks
			in incoming OTU signal.
			-----------------------------
			ommp021InterfaceNumber:
			CLIENT-1
			CLIENT-2
			LINE-3
			-----------------------------
			Values:
			eg: 1234
			-----------------------------"
	::= { ommp021PerformanceEntry 29 }

	ommp021OduUnavailableSeconds OBJECT-TYPE
		SYNTAX  DisplayString
		MAX-ACCESS  read-only
		STATUS  current
		DESCRIPTION
			"For port configured with OTU4/OTUC2 traffic,
			ODU Unavailable Seconds increases, when 10 consecutive
			Severe ODU Error seconds are detected
			-----------------------------
			ommp021InterfaceNumber:
			CLIENT-1
			CLIENT-2
			LINE-3
			-----------------------------
			Values:
			eg: 1234
			-----------------------------"
	::= { ommp021PerformanceEntry 30 }

	ommp021OduFarEndErrorFreeSeconds OBJECT-TYPE
		SYNTAX  DisplayString
		MAX-ACCESS  read-only
		STATUS  current
		DESCRIPTION
			"For port configured with OTU4/OTUC2 traffic,
			ODU Far end Error Free Seconds, increases when no
			far end errors or defects are detected
			-----------------------------
			ommp021InterfaceNumber:
			CLIENT-1
			CLIENT-2
			LINE-3
			-----------------------------
			Values:
			eg: 1234
			-----------------------------"
	::= { ommp021PerformanceEntry 31 }

	ommp021OduFarEndErrorSeconds OBJECT-TYPE
		SYNTAX  DisplayString
		MAX-ACCESS  read-only
		STATUS  current
		DESCRIPTION
			"For port configured with OTU4/OTUC2 traffic,
			ODU Far End Error Seconds increases on detection of
			defects like BDI and BEI at path monitoring level
			-----------------------------
			ommp021InterfaceNumber:
			CLIENT-1
			CLIENT-2
			LINE-3
			-----------------------------
			Values:
			eg: 1234
			-----------------------------"
	::= { ommp021PerformanceEntry 32 }

	ommp021OduFarEndBackgroundBlockErrors OBJECT-TYPE
		SYNTAX  DisplayString
		MAX-ACCESS  read-only
		STATUS  current
		DESCRIPTION
			"For port configured with OTU4/OTUC2 traffic,
			ODU Far End Background Block Errors increases when
			BEI errors are less than 15% Errored Blocks in
			incoming OTU signal.
			-----------------------------
			ommp021InterfaceNumber:
			CLIENT-1
			CLIENT-2
			LINE-3
			-----------------------------
			Values:
			eg: 1234
			-----------------------------"
	::= { ommp021PerformanceEntry 33 }

	ommp021OduFarEndSevereErrorSeconds OBJECT-TYPE
		SYNTAX  DisplayString
		MAX-ACCESS  read-only
		STATUS  current
		DESCRIPTION
			"For port configured with OTU4/OTUC2 traffic,
			ODU Far End Severe Error Seconds increases on defects
			like BDI are detected and when BEI errors are more than
			15% Errored Blocks in incoming OTU signal.
			-----------------------------
			ommp021InterfaceNumber:
			CLIENT-1
			CLIENT-2
			LINE-3
			-----------------------------
			Values:
			eg: 1234
			-----------------------------"
	::= { ommp021PerformanceEntry 34 }

	ommp021OduFarEndUnavailableSeconds OBJECT-TYPE
		SYNTAX  DisplayString
		MAX-ACCESS  read-only
		STATUS  current
		DESCRIPTION
			"For port configured with OTU4/OTUC2 traffic,
			ODU Far End Unavailable Seconds increases, when 10
			consecutive OTU Far End Error seconds are detected
			-----------------------------
			ommp021InterfaceNumber:
			CLIENT-1
			CLIENT-2
			LINE-3
			-----------------------------
			Values:
			eg: 1234
			-----------------------------"
	::= { ommp021PerformanceEntry 35 }

	ommp021EthernetMacTerminatedFramesTransmitted OBJECT-TYPE
		SYNTAX  DisplayString
		MAX-ACCESS  read-only
		STATUS  current
		DESCRIPTION
			"For port configured with Ethernet traffic,
			gives Tx Good frames count.
			-----------------------------
			ommp021InterfaceNumber:
			CLIENT-1
			CLIENT-2
			LINE-3
			-----------------------------
			Values:
			eg: 1e-3
			-----------------------------"
	::= { ommp021PerformanceEntry 36 }

	ommp021EthernetMacTerminatedFramesReceived OBJECT-TYPE
		SYNTAX  DisplayString
		MAX-ACCESS  read-only
		STATUS  current
		DESCRIPTION
			"For port configured with Ethernet traffic,
			gives Tx Good Octects frames count.
			-----------------------------
			ommp021InterfaceNumber:
			CLIENT-1
			CLIENT-2
			LINE-3
			-----------------------------
			Values:
			eg: 1e-3
			-----------------------------"
	::= { ommp021PerformanceEntry 37 }

	ommp021EthernetMacTerminatedUnicastFramesReceived OBJECT-TYPE
		SYNTAX  DisplayString
		MAX-ACCESS  read-only
		STATUS  current
		DESCRIPTION
			"For port configured with Ethernet traffic,
			gives Tx Good 65B to 127Bpkt frames count.
			-----------------------------
			ommp021InterfaceNumber:
			CLIENT-1
			CLIENT-2
			LINE-3
			-----------------------------
			Values:
			eg: 1e-3
			-----------------------------"
	::= { ommp021PerformanceEntry 38 }

	ommp021EthernetMacTerminatedMulticastFramesReceived OBJECT-TYPE
		SYNTAX  DisplayString
		MAX-ACCESS  read-only
		STATUS  current
		DESCRIPTION
			"For port configured with Ethernet traffic,
			gives Tx Good 256B to 511Bpkt frames count.
			-----------------------------
			ommp021InterfaceNumber:
			CLIENT-1
			CLIENT-2
			LINE-3
			-----------------------------
			Values:
			eg: 1e-3
			-----------------------------"
	::= { ommp021PerformanceEntry 39 }

	ommp021EthernetMacTerminatedBroadcastFramesReceived OBJECT-TYPE
		SYNTAX  DisplayString
		MAX-ACCESS  read-only
		STATUS  current
		DESCRIPTION
			"For port configured with Ethernet traffic,
			gives Tx Good 1024B to 1518Bpkt frames count.
			-----------------------------
			ommp021InterfaceNumber:
			CLIENT-1
			CLIENT-2
			LINE-3
			-----------------------------
			Values:
			eg: 1e-3
			-----------------------------"
	::= { ommp021PerformanceEntry 40 }

	ommp021EthernetMacTerminatedUnderSizeFramesReceived OBJECT-TYPE
		SYNTAX  DisplayString
		MAX-ACCESS  read-only
		STATUS  current
		DESCRIPTION
			"For port configured with Ethernet traffic,
			gives Tx Good jumbo frames count.
			-----------------------------
			ommp021InterfaceNumber:
			CLIENT-1
			CLIENT-2
			LINE-3
			-----------------------------
			Values:
			eg: 1e-3
			-----------------------------"
	::= { ommp021PerformanceEntry 41 }

	ommp021EthernetMacTerminatedOverSizeFramesReceived OBJECT-TYPE
		SYNTAX  DisplayString
		MAX-ACCESS  read-only
		STATUS  current
		DESCRIPTION
			"For port configured with Ethernet traffic,
			gives Tx Bad Octects frames count.
			-----------------------------
			ommp021InterfaceNumber:
			CLIENT-1
			CLIENT-2
			LINE-3
			-----------------------------
			Values:
			eg: 1e-3
			-----------------------------"
	::= { ommp021PerformanceEntry 42 }

	ommp021EthernetMacTerminatedFrameCheckSequenceErrorsReceived OBJECT-TYPE
		SYNTAX  DisplayString
		MAX-ACCESS  read-only
		STATUS  current
		DESCRIPTION
			"For port configured with Ethernet traffic,
			gives Tx Bad 65B to 127Bpkt frames count.
			-----------------------------
			ommp021InterfaceNumber:
			CLIENT-1
			CLIENT-2
			LINE-3
			-----------------------------
			Values:
			eg: 1e-3
			-----------------------------"
	::= { ommp021PerformanceEntry 43 }
	
	ommp021LineOtnFecUncorrectedWords OBJECT-TYPE
		SYNTAX  DisplayString
		MAX-ACCESS  read-only
		STATUS  current
		DESCRIPTION
			"For port configured with OTU4/OTUC2 traffic,
			OTU Uncorrected Word Error Counter counts the number of
			FEC errored code words that could not be corrected.
			-----------------------------
			ommp021 InterfaceNumber:
			1 to 2 - CLIENT-1 and CLIENT-2
			-----------------------------
			Values:
			eg: 1234
			-----------------------------"
	::= { ommp021PerformanceEntry 44 }

	ommp021LineOtnFecCorrectedBits OBJECT-TYPE
		SYNTAX  DisplayString
		MAX-ACCESS  read-only
		STATUS  current
		DESCRIPTION
			"For port configured with OTU4/OTUC2 traffic,
			OTU Corrected Bit Error Counter counts the number of
			FEC error bits that could be corrected(sum of ones
			corrected and zeros corrected bits).
			-----------------------------
			ommp021 InterfaceNumber:
			1 to 2 - CLIENT-1 and CLIENT-2
			-----------------------------
			Values:
			eg: 1234
			-----------------------------"
	::= { ommp021PerformanceEntry 45 }

	ommp021LineOtuBitInterleavedParityErrors OBJECT-TYPE
		SYNTAX  DisplayString
		MAX-ACCESS  read-only
		STATUS  current
		DESCRIPTION
			"For port configured with OTU4/OTUC2 traffic,
			OTU-BIP Counter counts the Parity errors evaluated by
			SM field of an OTU4 frame.
			-----------------------------
			ommp021 InterfaceNumber:
			1 to 2 - CLIENT-1 and CLIENT-2
			-----------------------------
			Values:
			eg: 1234
			-----------------------------"
	::= { ommp021PerformanceEntry 46 }

	ommp021LineOtuBackwardErrorIndicationErrorCount OBJECT-TYPE
		SYNTAX  DisplayString
		MAX-ACCESS  read-only
		STATUS  current
		DESCRIPTION
			"For port configured with OTU4/OTUC2 traffic,
			this signal is used to convey in the upstream direction 
			the count of interleaved bit blocks that have 
			been detected in error using the BIP-8 code.
			-----------------------------
			ommp021 InterfaceNumber:
			1 to 2 - CLIENT-1 and CLIENT-2
			-----------------------------
			Values:
			eg: 1234
			-----------------------------"
	::= { ommp021PerformanceEntry 47 }

	ommp021LineOtuErrorFreeSeconds OBJECT-TYPE
		SYNTAX  DisplayString
		MAX-ACCESS  read-only
		STATUS  current
		DESCRIPTION
			"For port configured with OTU4/OTUC2 traffic,
			OTU Error Free Seconds increases when no BIP errors
			or defects are detected
			-----------------------------
			ommp021 InterfaceNumber:
			1 to 2 - CLIENT-1 and CLIENT-2
			-----------------------------
			Values:
			eg: 1234
			-----------------------------"
	::= { ommp021PerformanceEntry 48 }

	ommp021LineOtuErrorSeconds OBJECT-TYPE
		SYNTAX  DisplayString
		MAX-ACCESS  read-only
		STATUS  current
		DESCRIPTION
			"For port configured with OTU4/OTUC2 traffic,
			OTU Error Seconds increases when any defects like 
			OTU-AIS, SM-TIM etc are detected at the
			section monitoring level
			-----------------------------
			ommp021 InterfaceNumber:
			1 to 2 - CLIENT-1 and CLIENT-2
			-----------------------------
			Values:
			eg: 1234
			-----------------------------"
	::= { ommp021PerformanceEntry 49 }

	ommp021LineOtuBackgroundBlockErrors OBJECT-TYPE
		SYNTAX  DisplayString
		MAX-ACCESS  read-only
		STATUS  current
		DESCRIPTION
			"For port configured with OTU4/OTUC2 traffic,
			OTU Background Block Errors increases on defects 
			detected and when BIP errors are less than 15% errored
			blocks received 
			-----------------------------
			ommp021 InterfaceNumber:
			1 to 2 - CLIENT-1 and CLIENT-2
			-----------------------------
			Values:
			eg: 1234
			-----------------------------"
	::= { ommp021PerformanceEntry 50 }

	ommp021LineOtuSevereErrorSeconds OBJECT-TYPE
		SYNTAX  DisplayString
		MAX-ACCESS  read-only
		STATUS  current
		DESCRIPTION
			"For port configured with OTU4/OTUC2 traffic,
			OTU Severe Error Seconds increases on defects
			detected and when BIP errors are greater than or
			equal to 15% errored blocks received 
			-----------------------------
			ommp021 InterfaceNumber:
			1 to 2 - CLIENT-1 and CLIENT-2
			-----------------------------
			Values:
			eg: 1234
			-----------------------------"
	::= { ommp021PerformanceEntry 51 }

	ommp021LineOtuUnavailableSeconds OBJECT-TYPE
		SYNTAX  DisplayString
		MAX-ACCESS  read-only
		STATUS  current
		DESCRIPTION
			"For port configured with OTU4/OTUC2 traffic,
			OTU Unavailable Seconds increases,
			when 10 consecutive OTU Severe Error seconds
			are detected
			-----------------------------
			ommp021 InterfaceNumber:
			1 to 2 - CLIENT-1 and CLIENT-2
			-----------------------------
			Values:
			eg: 1234
			-----------------------------"
	::= { ommp021PerformanceEntry 52 }

	ommp021LineOtuFarEndErrorFreeSeconds OBJECT-TYPE
		SYNTAX  DisplayString
		MAX-ACCESS  read-only
		STATUS  current
		DESCRIPTION
			"For port configured with OTU4/OTUC2 traffic,
			OTU Far end Error Free Seconds, increases when no
			backward errors or defects like BDI or BEI
			are detected in the incoming OTU signal.
			-----------------------------
			ommp021 InterfaceNumber:
			1 to 2 - CLIENT-1 and CLIENT-2
			-----------------------------
			Values:
			eg: 1234
			-----------------------------"
	::= { ommp021PerformanceEntry 53 }

	ommp021LineOtuFarEndBackgroundBlockErrors OBJECT-TYPE
		SYNTAX  DisplayString
		MAX-ACCESS  read-only
		STATUS  current
		DESCRIPTION
			"For port configured with OTU4/OTUC2 traffic,
			OTU Far End Background Block Errors increases when BEI
			errors are less than 15% Errored Blocks in incoming
			OTU signal.
			-----------------------------
			ommp021 InterfaceNumber:
			1 to 2 - CLIENT-1 and CLIENT-2
			-----------------------------
			Values:
			eg: 1234
			-----------------------------"
	::= { ommp021PerformanceEntry 54 }

	ommp021LineOtuFarEndSevereErrorSeconds OBJECT-TYPE
		SYNTAX  DisplayString
		MAX-ACCESS  read-only
		STATUS  current
		DESCRIPTION
			"For port configured with OTU4/OTUC2 traffic,
			OTU Far End Severe Error Seconds increases on defects
			like BDI are detected and when BEI errors are greater
			than or equal to 15% Errored Blocks in incoming OTU 
			signal.
			-----------------------------
			ommp021 InterfaceNumber:
			1 to 2 - CLIENT-1 and CLIENT-2
			-----------------------------
			Values:
			eg: 1234
			-----------------------------"
	::= { ommp021PerformanceEntry 55 }

	ommp021LineOtuFarEndUnavailableSeconds OBJECT-TYPE
		SYNTAX  DisplayString
		MAX-ACCESS  read-only
		STATUS  current
		DESCRIPTION
			"For port configured with OTU4/OTUC2 traffic,
			OTU Far End Unavailable Seconds increases, 
			after 9 consecutive OTU Far End Severe Error
			seconds are detected
			-----------------------------
			ommp021 InterfaceNumber:
			1 to 2 - CLIENT-1 and CLIENT-2
			-----------------------------
			Values:
			eg: 1234
			-----------------------------"
	::= { ommp021PerformanceEntry 56 }

	ommp021LineOtuFarEndErrorSeconds OBJECT-TYPE
		SYNTAX  DisplayString
		MAX-ACCESS  read-only
		STATUS  current
		DESCRIPTION
			"For port configured with OTU4/OTUC2 traffic,
			OTU Far End Error Seconds increases on
			detection of defects like BDI in incoming
			OTU signal.
			-----------------------------
			ommp021 InterfaceNumber:
			1 to 2 - CLIENT-1 and CLIENT-2
			-----------------------------
			Values:
			eg: 1234
			-----------------------------"
	::= { ommp021PerformanceEntry 57 }

	ommp021LineOduBitInterleavedParityErrors OBJECT-TYPE
		SYNTAX  DisplayString
		MAX-ACCESS  read-only
		STATUS  current
		DESCRIPTION
			"For port configured with OTU4/OTUC2 traffic,
			ODU-BIP Counter counts the Parity errors evaluated by
			PM field of an OTU4 frame
			-----------------------------
			ommp021 InterfaceNumber:
			1 to 2 - CLIENT-1 and CLIENT-2
			-----------------------------
			Values:
			eg: 1234
			-----------------------------"
	::= { ommp021PerformanceEntry 58 }

	ommp021LineOduBackwardErrorIndicationErrorCount OBJECT-TYPE
		SYNTAX  DisplayString
		MAX-ACCESS  read-only
		STATUS  current
		DESCRIPTION
			"For port configured with OTU4/OTUC2 traffic,
			this signal is used to convey in the upstream direction 
			the count of interleaved bit blocks that have 
			been detected in error using the BIP-8 code.
			-----------------------------
			ommp021 InterfaceNumber:
			1 to 2 - CLIENT-1 and CLIENT-2
			-----------------------------
			Values:
			eg: 1234
			-----------------------------"
	::= { ommp021PerformanceEntry 59 }

	ommp021LineOduErrorFreeSeconds OBJECT-TYPE
		SYNTAX  DisplayString
		MAX-ACCESS  read-only
		STATUS  current
		DESCRIPTION
			"For port configured with OTU4/OTUC2 traffic,
			ODU Error Free Seconds increases,
			when no BIP errors or defects are detected at the
			path monitoring level
			-----------------------------
			ommp021 InterfaceNumber:
			1 to 2 - CLIENT-1 and CLIENT-2
			-----------------------------
			Values:
			eg: 1234
			-----------------------------"
	::= { ommp021PerformanceEntry 60 }

	ommp021LineOduErrorSeconds OBJECT-TYPE
		SYNTAX  DisplayString
		MAX-ACCESS  read-only
		STATUS  current
		DESCRIPTION
			"For port configured with OTU4/OTUC2 traffic,
			ODU Error Seconds increases on defects detected at the
			path monitoring level
			-----------------------------
			ommp021 InterfaceNumber:
			1 to 2 - CLIENT-1 and CLIENT-2
			-----------------------------
			Values:
			eg: 1234
			-----------------------------"
	::= { ommp021PerformanceEntry 61 }

	ommp021LineOduBackgroundBlockErrors OBJECT-TYPE
		SYNTAX  DisplayString
		MAX-ACCESS  read-only
		STATUS  current
		DESCRIPTION
			"For port configured with OTU4/OTUC2 traffic,
			ODU Background Block Errors increases on defects 
			detected and when BIP errors are less than 15% 
			Errored Blocks in incoming OTU signal.
			-----------------------------
			ommp021 InterfaceNumber:
			1 to 2 - CLIENT-1 and CLIENT-2
			-----------------------------
			Values:
			eg: 1234
			-----------------------------"
	::= { ommp021PerformanceEntry 62 }

	ommp021LineOduSevereErrorSeconds OBJECT-TYPE
		SYNTAX  DisplayString
		MAX-ACCESS  read-only
		STATUS  current
		DESCRIPTION
			"For port configured with OTU4/OTUC2 traffic,
			ODU Severe Error Seconds increases on defects detected
			and when BIP errors are more than 15% Errored Blocks
			in incoming OTU signal.
			-----------------------------
			ommp021 InterfaceNumber:
			1 to 2 - CLIENT-1 and CLIENT-2
			-----------------------------
			Values:
			eg: 1234
			-----------------------------"
	::= { ommp021PerformanceEntry 63 }

	ommp021LineOduUnavailableSeconds OBJECT-TYPE
		SYNTAX  DisplayString
		MAX-ACCESS  read-only
		STATUS  current
		DESCRIPTION
			"For port configured with OTU4/OTUC2 traffic,
			ODU Unavailable Seconds increases, when 10 consecutive
			Severe ODU Error seconds are detected
			-----------------------------
			ommp021 InterfaceNumber:
			1 to 2 - CLIENT-1 and CLIENT-2
			-----------------------------
			Values:
			eg: 1234
			-----------------------------"
	::= { ommp021PerformanceEntry 64 }

	ommp021LineOduFarEndErrorFreeSeconds OBJECT-TYPE
		SYNTAX  DisplayString
		MAX-ACCESS  read-only
		STATUS  current
		DESCRIPTION
			"For port configured with OTU4/OTUC2 traffic,
			ODU Far end Error Free Seconds, increases when no
			far end errors or defects are detected
			-----------------------------
			ommp021 InterfaceNumber:
			1 to 2 - CLIENT-1 and CLIENT-2
			-----------------------------
			Values:
			eg: 1234
			-----------------------------"
	::= { ommp021PerformanceEntry 65 }

	ommp021LineOduFarEndErrorSeconds OBJECT-TYPE
		SYNTAX  DisplayString
		MAX-ACCESS  read-only
		STATUS  current
		DESCRIPTION
			"For port configured with OTU4/OTUC2 traffic,
			ODU Far End Error Seconds increases on detection of
			defects like BDI and BEI at path monitoring level
			-----------------------------
			ommp021 InterfaceNumber:
			1 to 2 - CLIENT-1 and CLIENT-2
			-----------------------------
			Values:
			eg: 1234
			-----------------------------"
	::= { ommp021PerformanceEntry 66 }

	ommp021LineOduFarEndBackgroundBlockErrors OBJECT-TYPE
		SYNTAX  DisplayString
		MAX-ACCESS  read-only
		STATUS  current
		DESCRIPTION
			"For port configured with OTU4/OTUC2 traffic,
			ODU Far End Background Block Errors increases when
			BEI errors are less than 15% Errored Blocks in
			incoming OTU signal.
			-----------------------------
			ommp021 InterfaceNumber:
			1 to 2 - CLIENT-1 and CLIENT-2
			-----------------------------
			Values:
			eg: 1234
			-----------------------------"
	::= { ommp021PerformanceEntry 67 }

	ommp021LineOduFarEndSevereErrorSeconds OBJECT-TYPE
		SYNTAX  DisplayString
		MAX-ACCESS  read-only
		STATUS  current
		DESCRIPTION
			"For port configured with OTU4/OTUC2 traffic,
			ODU Far End Severe Error Seconds increases on defects
			like BDI are detected and when BEI errors are more than
			15% Errored Blocks in incoming OTU signal.
			-----------------------------
			ommp021 InterfaceNumber:
			1 to 2 - CLIENT-1 and CLIENT-2
			-----------------------------
			Values:
			eg: 1234
			-----------------------------"
	::= { ommp021PerformanceEntry 68 }

	ommp021LineOduFarEndUnavailableSeconds OBJECT-TYPE
		SYNTAX  DisplayString
		MAX-ACCESS  read-only
		STATUS  current
		DESCRIPTION
			"For port configured with OTU4/OTUC2 traffic,
			ODU Far End Unavailable Seconds increases, when 10
			consecutive OTU Far End Error seconds are detected
			-----------------------------
			ommp021 InterfaceNumber:
			1 to 2 - CLIENT-1 and CLIENT-2
			-----------------------------
			Values:
			eg: 1234
			-----------------------------"
	::= { ommp021PerformanceEntry 69 }

	ommp021PerformanceTableRowStatus OBJECT-TYPE
              SYNTAX      RowStatus
              MAX-ACCESS  read-write
              STATUS      current
              DESCRIPTION
			"*****************************
			This is MIB realted property,
			NOT to be considered as a card property
			*****************************"
              ::= { ommp021PerformanceEntry 70 }
              
--*****************************************************************************

--*****************************************************************************

	snmpCurrentNotificationsGroup NOTIFICATION-GROUP
		NOTIFICATIONS { 
					ommp021Cfp2InputPowerFailureAlarmTrap,
					ommp021Cfp2OutputPowerFailureAlarmTrap,
					ommp021Cfp2HighTemperatureAlarmTrap,
					ommp021Cfp2LowTemperatureAlarmTrap,
					ommp021Cfp2InputHighPowerAlarmTrap,
					ommp021Cfp2InputLowPowerAlarmTrap,
					ommp021Cfp2OutputHighPowerAlarmTrap,
					ommp021Cfp2OutputLowPowerAlarmTrap,
					ommp021Cfp2HighSupplyVoltageAlarmTrap,
					ommp021Cfp2LowSupplyVoltageAlarmTrap,
					ommp021Cfp2PresenceAbsenceNotificationTrap,
					ommp021Qsfp28InputPowerFailureAlarmTrap,
					ommp021Qsfp28OutputPowerFailureAlarmTrap,
					ommp021Qsfp28HighTemperatureAlarmTrap,
					ommp021Qsfp28LowTemperatureAlarmTrap,
					ommp021Qsfp28HighBiasCurrentAlarmTrap,
					ommp021Qsfp28LowBiasCurrentAlarmTrap,
					ommp021Qsfp28InputHighPowerAlarmTrap,
					ommp021Qsfp28InputLowPowerAlarmTrap,
					ommp021Qsfp28OutputHighPowerAlarmTrap,
					ommp021Qsfp28OutputLowPowerAlarmTrap,
					ommp021Qsfp28HighSupplyVoltageAlarmTrap,
					ommp021Qsfp28LowSupplyVoltageAlarmTrap,
					ommp021Qsfp28PresenceAbsenceNotificationTrap,
					ommp021OtuLossOfSignalAlarmTrap,
					ommp021OtuLossOfFrameAlarmTrap,
					ommp021OtuOutOfFrameAlarmTrap,
					ommp021OtuLossOfMultiFrameAlarmTrap,
					ommp021OtuOutOfMultiFrameAlarmTrap,
					ommp021OtuSignalFailAlarmTrap,
					ommp021OtuSignalDegradeAlarmTrap,
					ommp021OtuAlarmIndicationSignalAlarmTrap,
					ommp021OtuIncomingAlignmentErrorAlarmTrap,
					ommp021OtuTrailTraceIdentifierMismatchAlarmTrap,
					ommp021OtuBackwardIncomingAlignmentErrorAlarmTrap,
					ommp021OtuBackwardDefectIndicationAlarmTrap,
					ommp021OduSignalFailAlarmTrap,
					ommp021OduSignalDegradeAlarmTrap,
					ommp021OduAlarmIndicationSignalAlarmTrap,
					ommp021OduTrailTraceIdentifierMismatchAlarmTrap,
					ommp021OduLockedDefectAlarmTrap,
					ommp021OduOpenConnectionIndicationAlarmTrap,
					ommp021OduBackwardDefectIndicationAlarmTrap,
					ommp021OpuPayloadMismatchAlarmTrap,
					ommp021EthernetLossOfSignalAlarmTrap,
					ommp021EthernetIngressRemoteFaultAlarmTrap,
					ommp021EthernetEgressRemoteFaultAlarmTrap,
					ommp021EthernetEgressHighBerAlarmTrap,
					ommp021EthernetEgressLocalFaultAlarmTrap,
					ommp021LineOtuLossOfSignalAlarmTrap,
					ommp021LineOtuLossOfFrameAlarmTrap,
					ommp021LineOtuOutOfFrameAlarmTrap,
					ommp021LineOtuLossOfMultiFrameAlarmTrap,
					ommp021LineOtuOutOfMultiFrameAlarmTrap,
					ommp021LineOtuSignalDegradeAlarmTrap,
					ommp021LineOtuAlarmIndicationSignalAlarmTrap,
					ommp021LineOtuIncomingAlignmentErrorAlarmTrap,
					ommp021LineOtuTrailTraceIdentifierMismatchAlarmTrap,
					ommp021LineOtuBackwardIncomingAlignmentErrorAlarmTrap,
					ommp021LineOtuBackwardDefectIndicationAlarmTrap,
					ommp021LineOduSignalDegradeAlarmTrap,
					ommp021LineOduAlarmIndicationSignalAlarmTrap,
					ommp021LineOduTrailTraceIdentifierMismatchAlarmTrap,
					ommp021LineOduLockedDefectAlarmTrap,
					ommp021LineOduOpenConnectionIndicationAlarmTrap,
					ommp021LineOduBackwardDefectIndicationAlarmTrap,					
					ommp021LineOpuPayloadMismatchAlarmTrap		
				}
  	STATUS current
	DESCRIPTION
  	   	"The UTL OMMP021 current notifications group"
  	::= { ommp021 6 }

            snmpcurrentGroup OBJECT-GROUP
    OBJECTS 	{ 
			ommp021InterfaceNumber,	
    			ommp021EepromCardId,
			ommp021EepromCardName,
			ommp021EepromCardSerialNumber,
			ommp021EepromHardwareExternalReleaseVersion,
			ommp021EepromHardwareInternalReleaseVersion,
			ommp021SoftwareExternalReleaseVersion,
			ommp021SoftwareInternalReleaseVersion,
			ommp021CardGeneralDetailsTableRowStatus,
			ommp021CardSoftwareUpgrade,
			ommp021CardSoftReset,
			ommp021CardFactoryReset,
			ommp021SyncSystemTimeWithNtpServer,
			ommp021SyncRtcWithNtpServer,
			ommp021SyncRtcWithSystemTime,
			ommp021UpdateGivenTimeIntoSystem,
			ommp021UpdateGivenTimeIntoRtc,
			ommp021SystemTimeAndRtcTime,
			ommp021TrafficConfiguration,
			ommp021LoopbackState,
			ommp021ClearSignalPerformance,
			ommp021AlsState,
			ommp021AlsPulseRepetitionTime,
			ommp021OtuFecConfiguration,
			ommp021OtuSignalFailThreshold,
			ommp021OtuSignalDegradeThreshold,
			ommp021OtuSapiTransmitTraceMessage,
			ommp021OtuDapiTransmitTraceMessage,
			ommp021OtuOperatorSpecificTransmitTraceMessage,
			ommp021OtuSapiExpectedTraceMessage,
			ommp021OtuDapiExpectedTraceMessage,
			ommp021OtuOperatorSpecificExpectedTraceMessage,
			ommp021OduSignalFailThreshold,
			ommp021OduSignalDegradeThreshold,
			ommp021OduSapiTransmitTraceMessage,
			ommp021OduDapiTransmitTraceMessage,
			ommp021OduOperatorSpecificTransmitTraceMessage,
			ommp021OduSapiExpectedTraceMessage,
			ommp021OduDapiExpectedTraceMessage,
			ommp021OduOperatorSpecificExpectedTraceMessage,
			ommp021TunableCfp2LaserWavelength,
			ommp021Cfp2LaserState,
			ommp021Qsfp28LaserState,
			ommp021TunableCfp2WavelengthGridSpacing,			
			ommp021Cfp2InputPowerFailureAlarmSeverity,
			ommp021Cfp2OutputPowerFailureAlarmSeverity,
			ommp021Cfp2HighTemperatureAlarmSeverity,
			ommp021Cfp2LowTemperatureAlarmSeverity,
			ommp021Cfp2InputHighPowerAlarmSeverity,
			ommp021Cfp2InputLowPowerAlarmSeverity,
			ommp021Cfp2OutputHighPowerAlarmSeverity,
			ommp021Cfp2OutputLowPowerAlarmSeverity,
			ommp021Cfp2HighSupplyVoltageAlarmSeverity,
			ommp021Cfp2LowSupplyVoltageAlarmSeverity,
			ommp021Cfp2PresenceAbsenceNotificationSeverity,
			ommp021Qsfp28InputPowerFailureAlarmSeverity,
			ommp021Qsfp28OutputPowerFailureAlarmSeverity,
			ommp021Qsfp28HighTemperatureAlarmSeverity,
			ommp021Qsfp28LowTemperatureAlarmSeverity,
			ommp021Qsfp28HighBiasCurrentAlarmSeverity,
			ommp021Qsfp28LowBiasCurrentAlarmSeverity,
			ommp021Qsfp28InputHighPowerAlarmSeverity,
			ommp021Qsfp28InputLowPowerAlarmSeverity,
			ommp021Qsfp28OutputHighPowerAlarmSeverity,
			ommp021Qsfp28OutputLowPowerAlarmSeverity,
			ommp021Qsfp28HighSupplyVoltageAlarmSeverity,
			ommp021Qsfp28LowSupplyVoltageAlarmSeverity,
			ommp021Qsfp28PresenceAbsenceNotificationSeverity,
			ommp021OtuLossOfSignalAlarmSeverity,
			ommp021OtuLossOfFrameAlarmSeverity,
			ommp021OtuOutOfFrameAlarmSeverity,
			ommp021OtuOutOfMultiFrameAlarmSeverity,
			ommp021OtuSignalDegradeAlarmSeverity,
			ommp021OtuAlarmIndicationSignalAlarmSeverity,
			ommp021OtuIncomingAlignmentErrorAlarmSeverity,
			ommp021OtuTrailTraceIdentifierMismatchAlarmSeverity,
			ommp021OtuBackwardIncomingAlignmentErrorAlarmSeverity,
			ommp021OtuBackwardDefectIndicationAlarmSeverity,
			ommp021OduSignalDegradeAlarmSeverity,
			ommp021OduAlarmIndicationSignalAlarmSeverity,
			ommp021OduTrailTraceIdentifierMismatchAlarmSeverity,
			ommp021OduLockedDefectAlarmSeverity,
			ommp021OduOpenConnectionIndicationAlarmSeverity,
			ommp021OduBackwardDefectIndicationAlarmSeverity,
			ommp021OpuPayloadMismatchAlarmSeverity,
			ommp021EthernetLossOfSignalAlarmSeverity,
			ommp021EthernetIngressRemoteFaultAlarmSeverity,
			ommp021EthernetEgressRemoteFaultAlarmSeverity,
			ommp021EthernetEgressHighBerAlarmSeverity,
			ommp021EthernetEgressLocalFaultAlarmSeverity,
			ommp021LineOtuSignalFailThreshold,
			ommp021LineOtuSignalDegradeThreshold,
			ommp021LineOtuSapiTransmitTraceMessage,
			ommp021LineOtuDapiTransmitTraceMessage,
			ommp021LineOtuOperatorSpecificTransmitTraceMessage,
			ommp021LineOtuSapiExpectedTraceMessage,
			ommp021LineOtuDapiExpectedTraceMessage,
			ommp021LineOtuOperatorSpecificExpectedTraceMessage,
			ommp021LineOduSignalFailThreshold,
			ommp021LineOduSignalDegradeThreshold,
			ommp021LineOduSapiTransmitTraceMessage,
			ommp021LineOduDapiTransmitTraceMessage,
			ommp021LineOduOperatorSpecificTransmitTraceMessage,
			ommp021LineOduSapiExpectedTraceMessage,
			ommp021LineOduDapiExpectedTraceMessage,
			ommp021LineOduOperatorSpecificExpectedTraceMessage,
			ommp021LineOtuLossOfSignalAlarmSeverity,
			ommp021LineOtuLossOfFrameAlarmSeverity,
			ommp021LineOtuOutOfFrameAlarmSeverity,
			ommp021LineOtuOutOfMultiFrameAlarmSeverity,
			ommp021LineOtuSignalDegradeAlarmSeverity,
			ommp021LineOtuAlarmIndicationSignalAlarmSeverity,
			ommp021LineOtuIncomingAlignmentErrorAlarmSeverity,
			ommp021LineOtuTrailTraceIdentifierMismatchAlarmSeverity,
			ommp021LineOtuBackwardIncomingAlignmentErrorAlarmSeverity,
			ommp021LineOtuBackwardDefectIndicationAlarmSeverity,
			ommp021LineOduSignalDegradeAlarmSeverity,
			ommp021LineOduAlarmIndicationSignalAlarmSeverity,
			ommp021LineOduTrailTraceIdentifierMismatchAlarmSeverity,
			ommp021LineOduLockedDefectAlarmSeverity,
			ommp021LineOduOpenConnectionIndicationAlarmSeverity,
			ommp021LineOduBackwardDefectIndicationAlarmSeverity,		
			ommp021LineOpuPayloadMismatchAlarmSeverity,
			ommp021ConfigurationTableRowStatus,
			ommp021Cfp2InputPowerFailureAlarm,
			ommp021Cfp2OutputPowerFailureAlarm,
			ommp021Cfp2HighTemperatureAlarm,
			ommp021Cfp2LowTemperatureAlarm,
			ommp021Cfp2InputHighPowerAlarm,
			ommp021Cfp2InputLowPowerAlarm,
			ommp021Cfp2OutputHighPowerAlarm,
			ommp021Cfp2OutputLowPowerAlarm,
			ommp021Cfp2HighSupplyVoltageAlarm,
			ommp021Cfp2LowSupplyVoltageAlarm,
			ommp021Cfp2PresenceAbsenceNotification,
			ommp021Qsfp28InputPowerFailureAlarm,
			ommp021Qsfp28OutputPowerFailureAlarm,
			ommp021Qsfp28HighTemperatureAlarm,
			ommp021Qsfp28LowTemperatureAlarm,
			ommp021Qsfp28HighBiasCurrentAlarm,
			ommp021Qsfp28LowBiasCurrentAlarm,
			ommp021Qsfp28InputHighPowerAlarm,
			ommp021Qsfp28InputLowPowerAlarm,
			ommp021Qsfp28OutputHighPowerAlarm,
			ommp021Qsfp28OutputLowPowerAlarm,
			ommp021Qsfp28HighSupplyVoltageAlarm,
			ommp021Qsfp28LowSupplyVoltageAlarm,
			ommp021Qsfp28PresenceAbsenceNotification,
			ommp021OtuLossOfSignalAlarm,
			ommp021OtuLossOfFrameAlarm,
			ommp021OtuOutOfFrameAlarm,
			ommp021OtuLossOfMultiFrameAlarm,
			ommp021OtuOutOfMultiFrameAlarm,
			ommp021OtuSignalFailAlarm,
			ommp021OtuSignalDegradeAlarm,
			ommp021OtuAlarmIndicationSignalAlarm,
			ommp021OtuIncomingAlignmentErrorAlarm,
			ommp021OtuTrailTraceIdentifierMismatchAlarm,
			ommp021OtuBackwardIncomingAlignmentErrorAlarm,
			ommp021OtuBackwardDefectIndicationAlarm,
			ommp021OduSignalFailAlarm,
			ommp021OduSignalDegradeAlarm,
			ommp021OduAlarmIndicationSignalAlarm,
			ommp021OduTrailTraceIdentifierMismatchAlarm,
			ommp021OduLockedDefectAlarm,
			ommp021OduOpenConnectionIndicationAlarm,
			ommp021OduBackwardDefectIndicationAlarm,
			ommp021OpuPayloadMismatchAlarm,
			ommp021EthernetLossOfSignalAlarm,
			ommp021EthernetIngressRemoteFaultAlarm,
			ommp021EthernetEgressRemoteFaultAlarm,
			ommp021EthernetEgressHighBerAlarm,
			ommp021EthernetEgressLocalFaultAlarm,
			ommp021LineOtuLossOfSignalAlarm,
			ommp021LineOtuLossOfFrameAlarm,
			ommp021LineOtuOutOfFrameAlarm,
			ommp021LineOtuLossOfMultiFrameAlarm,
			ommp021LineOtuOutOfMultiFrameAlarm,
			ommp021LineOtuSignalDegradeAlarm,
			ommp021LineOtuAlarmIndicationSignalAlarm,
			ommp021LineOtuIncomingAlignmentErrorAlarm,
			ommp021LineOtuTrailTraceIdentifierMismatchAlarm,
			ommp021LineOtuBackwardIncomingAlignmentErrorAlarm,
			ommp021LineOtuBackwardDefectIndicationAlarm,
			ommp021LineOduSignalDegradeAlarm,
			ommp021LineOduAlarmIndicationSignalAlarm,
			ommp021LineOduTrailTraceIdentifierMismatchAlarm,
			ommp021LineOduLockedDefectAlarm,
			ommp021LineOduOpenConnectionIndicationAlarm,
			ommp021LineOduBackwardDefectIndicationAlarm,
			ommp021LineOpuPayloadMismatchAlarm,
			ommp021AlarmQueryTableRowStatus,
			ommp021Cfp2InputPower,
			ommp021Cfp2OutputPower,
			ommp021Cfp2SupplyVoltage,
			ommp021Cfp2Temperature,
			ommp021Qsfp28InputPower,
			ommp021Qsfp28OutputPower,
			ommp021Qsfp28BiasCurrent,
			ommp021Qsfp28SupplyVoltage,
			ommp021Qsfp28Temperature,
			ommp021OtnFecUncorrectedWords,
			ommp021OtnFecCorrectedBits,
			ommp021OtuBitInterleavedParityErrors,
			ommp021OtuBackwardErrorIndicationErrorCount,
			ommp021OtuErrorFreeSeconds,
			ommp021OtuErrorSeconds,
			ommp021OtuBackgroundBlockErrors,
			ommp021OtuSevereErrorSeconds,
			ommp021OtuUnavailableSeconds,
			ommp021OtuFarEndErrorFreeSeconds,
			ommp021OtuFarEndBackgroundBlockErrors,
			ommp021OtuFarEndSevereErrorSeconds,
			ommp021OtuFarEndUnavailableSeconds,
			ommp021OtuFarEndErrorSeconds,
			ommp021OduBitInterleavedParityErrors,
			ommp021OduBackwardErrorIndicationErrorCount,
			ommp021OduErrorFreeSeconds,
			ommp021OduErrorSeconds,
			ommp021OduBackgroundBlockErrors,
			ommp021OduSevereErrorSeconds,
			ommp021OduUnavailableSeconds,
			ommp021OduFarEndErrorFreeSeconds,
			ommp021OduFarEndErrorSeconds,
			ommp021OduFarEndBackgroundBlockErrors,
			ommp021OduFarEndSevereErrorSeconds,
			ommp021OduFarEndUnavailableSeconds,
			ommp021EthernetMacTerminatedFramesTransmitted,
			ommp021EthernetMacTerminatedFramesReceived,
			ommp021EthernetMacTerminatedUnicastFramesReceived,
			ommp021EthernetMacTerminatedMulticastFramesReceived,
			ommp021EthernetMacTerminatedBroadcastFramesReceived,
			ommp021EthernetMacTerminatedUnderSizeFramesReceived,
			ommp021EthernetMacTerminatedOverSizeFramesReceived,
			ommp021EthernetMacTerminatedFrameCheckSequenceErrorsReceived,
			ommp021LineOtnFecUncorrectedWords,
			ommp021LineOtnFecCorrectedBits,
			ommp021LineOtuBitInterleavedParityErrors,
			ommp021LineOtuBackwardErrorIndicationErrorCount,
			ommp021LineOtuErrorFreeSeconds,
			ommp021LineOtuErrorSeconds,
			ommp021LineOtuBackgroundBlockErrors,
			ommp021LineOtuSevereErrorSeconds,
			ommp021LineOtuUnavailableSeconds,
			ommp021LineOtuFarEndErrorFreeSeconds,
			ommp021LineOtuFarEndBackgroundBlockErrors,
			ommp021LineOtuFarEndSevereErrorSeconds,
			ommp021LineOtuFarEndUnavailableSeconds,
			ommp021LineOtuFarEndErrorSeconds,
			ommp021LineOduBitInterleavedParityErrors,
			ommp021LineOduBackwardErrorIndicationErrorCount,
			ommp021LineOduErrorFreeSeconds,
			ommp021LineOduErrorSeconds,
			ommp021LineOduBackgroundBlockErrors,
			ommp021LineOduSevereErrorSeconds,
			ommp021LineOduUnavailableSeconds,
			ommp021LineOduFarEndErrorFreeSeconds,
			ommp021LineOduFarEndErrorSeconds,
			ommp021LineOduFarEndBackgroundBlockErrors,
			ommp021LineOduFarEndSevereErrorSeconds,
			ommp021LineOduFarEndUnavailableSeconds,
			ommp021PerformanceTableRowStatus
		}
    STATUS  current
    DESCRIPTION
            "A collection of objects from RFC 10213 made current by this MIB module."
    ::= { utlrnd 2 }

	
END

--*****************************************************************************
--			MIB FILE FOR THE OMMP81-PLUS CARD
--*****************************************************************************

OMMP81-PLUS-MIB DEFINITIONS ::= BEGIN
 
          IMPORTS
        	
		RowStatus      			FROM STANDARD-MIB
			
		DisplayString  			FROM RFC1213-MIB       
    	
    		OBJECT-IDENTITY,
    		NOTIFICATION-TYPE,
    		MODULE-IDENTITY,
    		Integer32,
    		Unsigned32,
    		IpAddress,
    		TimeTicks			FROM SNMPv2-SMI
	 
	 	OBJECT-TYPE    			FROM RFC-1212
	 		
		MODULE-COMPLIANCE,
		OBJECT-GROUP,
		NOTIFICATION-GROUP		FROM SNMPv2-CONF
	
		node,
		rack,
		subRack,
		slot				FROM SCC-MIB
    
		enterprises			FROM RFC1155-SMI
	;

 

	utl   MODULE-IDENTITY
            LAST-UPDATED    	"1807130630Z"
            ORGANIZATION    	"United Telecoms Limited, Bangalore-560048."
            CONTACT-INFO    	"Website: http://www.utlindia.com."                                           
            DESCRIPTION     	"MIB module for UTL 40/80 channel DWDM."
            REVISION 	    	"1807130630Z"
            DESCRIPTION    	"MIB module for OMMP81-PLUS Card."
            ::= { enterprises 18036 }

	utlrnd  OBJECT-IDENTITY
            STATUS  current
            DESCRIPTION "UTL Research and Development."
            ::= { utl 1 }

	dwdm 	OBJECT IDENTIFIER				::=	{ utlrnd 1 }
	indus 	OBJECT IDENTIFIER				::=	{ dwdm 1 }
	ommp81Plus 	OBJECT IDENTIFIER 			::=	{ indus 86 }

	ommp81PlusCardGeneralDetails OBJECT IDENTIFIER		::=	{ ommp81Plus 1 }
	ommp81PlusConfiguration OBJECT IDENTIFIER 		::=	{ ommp81Plus 2 }
	ommp81PlusAlarm OBJECT IDENTIFIER 			::=	{ ommp81Plus 3 }
	ommp81PlusPerformance OBJECT IDENTIFIER 		::=	{ ommp81Plus 4 }
	ommp81PlusDiagnostics OBJECT IDENTIFIER 		::=	{ ommp81Plus 5 }

	ommp81PlusAlarmQuery OBJECT IDENTIFIER			::=	{ ommp81PlusAlarm 1 }
	ommp81PlusAlarmNotification OBJECT IDENTIFIER		::=	{ ommp81PlusAlarm 2 }

--*****************************************************************************
--				CARD GENERAL DETAILS
--*****************************************************************************

	ommp81PlusCardGeneralDetailsTable OBJECT-TYPE
		SYNTAX  SEQUENCE OF Ommp81PlusCardGeneralDetailsEntry 
		MAX-ACCESS  not-accessible
		STATUS  current
		DESCRIPTION
                     "Contains card general details' queries for the OMMP81-PLUS card"
		::= { ommp81PlusCardGeneralDetails 1 }

	ommp81PlusCardGeneralDetailsEntry  OBJECT-TYPE
		SYNTAX  Ommp81PlusCardGeneralDetailsEntry 
		MAX-ACCESS  not-accessible
		STATUS  current
		DESCRIPTION 
              	""
		INDEX   { node, rack, subRack, slot, ommp81PlusInterfaceNumber }
		::= { ommp81PlusCardGeneralDetailsTable 1 }

	Ommp81PlusCardGeneralDetailsEntry  ::= 
		SEQUENCE {
				ommp81PlusInterfaceNumber					INTEGER,
				ommp81PlusEepromCardId					        INTEGER,
				ommp81PlusEepromCardName					DisplayString,
				ommp81PlusEepromPartCode					DisplayString,
				ommp81PlusEepromCardSerialNumber				DisplayString,
				ommp81PlusEepromHardwareExternalReleaseVersion		        DisplayString,
				ommp81PlusSoftwareExternalReleaseVersion		        DisplayString,
				ommp81PlusEepromHardwareInternalReleaseVersion		        DisplayString,
				ommp81PlusSoftwareInternalReleaseVersion		        DisplayString,
				ommp81PlusEepromCardUidNumber			                DisplayString,
				ommp81PlusEepromCardEui48Number				        DisplayString,
				ommp81PlusEepromCardEui64Number				        DisplayString,
				ommp81PlusCardRootFileSystemVersion				DisplayString,
				ommp81PlusCardInstallationDate				        DisplayString,
				ommp81PlusCardCommissionDate				        DisplayString,
				ommp81PlusCardRunningTime					DisplayString,
				ommp81PlusCardRestartCount					INTEGER,
				ommp81PlusXfpReadyForOperation				        INTEGER,
				ommp81PlusXfpI2cCommunicationStatus				INTEGER,
				ommp81PlusXfpEepromPage					        INTEGER,
				ommp81PlusCheckCodeOfXfpEepromPage				INTEGER,
				ommp81PlusExtendedCheckCodeOfXfpEepromPage			INTEGER,
				ommp81PlusXfpVendorName					        DisplayString,
				ommp81PlusXfpVendorIeeeId					DisplayString,
				ommp81PlusXfpPartNumber					        DisplayString,
				ommp81PlusXfpSerialNumber					DisplayString,
				ommp81PlusXfpRevisionNumber					DisplayString,
				ommp81PlusXfpManufacturingDate				        DisplayString,
				ommp81PlusFixedXfpLaserWavelength				DisplayString,
				ommp81PlusXfpLaserWavelengthTolerance				DisplayString,
				ommp81PlusXfpWavelengthTunabilitySupported			INTEGER,
				ommp81PlusTunableXfpLaserWavelengthError			DisplayString,
				ommp81PlusTunableXfpLaserFrequencyError			        DisplayString,
				ommp81PlusTunableXfpLaserFirstFrequency			        DisplayString,
				ommp81PlusTunableXfpLaserLastFrequency			        DisplayString,
				ommp81PlusTunableXfpWavelengthGridSpacing			DisplayString,
				ommp81PlusXfpConnectorType					DisplayString,
				ommp81PlusXfpLinkLength					        DisplayString,
				ommp81PlusXfpCdrRateSupported				        INTEGER,
				ommp81PlusXfpSignalEncodingTypeSupported			INTEGER,
				ommp81PlusXfpTransceiverCodesSupported			        DisplayString,
				ommp81PlusXfpMaximumBitrateSupported			        DisplayString,
				ommp81PlusXfpMinimumBitrateSupported			        DisplayString,
				ommp81PlusXfpMaximumCaseTemperatureSupported		        INTEGER,
				ommp81PlusXfpMaximumPowerDissipationSupported			INTEGER,
				ommp81PlusXfpMaximumPowerDissipationSupportedAtPowerDownMode	INTEGER,
				ommp81PlusXfpMaximumCurrentLimitSupportedAtPlus5vSupply		INTEGER,
				ommp81PlusXfpMaximumCurrentLimitSupportedAtPlus3Point3vSupply	INTEGER,
				ommp81PlusXfpMaximumCurrentLimitSupportedAtPlus1Point8vSupply	INTEGER,
				ommp81PlusXfpMaximumCurrentLimitSupportedAtMinus5Point2vSupply	INTEGER,
				ommp81PlusXfpLineLoopbackSupported				INTEGER,
				ommp81PlusXfpXfiLoopbackSupported				INTEGER,
				ommp81PlusXfpOptionalVpsSupported				INTEGER,
				ommp81PlusXfpLaserDisableThroughI2cSupported			INTEGER,
				ommp81PlusXfpPowerDownThroughI2cSupported			INTEGER,
				ommp81PlusXfpVpsLvRegulatorModeSupported			INTEGER,
				ommp81PlusXfpVpsBypassedRegulatorModeSupported			INTEGER,
				ommp81PlusXfpActiveFecControlSupported				INTEGER,
				ommp81PlusXfpOptionalCmuModeSupported				INTEGER,
				ommp81PlusXfpFecBerSupported					INTEGER,
				ommp81PlusXfpReceivePowerMeasurementIsInOmaOrAverage		INTEGER,
				ommp81PlusXfpActiveWavelengthControlSupported			INTEGER,
				ommp81PlusXfpTransmitterIsCooledOrUncooled			INTEGER,
				ommp81PlusXfpReceiverTypeIsPinOrApd                             INTEGER,
				ommp81PlusSfpEepromPage						INTEGER,
				ommp81PlusCheckCodeOfSfpEepromPage				INTEGER,
				ommp81PlusExtendedCheckCodeOfSfpEepromPage			INTEGER,
				ommp81PlusSfpVendorName						DisplayString,
				ommp81PlusSfpVendorIeeeId					DisplayString,
				ommp81PlusSfpPartNumber						DisplayString,
				ommp81PlusSfpSerialNumber					DisplayString,
				ommp81PlusSfpRevisionNumber					DisplayString,
				ommp81PlusSfpManufacturingDate					DisplayString,
				ommp81PlusFixedSfpLaserWavelength				DisplayString,
				ommp81PlusSfpConnectorType					DisplayString,
				ommp81PlusSfpLinkLength						DisplayString,
				ommp81PlusSfpSignalEncodingTypeSupported			INTEGER,
				ommp81PlusSfpTransceiverCodesSupported				INTEGER,
				ommp81PlusSfpMaximumBitrateSupported				DisplayString,
				ommp81PlusSfpNominalBitrateSupported				DisplayString,
				ommp81PlusSfpMinimumBitrateSupported				DisplayString,
				ommp81PlusCardGeneralDetailsTableRowStatus			RowStatus
			 }
	

	ommp81PlusInterfaceNumber OBJECT-TYPE
		SYNTAX  INTEGER
		MAX-ACCESS  not-accessible
		STATUS  current
		DESCRIPTION
			"Interface number represents the port number.
			InterfaceNumber to port mapping is as follows:
			1 - CLIENT-1,
			2 - CLIENT-2,
			3 - CLIENT-3,
			4 - CLIENT-4,
			5 - CLIENT-5,
			6 - CLIENT-6,
			7 - CLIENT-7,
			8 - CLIENT-8,
			9 - LINE-1
			-----------------------------
			Values of the demultiplexing properties can be accessed
			with respect to slice number.  In such cases the
			InterfaceNumber will represent the slice number.
			1 - Slice-1
			2 - Slice-2
			3 - Slice-3
			4 - Slice-4
			-----------------------------
			For properties which do not apply on any interface,
			the interface number must be passed as 0
			-----------------------------"
		::= { ommp81PlusCardGeneralDetailsEntry 1 }
	
	ommp81PlusEepromCardId OBJECT-TYPE		 
		SYNTAX  INTEGER
		MAX-ACCESS  read-only
		STATUS current
		DESCRIPTION
			"Tells the card ID of the OMMP81-PLUS card, present in the EEPROM
			-----------------------------
			ommp81PlusInterfaceNumber: 0
			-----------------------------"
		::= { ommp81PlusCardGeneralDetailsEntry 2 }

	ommp81PlusEepromCardName OBJECT-TYPE		 
		SYNTAX  DisplayString
		MAX-ACCESS  read-only
		STATUS current
		DESCRIPTION
			"Tells the card name of the OMMP81-PLUS card, present in the EEPROM
			-----------------------------
			ommp81PlusInterfaceNumber: 0
			-----------------------------"
		::= { ommp81PlusCardGeneralDetailsEntry 3 }

	ommp81PlusEepromPartCode OBJECT-TYPE		 
		SYNTAX  DisplayString
		MAX-ACCESS  read-only
		STATUS current
		DESCRIPTION
			"Tells the part code of the OMMP81-PLUS card, present in the EEPROM
			-----------------------------
			ommp81PlusInterfaceNumber: 0
			-----------------------------"
		::= { ommp81PlusCardGeneralDetailsEntry 4 }

	ommp81PlusEepromCardSerialNumber OBJECT-TYPE		 
		SYNTAX  DisplayString
		MAX-ACCESS  read-write
		STATUS current
		DESCRIPTION
			"This property get / set the information about 
			OMMP81-PLUS Card's Serial Number.
			-----------------------------
			ommp81PlusInterfaceNumber: 0
			-----------------------------
			Values:
			eg: 123456
			-----------------------------"
		::= { ommp81PlusCardGeneralDetailsEntry 5 }

	ommp81PlusEepromHardwareExternalReleaseVersion OBJECT-TYPE		 
		SYNTAX  DisplayString
		MAX-ACCESS  read-only
		STATUS current
		DESCRIPTION
			"Gets the Card's Hardware External Release Version. 
			This detail will be displayed to the customer.
			This version will increment only if there are significant
			architectural changes in the product
			-----------------------------
			ommp81PlusInterfaceNumber: 0
			-----------------------------
			Value:
			eg: 0.1
			-----------------------------"
		::= { ommp81PlusCardGeneralDetailsEntry 6 }

	ommp81PlusSoftwareExternalReleaseVersion OBJECT-TYPE		 
		SYNTAX  DisplayString
		MAX-ACCESS  read-only
		STATUS current
		DESCRIPTION
			"Gets the Card's Software External Release Version. 
			This detail will be displayed to the customer.
			This version will increment only if there are
			significant architectural changes in the product
			-----------------------------
			ommp81PlusInterfaceNumber: 0
			-----------------------------
			Value:
			eg: 0.1
			-----------------------------"
		::= { ommp81PlusCardGeneralDetailsEntry 7 }

	ommp81PlusEepromHardwareInternalReleaseVersion OBJECT-TYPE		 
		SYNTAX  DisplayString
		MAX-ACCESS  read-only
		STATUS current
		DESCRIPTION
			"Gets the Card's Hardware Internal Release Version.
			This detail is used for development purposes only.
			It differs from the external hardware version.
			-----------------------------
			ommp81PlusInterfaceNumber: 0
			-----------------------------
			Value:
			eg: 4.1
			-----------------------------"
		::= { ommp81PlusCardGeneralDetailsEntry 8 }

	ommp81PlusSoftwareInternalReleaseVersion OBJECT-TYPE		 
		SYNTAX  DisplayString
		MAX-ACCESS  read-only
		STATUS current
		DESCRIPTION
			"Gets the Card's Software Internal Release Version.
			This detail is used for development purposes only.
			It differs from the external software version.
		      	-----------------------------
			ommp81PlusInterfaceNumber: 0
			-----------------------------
			Value:
			eg: 5.1
			-----------------------------"
		::= { ommp81PlusCardGeneralDetailsEntry 9 }

	ommp81PlusEepromCardUidNumber OBJECT-TYPE		 
		SYNTAX  DisplayString
		MAX-ACCESS  read-only
		STATUS current
		DESCRIPTION
			"Tells the Card Unique IDentifier. It is a 4 byte
			address used to uniquely identify a card.
			----------------------------
			ommp81PlusInterfaceNumber: 0
			------------------------------
			Value:
		      	eg: 12345678
			-----------------------------"
		::= { ommp81PlusCardGeneralDetailsEntry 10 }

	ommp81PlusEepromCardEui48Number OBJECT-TYPE		 
		SYNTAX  DisplayString
		MAX-ACCESS  read-only
		STATUS current
		DESCRIPTION
			"Tells the Card EUI-48 Number. It is a 6 byte address
			used to uniquely identify a card.
			-----------------------------
			ommp81PlusInterfaceNumber: 0
			-----------------------------
			Value:
		      	eg: 0004A3123456
			-----------------------------"
		::= { ommp81PlusCardGeneralDetailsEntry 11 }

	ommp81PlusEepromCardEui64Number OBJECT-TYPE		 
		SYNTAX  DisplayString
		MAX-ACCESS  read-only
		STATUS current
		DESCRIPTION
			"Tells the Card EUI-64 Number. It is a 8 byte address
			used to uniquely identify a card.
			-----------------------------
			ommp81PlusInterfaceNumber: 0
			-----------------------------
			Value:
		      	eg: 0004A31234567890
			-----------------------------"
		::= { ommp81PlusCardGeneralDetailsEntry 12 }
		
        ommp81PlusCardRootFileSystemVersion OBJECT-TYPE		 
		SYNTAX  DisplayString
		MAX-ACCESS  read-only
		STATUS current
		DESCRIPTION
			"Tells the Card's Root File System Version
			-----------------------------
			ommp81PlusInterfaceNumber: 0
			-----------------------------
			Value:
		      	eg: 8
			-----------------------------"
		::= { ommp81PlusCardGeneralDetailsEntry 13 }

	ommp81PlusCardInstallationDate OBJECT-TYPE		 
		SYNTAX  DisplayString
		MAX-ACCESS  read-write
		STATUS current
		DESCRIPTION
			"Gets the card's installation date in
			dd/mm/yyyy format
			-----------------------------
			ommp81PlusInterfaceNumber: 0
			-----------------------------
			Value:
		      	eg: 12/03/2016
			-----------------------------"
		::= { ommp81PlusCardGeneralDetailsEntry 21 }

	ommp81PlusCardCommissionDate OBJECT-TYPE		 
		SYNTAX  DisplayString
		MAX-ACCESS  read-write
		STATUS current
		DESCRIPTION
			"Gets the card's commission date in
			dd/mm/yyyy format
			-----------------------------
			ommp81PlusInterfaceNumber: 0
			-----------------------------
			Value:
		      	eg: 20/03/2016
			-----------------------------"
		::= { ommp81PlusCardGeneralDetailsEntry 22 }

	ommp81PlusCardRunningTime OBJECT-TYPE		 
		SYNTAX  DisplayString
		MAX-ACCESS  read-only
		STATUS current
		DESCRIPTION
			"Get the duration of time for which the card is
			operational/running
			-----------------------------
			ommp81PlusInterfaceNumber: 0
			-----------------------------
			Values:
		      	eg: 4d:3h:2m:1s
			-----------------------------"
		::= { ommp81PlusCardGeneralDetailsEntry 23 }

	ommp81PlusCardRestartCount OBJECT-TYPE		 
		SYNTAX  INTEGER
		MAX-ACCESS  read-only
		STATUS current
		DESCRIPTION
			"Get the number of times the card has been soft reset.
			This value will get reset to 0 on factory reset.
			-----------------------------
			ommp81PlusInterfaceNumber: 0
			-----------------------------
			Values:
		      	eg: 10
			-----------------------------"
		::= { ommp81PlusCardGeneralDetailsEntry 24 }

	ommp81PlusXfpReadyForOperation OBJECT-TYPE		 
		SYNTAX  INTEGER
		MAX-ACCESS  read-only
		STATUS current
		DESCRIPTION
			"Module not ready indicates that the XFP
			has detected a condition that tells
			transmit or receive data is invalid.
			It shall consist of logical OR of the
			following signals:
			> Transmit Signal Conditioner Loss of Lock
			> Transmitter Laser Fault
			> Receiver Signal Conditioner Loss of Lock
			(Ref: INF-8077 2.4.1)
			-----------------------------
			ommp81PlusInterfaceNumber:
			9 - LINE-1
			-----------------------------
			Values:		
			1 - XFP is ready for operation 
			0 - XFP is not ready for operation
			-----------------------------"
		::= { ommp81PlusCardGeneralDetailsEntry 31 }

	ommp81PlusXfpI2cCommunicationStatus OBJECT-TYPE		 
		SYNTAX  INTEGER
		MAX-ACCESS  read-write
		STATUS current
		DESCRIPTION
			"Tells whether the XFP can be accessed
			on a single 2-wire interface bus or not.
			(Ref: INF-8077 2.4.2)
			-----------------------------
			ommp81PlusInterfaceNumber:
			9 - LINE-1
			-----------------------------
			Values:			
			1 - Enable I2C communication for XFP
				i.e. the XFP responds to 2-wire serial
				communication commands.
			0 - Disable I2C communication for XFP
				i.e. the XFP will not respond to or
				acknowledge any 2-wire interface communication
				from the host.
			-----------------------------"
		::= { ommp81PlusCardGeneralDetailsEntry 32 }

	ommp81PlusXfpEepromPage OBJECT-TYPE		 
		SYNTAX  INTEGER
		MAX-ACCESS  read-write
		STATUS current
		DESCRIPTION
			"This property sets/gets the XFP EEPROM page, 
			the value represents the XFP EEPROM page number.
			-----------------------------
			ommp81PlusInterfaceNumber:
			9 - LINE-1
			-----------------------------
			Values:			
			eg: 1(EEPROM Page number)
			-----------------------------"
		::= { ommp81PlusCardGeneralDetailsEntry 33 }

	ommp81PlusCheckCodeOfXfpEepromPage OBJECT-TYPE		 
		SYNTAX  INTEGER
		MAX-ACCESS  read-only
		STATUS current
		DESCRIPTION
			"This property provides the XFP
			check code(checksum) value for bytes 128 to 190
			present in XFP EEPROM Page number 1. 
			-----------------------------
			ommp81PlusInterfaceNumber:
			9 - LINE-1
			-----------------------------
			Values:			
			eg: 1(EEPROM Page number)
			-----------------------------"
		::= { ommp81PlusCardGeneralDetailsEntry 34 }

	ommp81PlusExtendedCheckCodeOfXfpEepromPage OBJECT-TYPE		 
		SYNTAX  INTEGER
		MAX-ACCESS  read-only
		STATUS current
		DESCRIPTION
			"This property provides the XFP
			extended check code(checksum) value for bytes 192 to 222
			present in XFP EEPROM Page number 1. 
			-----------------------------
			ommp81PlusInterfaceNumber:
			9 - LINE-1
			-----------------------------
			Values:			
			eg: 1(EEPROM Page number)
			-----------------------------"
		::= { ommp81PlusCardGeneralDetailsEntry 35 }

	ommp81PlusXfpVendorName OBJECT-TYPE		 
		SYNTAX  DisplayString
		MAX-ACCESS  read-only
		STATUS current
		DESCRIPTION
			"This property provides Vendor Name for given XFP. 
			The vendor name shall be the full name of the 
			corporation, a commonly accepted abbreviation of 
			the name of the corporation, the SCSI company code
			for the corporation, or the stock exchange code for
			the corporation.
			-----------------------------
			ommp81PlusInterfaceNumber:
			9 - LINE-1
			-----------------------------
			Values:			
			eg: WTD
			-----------------------------"
		::= { ommp81PlusCardGeneralDetailsEntry 36 }

	ommp81PlusXfpVendorIeeeId OBJECT-TYPE		 
		SYNTAX  DisplayString
		MAX-ACCESS  read-only
		STATUS current
		DESCRIPTION
			"This property defines the IEEE company Identifier for
			the vendor of XFP. A value of all zero in the 3-byte
			field indicates that the Vendor OUI is unspecified.
			-----------------------------
			ommp81PlusInterfaceNumber:
			9 - LINE-1
			-----------------------------
			Values:			
			eg: 010
			-----------------------------"
		::= { ommp81PlusCardGeneralDetailsEntry 37 }

	ommp81PlusXfpPartNumber OBJECT-TYPE		 
		SYNTAX  DisplayString
		MAX-ACCESS  read-only
		STATUS current
		DESCRIPTION
			"This property defines the vendor part number or
			product name of the XFP. A value of all zero
			indicates that the vendor Part Number is unspecified.
			-----------------------------
			ommp81PlusInterfaceNumber:
			9 - LINE-1
			-----------------------------
			Values:			
			eg: FTRX-1811-2D2
			-----------------------------"
		::= { ommp81PlusCardGeneralDetailsEntry 38 }

	ommp81PlusXfpSerialNumber OBJECT-TYPE		 
		SYNTAX  DisplayString
		MAX-ACCESS  read-only
		STATUS current
		DESCRIPTION
			"This property provides vendor serial number defining
			the vendor’s serial number for the XFP. A value of all
			zero in the 16-byte field indicates that the vendor
			serial number is unspecified.
			-----------------------------
			ommp81PlusInterfaceNumber:
			9 - LINE-1
			-----------------------------
			Values:			
			eg: KBG02CU
			-----------------------------"
		::= { ommp81PlusCardGeneralDetailsEntry 39 }

	ommp81PlusXfpRevisionNumber OBJECT-TYPE		 
		SYNTAX  DisplayString
		MAX-ACCESS  read-only
		STATUS current
		DESCRIPTION
			"The vendor revision number defining the vendor’s
			product revision number. A value of all zero indicates
			that the vendor revision number is unspecified
			-----------------------------
			ommp81PlusInterfaceNumber:
			9 - LINE-1
			-----------------------------
			Values:			
			eg: RT
			-----------------------------"
		::= { ommp81PlusCardGeneralDetailsEntry 40 }

	ommp81PlusXfpManufacturingDate OBJECT-TYPE		 
		SYNTAX  DisplayString
		MAX-ACCESS  read-only
		STATUS current
		DESCRIPTION
			"This property defines the manufacturing date for 
			XFP. A value of 8-byte field in ASCII which represents
			year, month and date of each two bytes. 
			Extra two bytes may be blank
			-----------------------------
			ommp81PlusInterfaceNumber:
			9 - LINE-1
			-----------------------------
			Values:			
			eg: 160224
			-----------------------------"
		::= { ommp81PlusCardGeneralDetailsEntry 41 }

	ommp81PlusFixedXfpLaserWavelength OBJECT-TYPE		 
		SYNTAX  DisplayString
		MAX-ACCESS  read-only
		STATUS current
		DESCRIPTION
			"This property provides transmitter LASER wavelength(nm)
			of the XFP
			-----------------------------
			ommp81PlusInterfaceNumber:
			9 - LINE-1
			-----------------------------
			Values:			
			eg: 1310
			-----------------------------"
		::= { ommp81PlusCardGeneralDetailsEntry 42 }

	ommp81PlusXfpLaserWavelengthTolerance OBJECT-TYPE		 
		SYNTAX  DisplayString
		MAX-ACCESS  read-only
		STATUS current
		DESCRIPTION
			"This property provides XFP wavelength tolerance in GhZ
			-----------------------------
			ommp81PlusInterfaceNumber:
			9 - LINE-1
			-----------------------------
			Values:			
			eg: 0.02
			-----------------------------"
		::= { ommp81PlusCardGeneralDetailsEntry 43 }

	ommp81PlusXfpWavelengthTunabilitySupported OBJECT-TYPE		 
		SYNTAX  INTEGER
		MAX-ACCESS  read-only
		STATUS current
		DESCRIPTION
			"This property provides information whether the XFP
			supports wavelength tunability or not.
			-----------------------------
			ommp81PlusInterfaceNumber:
			9 - LINE-1
			-----------------------------
			Values:			
			1 - XFP supports wavelength tunability
			0 - XFP does not supports wavelength tunability
			-----------------------------"
		::= { ommp81PlusCardGeneralDetailsEntry 44 }

	ommp81PlusTunableXfpLaserWavelengthError OBJECT-TYPE		 
		SYNTAX  DisplayString
		MAX-ACCESS  read-only
		STATUS current
		DESCRIPTION
			"This property provides wavelength error in picometer(pm)
			-----------------------------
			ommp81PlusInterfaceNumber:
			9 - LINE-1
			-----------------------------
			Values:			
			eg: 0.02
			-----------------------------"
		::= { ommp81PlusCardGeneralDetailsEntry 45 }

	ommp81PlusTunableXfpLaserFrequencyError OBJECT-TYPE		 
		SYNTAX  DisplayString
		MAX-ACCESS  read-only
		STATUS current
		DESCRIPTION
			"This property provides frequency error in Ghz.
			-----------------------------
			ommp81PlusInterfaceNumber:
			9 - LINE-1
			-----------------------------
			Values:			
			eg: 0.03
			-----------------------------"
		::= { ommp81PlusCardGeneralDetailsEntry 46 }

	ommp81PlusTunableXfpLaserFirstFrequency OBJECT-TYPE		 
		SYNTAX  DisplayString
		MAX-ACCESS  read-only
		STATUS current
		DESCRIPTION
			"This property defines the first LASER frequency of XFP.
			The two byte value is specified in units of THz.
			-----------------------------
			ommp81PlusInterfaceNumber:
			9 - LINE-1
			-----------------------------
			Values:			
			eg: 1529.45
			-----------------------------"
		::= { ommp81PlusCardGeneralDetailsEntry 47 }

	ommp81PlusTunableXfpLaserLastFrequency OBJECT-TYPE		 
		SYNTAX  DisplayString
		MAX-ACCESS  read-only
		STATUS current
		DESCRIPTION
			"This property defines the last laser frequency of XFP.
		 	 The two byte value is specified in units of THz.
			-----------------------------
			ommp81PlusInterfaceNumber:
			9 - LINE-1
			-----------------------------
			Values:			
			eg: 1563.45
			-----------------------------"
		::= { ommp81PlusCardGeneralDetailsEntry 48 }

	ommp81PlusTunableXfpWavelengthGridSpacing OBJECT-TYPE		 
		SYNTAX  DisplayString
		MAX-ACCESS  read-only
		STATUS current
		DESCRIPTION
			"This property gives difference in the wavelength
			between two channels In GHz.
			-----------------------------
			ommp81PlusInterfaceNumber:
			9 - LINE-1
			-----------------------------
			Values:
			eg: 50
			-----------------------------"
		::= { ommp81PlusCardGeneralDetailsEntry 49 }

	ommp81PlusXfpConnectorType OBJECT-TYPE		 
		SYNTAX  DisplayString
		MAX-ACCESS  read-only
		STATUS current
		DESCRIPTION
			"This property provides information of the XFP
			connector, value indicates the external connector
			provided on the XFP.
			-----------------------------
			ommp81PlusInterfaceNumber:
			9 - LINE-1
			-----------------------------
			Values:
			00h 	Unknown or unspecified
			01h 	SC
			02h 	Fibre Channel Style 1 copper connector
			03h 	Fibre Channel Style 2 copper connector
			04h 	BNC/TNC
			05h 	Fibre Channel coaxial headers
			06h 	FiberJack
			07h 	LC
			08h 	MT-RJ
			09h 	MU
			0Ah 	SG
			0Bh 	Optical pigtail
			0C-1Fh 	Reserved
			20h 	HSSDC II
			21h 	Copper Pigtail
			22h-7Fh Reserved
			80-FFh 	Vendor specific
			-----------------------------"
		::= { ommp81PlusCardGeneralDetailsEntry 50 }

	ommp81PlusXfpLinkLength OBJECT-TYPE		 
		SYNTAX  DisplayString
		MAX-ACCESS  read-only
		STATUS current
		DESCRIPTION
			"This property provides link length suported by the XFP
			-----------------------------
			ommp81PlusInterfaceNumber:
			9 - LINE-1
			-----------------------------
			Values:
			eg: 80.00
			-----------------------------"
		::= { ommp81PlusCardGeneralDetailsEntry 51 }

	ommp81PlusXfpCdrRateSupported OBJECT-TYPE		 
		SYNTAX  INTEGER
		MAX-ACCESS  read-only
		STATUS current
		DESCRIPTION
			"This property indicates which rates are supported by
			the CDR present in XFP.
			-----------------------------
			ommp81PlusInterfaceNumber:
			9 - LINE-1
			-----------------------------
			Values:
			Return value 1-Byte represetation:
			Byte-1  CDR Rates
			Bit-7	9.95 Gb/s
			Bit-6	10.3 Gb/s
			Bit-5	10.5 Gb/s
			Bit-4	10.7 Gb/s
			Bit-3	11.1 Gb/s
			Bit-2	Reserved
			Bit-1	Dont care for this property
			Bit-0	Dont care for this property
			-----------------------------"
		::= { ommp81PlusCardGeneralDetailsEntry 52 }

	ommp81PlusXfpSignalEncodingTypeSupported OBJECT-TYPE		 
		SYNTAX  INTEGER
		MAX-ACCESS  read-only
		STATUS current
		DESCRIPTION
			"This property indicates the serial encoding mechanisms
			that are supported by the XFP.
			-----------------------------
			ommp81PlusInterfaceNumber:
			9 - LINE-1
			-----------------------------
			Values:
			Return value 1-Byte represetation:
			Byte-1  Encoding Type
			Bit-7	64B/66B          
			Bit-6	8B10B     	 	 
			Bit-5	SONET Scrambled  
			Bit-4	NRZ              
			Bit-3	RZ              
			Bit-2	Reserved        
			Bit-1	Reserved         
			Bit-0	Reserved 
			-----------------------------"
		::= { ommp81PlusCardGeneralDetailsEntry 53 }

	ommp81PlusXfpTransceiverCodesSupported OBJECT-TYPE		 
		SYNTAX  DisplayString
		MAX-ACCESS  read-only
		STATUS current
		DESCRIPTION
			"The identifier value specifies which transceiver
			codes are supported by the XFP
			-----------------------------
			ommp81PlusInterfaceNumber:
			9 - LINE-1
			-----------------------------
			Values:
			Return value 8-Byte represetation:
			---------------------------------------------------------------------------------------------------------------------------------------
				  Byte-1	  Byte-2	          Byte-3	  Byte-4	          Byte-5    Byte-6    Byte-7	        Byte-8
			---------------------------------------------------------------------------------------------------------------------------------------
			Bit-7	 10GBASE-SR	 1200-MX-SN-I        	 Reserved	 1000BASE-SX/1xFC MMF	 I-64.1r   S-64.1    L-64.1	       V-64.2a
			Bit-6	 10GBASE-LR	 1200-SM-LL-L	         Reserved	 1000BASE-LX/1xFC-SMF	 I-64.1	   S-64.2a   L-64.2a	       V-64.2b
			Bit-5	 10GBASE-ER	 Extended 1550 nm	 Reserved	 2xFC-MMF/2xFC-SMF	 I-64.2r   S-64.2b   L-64.2b	       V-64.3
			Bit-4	 10GBASE-LRM	 Intermediate 1300 nm	 Reserved	 OC-48-SR	         I-64.2	   S-64.3a   L-64.2c	       Reserved
			Bit-3	 10GBASE-SW	 Reserved	         Reserved	 OC-48-IR	         I-64.3	   S-64.3b   L-64.3	       Reserved
			Bit-2	 10GBASE-LW	 Reserved	         Reserved	 OC-48-LR	         I-64.5	   S-64.5a   G.959.1 P1L1-2D2  Reserved
			Bit-1	 10GBASE-EW	 Reserved	         Reserved	 Reserved	         Reserved  S-64.5b   Reserved	       Reserved
			Bit-0	 Reserved	 Reserved	         Reserved	 Reserved	         Reserved  Reserved  Reserved	       Reserved
			-----------------------------"
		::= { ommp81PlusCardGeneralDetailsEntry 54 }

	ommp81PlusXfpMaximumBitrateSupported OBJECT-TYPE		 
		SYNTAX  DisplayString
		MAX-ACCESS  read-only
		STATUS current
		DESCRIPTION
			"This property provides maximum bit rate(Gbps) value
			supported by XFP
			-----------------------------
			ommp81PlusInterfaceNumber:
			9 - LINE-1
			-----------------------------
			Values: 9.5
			-----------------------------"
		::= { ommp81PlusCardGeneralDetailsEntry 55 }

	ommp81PlusXfpMinimumBitrateSupported OBJECT-TYPE		 
		SYNTAX  DisplayString
		MAX-ACCESS  read-only
		STATUS current
		DESCRIPTION
			"This property provides minimum bit rate(Gbps) value
			supported by XFP
			-----------------------------
			ommp81PlusInterfaceNumber:
			9 - LINE-1
			-----------------------------
			Values: 5.5
			-----------------------------"

		::= { ommp81PlusCardGeneralDetailsEntry 56 }

	ommp81PlusXfpMaximumCaseTemperatureSupported OBJECT-TYPE		 
		SYNTAX  INTEGER
		MAX-ACCESS  read-only
		STATUS current
		DESCRIPTION
			"This property provides the maximum case temperature
			(degree celcius) supported by XFP.
			-----------------------------
			ommp81PlusInterfaceNumber:
			9 - LINE-1
			-----------------------------
			Values:
			eg: 70
			-----------------------------"


		::= { ommp81PlusCardGeneralDetailsEntry 57 }

	ommp81PlusXfpMaximumPowerDissipationSupported OBJECT-TYPE		 
		SYNTAX  INTEGER
		MAX-ACCESS  read-only
		STATUS current
		DESCRIPTION
			"This property provides the maximum power dissipation(mW)
			supported from XFP.
			-----------------------------
			ommp81PlusInterfaceNumber:
			9 - LINE-1
			-----------------------------
			Values:
			eg: 25
			-----------------------------"
		::= { ommp81PlusCardGeneralDetailsEntry 58 }

	ommp81PlusXfpMaximumPowerDissipationSupportedAtPowerDownMode OBJECT-TYPE		 
		SYNTAX  INTEGER
		MAX-ACCESS  read-only
		STATUS current
		DESCRIPTION
			"This property provides the maximum power dissipation(mW)
			supported from XFP in power-down mode.
			-----------------------------
			ommp81PlusInterfaceNumber:
			9 - LINE-1
			-----------------------------
			Values:
			eg: 20
			-----------------------------"
		::= { ommp81PlusCardGeneralDetailsEntry 59 }

	ommp81PlusXfpMaximumCurrentLimitSupportedAtPlus5vSupply OBJECT-TYPE		 
		SYNTAX  INTEGER
		MAX-ACCESS  read-only
		STATUS current
		DESCRIPTION
			"This property defines the maximum current(mA) required
			by XFP at +5V power supply.
			-----------------------------
			ommp81PlusInterfaceNumber:
			9 - LINE-1
			-----------------------------
			Values:
			eg: 50
			-----------------------------"
		::= { ommp81PlusCardGeneralDetailsEntry 60 }

	ommp81PlusXfpMaximumCurrentLimitSupportedAtPlus3Point3vSupply OBJECT-TYPE		 
		SYNTAX  INTEGER
		MAX-ACCESS  read-only
		STATUS current
		DESCRIPTION
			"This property defines the maximum current(mA) required
			by XFP at +3.3V power supply.
			-----------------------------
			ommp81PlusInterfaceNumber:
			9 - LINE-1
			-----------------------------
			Values:
			eg: 50
			-----------------------------"
		::= { ommp81PlusCardGeneralDetailsEntry 61 }

	ommp81PlusXfpMaximumCurrentLimitSupportedAtPlus1Point8vSupply OBJECT-TYPE		 
		SYNTAX  INTEGER
		MAX-ACCESS  read-only
		STATUS current
		DESCRIPTION
			"This property defines the maximum current(mA) required
			by XFP at +1.8V power supply.
			-----------------------------
			ommp81PlusInterfaceNumber:
			9 - LINE-1
			-----------------------------
			Values:
			eg: 50
			-----------------------------"
		::= { ommp81PlusCardGeneralDetailsEntry 62 }

	ommp81PlusXfpMaximumCurrentLimitSupportedAtMinus5Point2vSupply OBJECT-TYPE		 
		SYNTAX  INTEGER
		MAX-ACCESS  read-only
		STATUS current
		DESCRIPTION
			"This property defines the maximum current(mA) required
			by XFP at -5.2V power supply.
			-----------------------------
			ommp81PlusInterfaceNumber:
			9 - LINE-1
			-----------------------------
			Values:
			eg: 50
			-----------------------------"
		::= { ommp81PlusCardGeneralDetailsEntry 63 }

	ommp81PlusXfpLineLoopbackSupported OBJECT-TYPE		 
		SYNTAX  INTEGER
		MAX-ACCESS  read-only
		STATUS current
		DESCRIPTION
			"This property provides information whether Line side
			loopback is supported or not.
			-----------------------------
			ommp81PlusInterfaceNumber:
			9 - LINE-1
			-----------------------------
			Values:
			1 - Lineside Loopback is supported in XFP
			0 - Lineside Loopback is not supported in XFP
			-----------------------------"
		::= { ommp81PlusCardGeneralDetailsEntry 64 }

	ommp81PlusXfpXfiLoopbackSupported OBJECT-TYPE		 
		SYNTAX  INTEGER
		MAX-ACCESS  read-only
		STATUS current
		DESCRIPTION
			"This property provides information whether Line side
			loopback at the Xfi level is supported or not.
			-----------------------------
			ommp81PlusInterfaceNumber:
			9 - LINE-1
			-----------------------------
			Values:
			1 - Xfi Loopback is supported in XFP
			0 - Xfi Loopback is not supported in XFP
			-----------------------------"
		::= { ommp81PlusCardGeneralDetailsEntry 65 }

	ommp81PlusXfpOptionalVpsSupported OBJECT-TYPE		 
		SYNTAX  INTEGER
		MAX-ACCESS  read-only
		STATUS current
		DESCRIPTION
			"This property provides information whether XFP
			supports optional variable power supply or not.
			-----------------------------
			ommp81PlusInterfaceNumber:
			9 - LINE-1
			-----------------------------
			Values:
			1 - XFP supports optional vps
			0 - XFP does not support optional vps
			-----------------------------"
		::= { ommp81PlusCardGeneralDetailsEntry 66 }

	ommp81PlusXfpLaserDisableThroughI2cSupported OBJECT-TYPE		 
		SYNTAX  INTEGER
		MAX-ACCESS  read-only
		STATUS current
		DESCRIPTION
			"This property provides information whether XFP
			LASER can be operated through single 2-wire interface
			bus or not.
			-----------------------------
			ommp81PlusInterfaceNumber:
			9 - LINE-1
			-----------------------------
			Values:
			1 - XFP supports LASER disable through I2C
			0 - XFP does not support LASER disable through I2C
			-----------------------------"
		::= { ommp81PlusCardGeneralDetailsEntry 67 }

	ommp81PlusXfpPowerDownThroughI2cSupported OBJECT-TYPE		 
		SYNTAX  INTEGER
		MAX-ACCESS  read-only
		STATUS current
		DESCRIPTION
			"This property provides information whether XFP-
			Power-down can be operated through single 2-wire 
			interface bus or not.
			-----------------------------
			ommp81PlusInterfaceNumber:
			9 - LINE-1
			-----------------------------
			Values:
			1 - XFP Supports XFP-power-down through I2C  
			0 - XFP does not supports XFP-power-down through I2C  
			-----------------------------"
		::= { ommp81PlusCardGeneralDetailsEntry 68 }

	ommp81PlusXfpVpsLvRegulatorModeSupported OBJECT-TYPE		 
		SYNTAX  INTEGER
		MAX-ACCESS  read-only
		STATUS current
		DESCRIPTION
			"This property provides information whether XFP
			supports VPS_LV_regulator_mode or not.
			-----------------------------
			ommp81PlusInterfaceNumber:
			9 - LINE-1
			-----------------------------
			Values:
			1 - XFP supports VPS_LV_regulator_mode
			0 - XFP does not support VPS_LV_regulator_mode
			-----------------------------"
		::= { ommp81PlusCardGeneralDetailsEntry 69 }

	ommp81PlusXfpVpsBypassedRegulatorModeSupported OBJECT-TYPE		 
		SYNTAX  INTEGER
		MAX-ACCESS  read-only
		STATUS current
		DESCRIPTION
			"This property provides information whether XFP
			supports VPS bypassed regulator mode or not.
			-----------------------------
			ommp81PlusInterfaceNumber:
			9 - LINE-1
			-----------------------------
			Values:
			1 - XFP supports VPS bypassed regulator mode
			0 - XFP does not support active VPS bypassed regulator mode
			-----------------------------"
		::= { ommp81PlusCardGeneralDetailsEntry 70 }

	ommp81PlusXfpActiveFecControlSupported OBJECT-TYPE		 
		SYNTAX  INTEGER
		MAX-ACCESS  read-only
		STATUS current
		DESCRIPTION
			"This property provides information whether XFP
			supports active FEC control functions or not.
			-----------------------------
			ommp81PlusInterfaceNumber:
			9 - LINE-1
			-----------------------------
			Values:
			1 - XFP supports active FEC control functions
			0 - XFP does not support active FEC control functions
			-----------------------------"
		::= { ommp81PlusCardGeneralDetailsEntry 71 }

	ommp81PlusXfpOptionalCmuModeSupported OBJECT-TYPE		 
		SYNTAX  INTEGER
		MAX-ACCESS  read-only
		STATUS current
		DESCRIPTION
			"This property provides information whether XFP
			supports CMU mode or not.
			-----------------------------
			ommp81PlusInterfaceNumber:
			9 - LINE-1
			-----------------------------
			Values:
			1 - XFP supports CMU mode
			0 - XFP does not support CMU mode
			-----------------------------"
		::= { ommp81PlusCardGeneralDetailsEntry 72 }

	ommp81PlusXfpFecBerSupported OBJECT-TYPE		 
		SYNTAX  INTEGER
		MAX-ACCESS  read-only
		STATUS current
		DESCRIPTION
			"This property provides information whether XFP
			supports FEC BER or not.
			-----------------------------
			ommp81PlusInterfaceNumber:
			9 - LINE-1
			-----------------------------
			Values:
			1 - XFP supports FEC BER
			0 - XFP does not support FEC BER
			-----------------------------"
		::= { ommp81PlusCardGeneralDetailsEntry 73 }

	ommp81PlusXfpReceivePowerMeasurementIsInOmaOrAverage OBJECT-TYPE		 
		SYNTAX  INTEGER
		MAX-ACCESS  read-only
		STATUS current
		DESCRIPTION
			"This property tells whether the received power  
			measurement from XFP is given as Oma or Average.
			-----------------------------
			ommp81PlusInterfaceNumber:
			9 - LINE-1
			-----------------------------
			Values:
			1 - OMA
			0 - Average Power
			-----------------------------"
		::= { ommp81PlusCardGeneralDetailsEntry 74 }

	ommp81PlusXfpActiveWavelengthControlSupported OBJECT-TYPE		 
		SYNTAX  INTEGER
		MAX-ACCESS  read-only
		STATUS current
		DESCRIPTION
			"This property provides whether the XFP wavelength 
			controlling state is active or not
			-----------------------------
			ommp81PlusInterfaceNumber:
			9 - LINE-1
			-----------------------------
			Values:
			1 - Active
			0 - Inactive
			-----------------------------"
		::= { ommp81PlusCardGeneralDetailsEntry 75 }

	ommp81PlusXfpTransmitterIsCooledOrUncooled OBJECT-TYPE		 
		SYNTAX  INTEGER
		MAX-ACCESS  read-only
		STATUS current
		DESCRIPTION
			"This property provide information on which type of
			diode used in transmitter of the XFP
			-----------------------------
			ommp81PlusInterfaceNumber:
			9 - LINE-1
			-----------------------------
			Values:
			1 - Cooling circuit supported for XFP transmitter. 
			0 - Cooling circuit not supported for XFP transmitter.
			-----------------------------"
		::= { ommp81PlusCardGeneralDetailsEntry 76 }

	ommp81PlusXfpReceiverTypeIsPinOrApd OBJECT-TYPE		 
		SYNTAX  INTEGER
		MAX-ACCESS  read-only
		STATUS current
		DESCRIPTION
			"This property provide information on which type of
			diode used in transmitter of the XFP.
			-----------------------------
			ommp81PlusInterfaceNumber:
			9 - LINE-1
			-----------------------------
			Values:
			1 - PIN detector
			0 - APD detector			 
			-----------------------------"
		::= { ommp81PlusCardGeneralDetailsEntry 77 }

	ommp81PlusSfpEepromPage OBJECT-TYPE		 
		SYNTAX  INTEGER
		MAX-ACCESS  read-write
		STATUS current
		DESCRIPTION
			"This property sets/gets the SFP EEPROM page, 
			the value represents the SFP EEPROM page number.
			-----------------------------
			ommp81PlusInterfaceNumber:
			1 to 8 - CLIENT-1 to CLIENT-8
			-----------------------------
			Values:			
			eg: 1(EEPROM Page number)
			-----------------------------"
		::= { ommp81PlusCardGeneralDetailsEntry 101 }

	ommp81PlusCheckCodeOfSfpEepromPage OBJECT-TYPE		 
		SYNTAX  INTEGER
		MAX-ACCESS  read-only
		STATUS current
		DESCRIPTION
			"This property provides the SFP
			check code(checksum) value for bytes 128 to 190
			present in SFP EEPROM Page number 1. 
			-----------------------------
			ommp81PlusInterfaceNumber:
			1 to 8 - CLIENT-1 to CLIENT-8
			-----------------------------
			Values:			
			eg: 1(EEPROM Page number)
			-----------------------------"
		::= { ommp81PlusCardGeneralDetailsEntry 102 }

	ommp81PlusExtendedCheckCodeOfSfpEepromPage OBJECT-TYPE		 
		SYNTAX  INTEGER
		MAX-ACCESS  read-only
		STATUS current
		DESCRIPTION
			"This property provides the SFP
			extended check code(checksum) value for bytes 192 to 222
			present in SFP EEPROM Page number 1. 
			-----------------------------
			ommp81PlusInterfaceNumber:
			1 to 8 - CLIENT-1 to CLIENT-8
			-----------------------------
			Values:			
			eg: 1(EEPROM Page number)
			-----------------------------"
		::= { ommp81PlusCardGeneralDetailsEntry 103 }

	ommp81PlusSfpVendorName OBJECT-TYPE		 
		SYNTAX  DisplayString
		MAX-ACCESS  read-only
		STATUS current
		DESCRIPTION
			"This property provides Vendor Name for given SFP. 
			The vendor name shall be the full name of the 
			corporation, a commonly accepted abbreviation of 
			the name of the corporation, the SCSI company code
			for the corporation, or the stock exchange code for
			the corporation.
			-----------------------------
			ommp81PlusInterfaceNumber:
			1 to 8 - CLIENT-1 to CLIENT-8
			-----------------------------
			Values:			
			eg: WTD
			-----------------------------"

		::= { ommp81PlusCardGeneralDetailsEntry 104 }

	ommp81PlusSfpVendorIeeeId OBJECT-TYPE		 
		SYNTAX  DisplayString
		MAX-ACCESS  read-only
		STATUS current
		DESCRIPTION
			"This property defines the IEEE company Identifier for
			the vendor of SFP. A value of all zero in the 3-byte
			field indicates that the Vendor OUI is unspecified.
			-----------------------------
			ommp81PlusInterfaceNumber:
			1 to 8 - CLIENT-1 to CLIENT-8
			-----------------------------
			Values:			
			eg: 010
			-----------------------------"
		::= { ommp81PlusCardGeneralDetailsEntry 105 }

	ommp81PlusSfpPartNumber OBJECT-TYPE		 
		SYNTAX  DisplayString
		MAX-ACCESS  read-only
		STATUS current
		DESCRIPTION
			"This property defines the vendor part number or
			product name of the SFP. A value of all zero
			indicates that the vendor Part Number is unspecified.
			-----------------------------
			ommp81PlusInterfaceNumber:
			1 to 8 - CLIENT-1 to CLIENT-8
			-----------------------------
			Values:			
			eg: WXTR15101000427
			-----------------------------"
		::= { ommp81PlusCardGeneralDetailsEntry 106 }

	ommp81PlusSfpSerialNumber OBJECT-TYPE		 
		SYNTAX  DisplayString
		MAX-ACCESS  read-only
		STATUS current
		DESCRIPTION
			"This property provides vendor serial number defining
			the vendor’s serial number for the SFP. A value of all
			zero in the 16-byte field indicates that the vendor
			serial number is unspecified.
			-----------------------------
			ommp81PlusInterfaceNumber:
			1 to 8 - CLIENT-1 to CLIENT-8
			-----------------------------
			Values:			
			eg: WXTRRPGEAS1
			-----------------------------"
		::= { ommp81PlusCardGeneralDetailsEntry 107 }

	ommp81PlusSfpRevisionNumber OBJECT-TYPE		 
		SYNTAX  DisplayString
		MAX-ACCESS  read-only
		STATUS current
		DESCRIPTION
			"The vendor revision number defining the vendor’s
			product revision number. A value of all zero indicates
			that the vendor revision number is unspecified
			-----------------------------
			ommp81PlusInterfaceNumber:
			1 to 8 - CLIENT-1 to CLIENT-8
			-----------------------------
			Values:			
			eg: RT
			-----------------------------"
		::= { ommp81PlusCardGeneralDetailsEntry 108 }

	ommp81PlusSfpManufacturingDate OBJECT-TYPE		 
		SYNTAX  DisplayString
		MAX-ACCESS  read-only
		STATUS current
		DESCRIPTION
			"This property defines the manufacturing date for 
			SFP. A value of 8-byte field in ASCII which represents
			year, month and date of each two bytes. 
			Extra two bytes may be blank
			-----------------------------
			ommp81PlusInterfaceNumber:
			1 to 8 - CLIENT-1 to CLIENT-8
			-----------------------------
			Values:			
			eg: 160224
			-----------------------------"
		::= { ommp81PlusCardGeneralDetailsEntry 109 }

	ommp81PlusFixedSfpLaserWavelength OBJECT-TYPE		 
		SYNTAX  DisplayString
		MAX-ACCESS  read-only
		STATUS current
		DESCRIPTION
			"This property provides transmitter LASER wavelength(nm)
			of the SFP
			-----------------------------
			ommp81PlusInterfaceNumber:
			1 to 8 - CLIENT-1 to CLIENT-8
			-----------------------------
			Values:			
			eg: 1310.0
			-----------------------------"
		::= { ommp81PlusCardGeneralDetailsEntry 110 }

	ommp81PlusSfpConnectorType OBJECT-TYPE		 
		SYNTAX  DisplayString
		MAX-ACCESS  read-only
		STATUS current
		DESCRIPTION
			"This property provides information of the SFP
			connector, value indicates the external connector
			provided on the SFP.
			-----------------------------
			ommp81PlusInterfaceNumber:
			1 to 8 - CLIENT-1 to CLIENT-8
			-----------------------------
			Values:

			00h 	Unknown or unspecified
			01h 	SC (Subscriber Connector)
			02h 	Fibre Channel Style 1 copper connector
			03h 	Fibre Channel Style 2 copper connector
			04h 	BNC/TNC (Bayonet/Threaded Neill-Concelman)
			05h 	Fibre Channel coax headers
			06h 	Fiber Jack
			07h 	LC (Lucent Connector)
			08h 	MT-RJ (Mechanical Transfer - Registered Jack)
			09h 	MU (Multiple Optical)
			0Ah 	SG
			0Bh 	Optical Pigtail
			0Ch 	MPO 1x12 (Multifiber Parallel Optic)
			0Dh 	MPO 2x16
			0E-1Fh 	Reserved
			20h 	HSSDC II (High Speed Serial Data Connector)
			21h 	Copper pigtail
			22h 	RJ45 (Registered Jack)
			23h 	No separable connector
			24h 	MXC 2x16
			25h-7Fh Reserved
			80h-FFh Vendor specific
			-----------------------------"
		::= { ommp81PlusCardGeneralDetailsEntry 111 }

	ommp81PlusSfpLinkLength OBJECT-TYPE		 
		SYNTAX  DisplayString
		MAX-ACCESS  read-only
		STATUS current
		DESCRIPTION
			"This property provides link length suported by the SFP
			-----------------------------
			ommp81PlusInterfaceNumber:
			1 to 8 - CLIENT-1 to CLIENT-8
			-----------------------------
			Values:
			eg: 80.00
			-----------------------------"
		::= { ommp81PlusCardGeneralDetailsEntry 112 }

	ommp81PlusSfpSignalEncodingTypeSupported OBJECT-TYPE		 
		SYNTAX  INTEGER
		MAX-ACCESS  read-only
		STATUS current
		DESCRIPTION
			"This property indicates the serial encoding mechanisms
			that are supported by the SFP.
			-----------------------------
			ommp81PlusInterfaceNumber:
			1 to 8 - CLIENT-1 to CLIENT-8
			-----------------------------
			Values:
			1 - 64B/66B
			2 - 8B10B
			3 - SONET Scrambled
			4 - NRZ
			5 - RZ
			-----------------------------"
		::= { ommp81PlusCardGeneralDetailsEntry 113 }

	ommp81PlusSfpTransceiverCodesSupported OBJECT-TYPE		 
		SYNTAX  INTEGER
		MAX-ACCESS  read-only
		STATUS current
		DESCRIPTION
			"The identifier value specifies which transceiver
			codes are supported by the SFP
			-----------------------------
			ommp81PlusInterfaceNumber:
			1 to 8 - CLIENT-1 to CLIENT-8
			-----------------------------
			Values:

			Return value 8-Byte represetation:
				  			 Byte-1	 Byte-2	 Byte-3	 Byte-4	 Byte-5  Byte-6  Byte-7	Byte-8
			100-M5-SN-I and 100-M6-SN-I	 0x00	 0x00   0x00	 0x00	 0x20    0x40    0x0C   0x01
			200-SM-LC-L and 100-SM-LC-L	 0x00	 0x00	 0x00	 0x00	 0x12	 0x00    0x01	0x05
			400-M5-SN-I and 400-M6-SN-I	 0x00	 0x00	 0x00	 0x00	 0x20    0x40    0x0C   0x15
			800-M5-SN-I and 800-M6-SN-I	 0x00	 0x00	 0x00	 0x00	 0x20    0x40    0x0C   0x54
			400-SM-LC-M	 		 0x00	 0x00	 0x00	 0x00	 0x0A    0x00    0x01   0x15
			400-SM-LC-L	 		 0x00	 0x00	 0x00	 0x00	 0x12    0x00    0x01   0x15
			200-SM-LL-V and 100-SM-LL-V	 0x00	 0x00	 0x00	 0x00	 0x80    0x10    0x01   0x05
			1000BASE-T	 		 0x00	 0x00	 0x00	 0x08    0x00    0x00    0x00   0x00
			1000BASE-SX	 		 0x00	 0x00	 0x00	 0x01    0x00    0x00    0x00   0x00
			1000BASE-LX	 		 0x00	 0x00	 0x00	 0x02    0x00    0x00    0x00   0x00
			1000BASE-LX10	 		 0x00	 0x00	 0x00	 0x02    0x00    0x00    0x00   0x00
			10GBASE-SR	 		 0x10h	 0x00	 0x00    0x00	 0x00	 0x00    0x00	0x00
			10GBASE-LR	 		 0x20h	 0x00	 0x00    0x00	 0x00	 0x00    0x00	0x00
			OC3/STM1 SR-1	 		 0x00	 0x00	 0x01h   0x00	 0x00	 0x00    0x00	0x00
			OC12/STM4 LR-1	 		 0x00	 0x10h	 0x40h   0x00	 0x00	 0x00    0x00	0x00
			OC48/STM16 LR-2	 		 0x00	 0x0Ch	 0x00    0x00	 0x00	 0x00    0x00	0x00
			10GE Passive copper cable	 0x00	 0x00	 0x00    0x00	 0x00	 0x04h   0x00	0x00
			10GE Active cable		 0x00	 0x00	 0x00    0x00	 0x00	 0x08h   0x00	0x00
			8/4/2G Passive copper cable	 0x00	 0x00	 0x00    0x00	 0x00	 0x04h   0x00	0x54h
			8/4/2G Active cable		 0x00	 0x00	 0x00    0x00	 0x00	 0x08h   0x00	0x54h
			-----------------------------"
		::= { ommp81PlusCardGeneralDetailsEntry 114 }

	ommp81PlusSfpMaximumBitrateSupported OBJECT-TYPE		 
		SYNTAX  DisplayString
		MAX-ACCESS  read-only
		STATUS current
		DESCRIPTION
			"This property provides maximum bit rate value(Gbps)
			supported by the SFP
			-----------------------------
			ommp81PlusInterfaceNumber:
			1 to 8 - CLIENT-1 to CLIENT-8
			-----------------------------
			Values: 2.7
			-----------------------------"
		::= { ommp81PlusCardGeneralDetailsEntry 115 }

	ommp81PlusSfpNominalBitrateSupported OBJECT-TYPE		 
		SYNTAX  DisplayString
		MAX-ACCESS  read-only
		STATUS current
		DESCRIPTION
			"This property provides maximum bit rate value(Gbps)
			supported by the SFP
			-----------------------------
			ommp81PlusInterfaceNumber:
			1 to 8 - CLIENT-1 to CLIENT-8
			-----------------------------
			Values: 2.5
			-----------------------------"
		::= { ommp81PlusCardGeneralDetailsEntry 116 }

	ommp81PlusSfpMinimumBitrateSupported OBJECT-TYPE		 
		SYNTAX  DisplayString
		MAX-ACCESS  read-only
		STATUS current
		DESCRIPTION
			"This property provides minimum bit rate value(Gbps)
			supported by the SFP
			-----------------------------
			ommp81PlusInterfaceNumber:
			1 to 8 - CLIENT-1 to CLIENT-8
			-----------------------------
			Values: 2.3
			-----------------------------"
		::= { ommp81PlusCardGeneralDetailsEntry 117 }

	ommp81PlusCardGeneralDetailsTableRowStatus OBJECT-TYPE
              SYNTAX      RowStatus
              MAX-ACCESS  read-write
              STATUS      current
              DESCRIPTION
			"*****************************
			This is MIB realted property,
			NOT to be considered as a card property
			*****************************"
              ::= { ommp81PlusCardGeneralDetailsEntry 118 }

--*****************************************************************************
--				   CONFIGURATION
--*****************************************************************************

	ommp81PlusConfigurationTable OBJECT-TYPE
		SYNTAX  SEQUENCE OF Ommp81PlusConfigurationEntry 
		MAX-ACCESS  not-accessible
		STATUS  current
		DESCRIPTION
		      "Contains configuration queries of the OMMP81-PLUS card"
		::= { ommp81PlusConfiguration 1 }

	ommp81PlusConfigurationEntry  OBJECT-TYPE
              SYNTAX  Ommp81PlusConfigurationEntry 
              MAX-ACCESS  not-accessible
              STATUS  current
              DESCRIPTION 
              	""
		INDEX   { node, rack, subRack, slot, ommp81PlusInterfaceNumber }
		::= { ommp81PlusConfigurationTable 1 }
	
	Ommp81PlusConfigurationEntry  ::= 
		SEQUENCE {
				ommp81PlusCardSoftwareUpgrade					DisplayString,
				ommp81PlusCardSignalMonitorState				INTEGER,
				ommp81PlusCardOpticalMonitorState				INTEGER,
				ommp81PlusCardSoftReset						INTEGER,
				ommp81PlusCardFactoryReset					INTEGER,
				ommp81PlusCardAccessStatus					INTEGER,
				ommp81PlusSyncSystemTimeWithNtpServer				DisplayString,
				ommp81PlusSyncRtcWithNtpServer						DisplayString,
				ommp81PlusSyncRtcWithSystemTime						DisplayString,
				ommp81PlusUpdateGivenTimeIntoSystem					DisplayString,
				ommp81PlusUpdateGivenTimeIntoRtc					DisplayString,
				ommp81PlusSystemTimeAndRtcTime						DisplayString,
--				ommp81PlusTrafficConfiguration					DisplayString,
				ommp81PlusTrafficConfiguration					INTEGER,
				ommp81PlusLoopbackState						INTEGER,
				ommp81PlusPortSignalMonitorState				INTEGER,
				ommp81PlusPortOpticalMonitorState				INTEGER,
				ommp81PlusClearSignalPerformance				INTEGER,
				ommp81PlusAlsState						INTEGER,
				ommp81PlusAlsPulseRepetitionTime				INTEGER,
				ommp81PlusOtuFecConfiguration					INTEGER,
				ommp81PlusOtuSignalFailThreshold				INTEGER,
				ommp81PlusOtuSignalDegradeThreshold				INTEGER,
				ommp81PlusOtuAlarmIndicationSignalAlarmInsertion		INTEGER,
				ommp81PlusOtuSapiTransmitTraceMessage				DisplayString,
				ommp81PlusOtuDapiTransmitTraceMessage				DisplayString,
				ommp81PlusOtuOperatorSpecificTransmitTraceMessage		DisplayString,
				ommp81PlusOtuSapiExpectedTraceMessage				DisplayString,
				ommp81PlusOtuDapiExpectedTraceMessage				DisplayString,
				ommp81PlusOtuOperatorSpecificExpectedTraceMessage		DisplayString,
				ommp81PlusOtuSapiReceivedTraceMessage				DisplayString,
				ommp81PlusOtuDapiReceivedTraceMessage				DisplayString,
				ommp81PlusOtuOperatorSpecificReceivedTraceMessage		DisplayString,
				ommp81PlusOduSignalFailThreshold				INTEGER,
				ommp81PlusOduSignalDegradeThreshold				INTEGER,
				ommp81PlusOduAlarmIndicationSignalAlarmInsertion		INTEGER,
				ommp81PlusOduLockedDefectAlarmInsertion				INTEGER,
				ommp81PlusOduOpenConnectionIndicationAlarmInsertion		INTEGER,
				ommp81PlusOduSapiTransmitTraceMessage				DisplayString,
				ommp81PlusOduDapiTransmitTraceMessage				DisplayString,
				ommp81PlusOduOperatorSpecificTransmitTraceMessage		DisplayString,
				ommp81PlusOduSapiExpectedTraceMessage				DisplayString,
				ommp81PlusOduDapiExpectedTraceMessage				DisplayString,
				ommp81PlusOduOperatorSpecificExpectedTraceMessage		DisplayString,
				ommp81PlusOduSapiReceivedTraceMessage				DisplayString,
				ommp81PlusOduDapiReceivedTraceMessage				DisplayString,
				ommp81PlusOduOperatorSpecificReceivedTraceMessage		DisplayString,
				ommp81PlusOpuTransmitPayloadType				INTEGER,
				ommp81PlusOpuReceivedPayloadType				INTEGER,
				ommp81PlusSdhMsB2ExcessiveErrorThreshold			INTEGER,
				ommp81PlusSdhMsB2SignalDegradeThreshold				INTEGER,
				ommp81PlusEthernetAutoNegotiation				INTEGER,
				ommp81PlusCalibrateHyphyXfiSerdes				INTEGER,
				ommp81PlusTunableXfpLaserWavelength				INTEGER,
				ommp81PlusTunableXfpLaserChannelNumber				INTEGER,
				ommp81PlusXfpLaserState						INTEGER,
				ommp81PlusXfpReset						INTEGER,
				ommp81PlusXfpPowerDownMode					INTEGER,
				ommp81PlusXfpLineLoopback					INTEGER,
				ommp81PlusXfpXfiLoopback					INTEGER,
				ommp81PlusXfpAmplitudeThresholdOfReceiverForFecControl		INTEGER,
				ommp81PlusXfpPhaseInEyeDiagramForFecControl			INTEGER,
				ommp81PlusXfpSystemReportingBer					INTEGER,
				ommp81PlusXfpHighTemperatureAlarmThreshold			DisplayString,
				ommp81PlusXfpLowTemperatureAlarmThreshold			DisplayString,
				ommp81PlusXfpHighTemperatureWarningThreshold			DisplayString,
				ommp81PlusXfpLowTemperatureWarningThreshold			DisplayString,
				ommp81PlusXfpHighBiasCurrentAlarmThreshold			DisplayString,
				ommp81PlusXfpLowBiasCurrentAlarmThreshold			DisplayString,
				ommp81PlusXfpHighBiasCurrentWarningThreshold			DisplayString,
				ommp81PlusXfpLowBiasCurrentWarningThreshold			DisplayString,
				ommp81PlusXfpInputHighPowerAlarmThreshold			DisplayString,
				ommp81PlusXfpInputLowPowerAlarmThreshold			DisplayString,
				ommp81PlusXfpInputHighPowerWarningThreshold			DisplayString,
				ommp81PlusXfpInputLowPowerWarningThreshold			DisplayString,
				ommp81PlusXfpOutputHighPowerAlarmThreshold			DisplayString,
				ommp81PlusXfpOutputLowPowerAlarmThreshold			DisplayString,
				ommp81PlusXfpOutputHighPowerWarningThreshold			DisplayString,
				ommp81PlusXfpOutputLowPowerWarningThreshold			DisplayString,
				ommp81PlusXfpHighSupplyVoltageAlarmThreshold			DisplayString,
				ommp81PlusXfpLowSupplyVoltageAlarmThreshold			DisplayString,
				ommp81PlusXfpHighSupplyVoltageWarningThreshold			DisplayString,
				ommp81PlusXfpLowSupplyVoltageWarningThreshold			DisplayString,
				ommp81PlusSfpLaserState						INTEGER,
				ommp81PlusSfpHighTemperatureAlarmThreshold			DisplayString,
				ommp81PlusSfpLowTemperatureAlarmThreshold			DisplayString,
				ommp81PlusSfpHighTemperatureWarningThreshold			DisplayString,
				ommp81PlusSfpLowTemperatureWarningThreshold			DisplayString,
				ommp81PlusSfpHighBiasCurrentAlarmThreshold			DisplayString,
				ommp81PlusSfpLowBiasCurrentAlarmThreshold			DisplayString,
				ommp81PlusSfpHighBiasCurrentWarningThreshold			DisplayString,
				ommp81PlusSfpLowBiasCurrentWarningThreshold			DisplayString,
				ommp81PlusSfpInputHighPowerAlarmThreshold			DisplayString,
				ommp81PlusSfpInputLowPowerAlarmThreshold			DisplayString,
				ommp81PlusSfpInputHighPowerWarningThreshold			DisplayString,
				ommp81PlusSfpInputLowPowerWarningThreshold			DisplayString,
				ommp81PlusSfpOutputHighPowerAlarmThreshold			DisplayString,
				ommp81PlusSfpOutputLowPowerAlarmThreshold			DisplayString,
				ommp81PlusSfpOutputHighPowerWarningThreshold			DisplayString,
				ommp81PlusSfpOutputLowPowerWarningThreshold			DisplayString,
				ommp81PlusSfpHighSupplyVoltageAlarmThreshold			DisplayString,
				ommp81PlusSfpLowSupplyVoltageAlarmThreshold			DisplayString,
				ommp81PlusSfpHighSupplyVoltageWarningThreshold			DisplayString,
				ommp81PlusSfpLowSupplyVoltageWarningThreshold			DisplayString,
				ommp81PlusXfpInputPowerFailureAlarmInhibit			INTEGER,
				ommp81PlusXfpOutputPowerFailureAlarmInhibit			INTEGER,
				ommp81PlusXfpHighTemperatureAlarmInhibit			INTEGER,
				ommp81PlusXfpLowTemperatureAlarmInhibit				INTEGER,
				ommp81PlusXfpHighTemperatureWarningInhibit			INTEGER,
				ommp81PlusXfpLowTemperatureWarningInhibit			INTEGER,
				ommp81PlusXfpHighBiasCurrentAlarmInhibit			INTEGER,
				ommp81PlusXfpLowBiasCurrentAlarmInhibit				INTEGER,
				ommp81PlusXfpHighBiasCurrentWarningInhibit			INTEGER,
				ommp81PlusXfpLowBiasCurrentWarningInhibit			INTEGER,
				ommp81PlusXfpInputHighPowerAlarmInhibit				INTEGER,
				ommp81PlusXfpInputLowPowerAlarmInhibit				INTEGER,
				ommp81PlusXfpInputHighPowerWarningInhibit			INTEGER,
				ommp81PlusXfpInputLowPowerWarningInhibit			INTEGER,
				ommp81PlusXfpOutputHighPowerAlarmInhibit			INTEGER,
				ommp81PlusXfpOutputLowPowerAlarmInhibit				INTEGER,
				ommp81PlusXfpOutputHighPowerWarningInhibit			INTEGER,
				ommp81PlusXfpOutputLowPowerWarningInhibit			INTEGER,
				ommp81PlusXfpHighSupplyVoltageAlarmInhibit			INTEGER,
				ommp81PlusXfpLowSupplyVoltageAlarmInhibit			INTEGER,
				ommp81PlusXfpHighSupplyVoltageWarningInhibit			INTEGER,
				ommp81PlusXfpLowSupplyVoltageWarningInhibit			INTEGER,
				ommp81PlusXfpPresenceAbsenceNotificationInhibit			INTEGER,
				ommp81PlusSfpInputPowerFailureAlarmInhibit			INTEGER,
				ommp81PlusSfpOutputPowerFailureAlarmInhibit			INTEGER,
				ommp81PlusSfpHighTemperatureAlarmInhibit			INTEGER,
				ommp81PlusSfpLowTemperatureAlarmInhibit				INTEGER,
				ommp81PlusSfpHighTemperatureWarningInhibit			INTEGER,
				ommp81PlusSfpLowTemperatureWarningInhibit			INTEGER,
				ommp81PlusSfpHighBiasCurrentAlarmInhibit			INTEGER,
				ommp81PlusSfpLowBiasCurrentAlarmInhibit				INTEGER,
				ommp81PlusSfpHighBiasCurrentWarningInhibit			INTEGER,
				ommp81PlusSfpLowBiasCurrentWarningInhibit			INTEGER,
				ommp81PlusSfpInputHighPowerAlarmInhibit				INTEGER,
				ommp81PlusSfpInputLowPowerAlarmInhibit				INTEGER,
				ommp81PlusSfpInputHighPowerWarningInhibit			INTEGER,
				ommp81PlusSfpInputLowPowerWarningInhibit			INTEGER,
				ommp81PlusSfpOutputHighPowerAlarmInhibit			INTEGER,
				ommp81PlusSfpOutputLowPowerAlarmInhibit				INTEGER,
				ommp81PlusSfpOutputHighPowerWarningInhibit			INTEGER,
				ommp81PlusSfpOutputLowPowerWarningInhibit			INTEGER,
				ommp81PlusSfpHighSupplyVoltageAlarmInhibit			INTEGER,
				ommp81PlusSfpLowSupplyVoltageAlarmInhibit			INTEGER,
				ommp81PlusSfpHighSupplyVoltageWarningInhibit			INTEGER,
				ommp81PlusSfpLowSupplyVoltageWarningInhibit			INTEGER,
				ommp81PlusSfpPresenceAbsenceNotificationInhibit			INTEGER,
				ommp81PlusSfpTransmitFaultPresenceAlarmInhibit			INTEGER,
				ommp81PlusOtuLossOfSignalAlarmInhibit				INTEGER,
				ommp81PlusOtuLossOfFrameAlarmInhibit				INTEGER,
				ommp81PlusOtuOutOfFrameAlarmInhibit				INTEGER,
				ommp81PlusOtuLossOfMultiFrameAlarmInhibit			INTEGER,
				ommp81PlusOtuOutOfMultiFrameAlarmInhibit			INTEGER,
				ommp81PlusOtuSignalFailAlarmInhibit				INTEGER,
				ommp81PlusOtuSignalDegradeAlarmInhibit				INTEGER,
				ommp81PlusOtuAlarmIndicationSignalAlarmInhibit			INTEGER,
				ommp81PlusOtuIncomingAlignmentErrorAlarmInhibit			INTEGER,
				ommp81PlusOtuTraceIdentifierMismatchAlarmInhibit		INTEGER,
				ommp81PlusOtuBackwardIncomingAlignmentErrorAlarmInhibit		INTEGER,
				ommp81PlusOtuBackwardDefectIndicationAlarmInhibit		INTEGER,
				ommp81PlusOduSignalFailAlarmInhibit				INTEGER,
				ommp81PlusOduSignalDegradeAlarmInhibit				INTEGER,
				ommp81PlusOduAlarmIndicationSignalAlarmInhibit			INTEGER,
				ommp81PlusOduTcm1IncomingAlignmentErrorAlarmInhibit		INTEGER,
				ommp81PlusOduTcm2IncomingAlignmentErrorAlarmInhibit		INTEGER,
				ommp81PlusOduTcm3IncomingAlignmentErrorAlarmInhibit		INTEGER,
				ommp81PlusOduTcm4IncomingAlignmentErrorAlarmInhibit		INTEGER,
				ommp81PlusOduTcm5IncomingAlignmentErrorAlarmInhibit		INTEGER,
				ommp81PlusOduTcm6IncomingAlignmentErrorAlarmInhibit		INTEGER,
				ommp81PlusOduTraceIdentifierMismatchAlarmInhibit		INTEGER,
				ommp81PlusOduLockedDefectAlarmInhibit				INTEGER,
				ommp81PlusOduOpenConnectionIndicationAlarmInhibit		INTEGER,
				ommp81PlusOduBackwardDefectIndicationAlarmInhibit		INTEGER,
				ommp81PlusOduTcm1BackwardIncomingAlignmentErrorAlarmInhibit	INTEGER,
				ommp81PlusOduTcm2BackwardIncomingAlignmentErrorAlarmInhibit	INTEGER,
				ommp81PlusOduTcm3BackwardIncomingAlignmentErrorAlarmInhibit	INTEGER,
				ommp81PlusOduTcm4BackwardIncomingAlignmentErrorAlarmInhibit	INTEGER,
				ommp81PlusOduTcm5BackwardIncomingAlignmentErrorAlarmInhibit	INTEGER,
				ommp81PlusOduTcm6BackwardIncomingAlignmentErrorAlarmInhibit	INTEGER,
				ommp81PlusOduLossOfFrameLossOfMultiframeAlarmInhibit		INTEGER,
				ommp81PlusOpuPayloadMismatchAlarmInhibit			INTEGER,
				ommp81PlusOchLossOfPayloadAlarmInhibit				INTEGER,
				ommp81PlusSdhLossOfSignalAlarmInhibit				INTEGER,
				ommp81PlusSdhOutOfFrameAlarmInhibit				INTEGER,
				ommp81PlusSdhLossOfFrameAlarmInhibit				INTEGER,
				ommp81PlusSdhRsAlarmIndicationSignalAlarmInhibit		INTEGER,
				ommp81PlusSdhRsTraceIdentifierMismatchAlarmInhibit		INTEGER,
				ommp81PlusSdhAuAlarmIndicationSignalAlarmInhibit		INTEGER,
				ommp81PlusSdhAuLossOfPointerAlarmInhibit			INTEGER,
				ommp81PlusSdhMsAlarmIndicationSignalAlarmInhibit		INTEGER,
				ommp81PlusSdhMsRemoteErrorIndicationAlarmInhibit		INTEGER,
				ommp81PlusSdhMsRemoteDefectIndicationAlarmInhibit		INTEGER,
				ommp81PlusSdhMsRemoteFailureIndicationAlarmInhibit		INTEGER,
				ommp81PlusSdhMsB2ExcessiveErrorAlarmInhibit			INTEGER,
				ommp81PlusSdhMsB2SignalDegradeAlarmInhibit			INTEGER,
				ommp81PlusSdhLossOfSequenceSynchronisationAlarmInhibit		INTEGER,
				ommp81PlusSdhLowerOrderPathPayloadLabelMismatchAlarmInhibit	INTEGER,
				ommp81PlusSdhLowerOrderPathUnequippedAlarmInhibit		INTEGER,
				ommp81PlusEthernetLossOfSignalAlarmInhibit			INTEGER,
				ommp81PlusEthernetLossOfSignalSyncAlarmInhibit			INTEGER,
				ommp81PlusEthernetLinkFailureAlarmInhibit			INTEGER,
				ommp81PlusEthernetAutoNegotiationAlarmInhibit			INTEGER,
				ommp81PlusEthernetFrameCheckSequenceAlarmInhibit		INTEGER,
				ommp81PlusEthernetCarrierStatusAlarmInhibit			INTEGER,
				ommp81PlusEthernetHighBerAlarmInhibit				INTEGER,
				ommp81PlusEthernetLocalFaultAlarmInhibit			INTEGER,
				ommp81PlusEthernetRemoteFaultAlarmInhibit			INTEGER,
				ommp81PlusFcTransmitDisparityInversionDefectAlarmInhibit	INTEGER,
				ommp81PlusFcTransmitDigitalLossOfLinkDefectAlarmInhibit		INTEGER,
				ommp81PlusFcTrasnmitLossOfSynchronizationDefectAlarmInhibit	INTEGER,
				ommp81PlusFcReceiveDigitalLossOfLinkDefectAlarmInhibit		INTEGER,
				ommp81PlusFcReceiveLossOfSynchronizationDefectAlarmInhibit	INTEGER,
				ommp81PlusFcReceiveTransitionDetectDefectAlarmInhibit		INTEGER,
				ommp81PlusFcReceiveAnalogLossOfSignalDefectAlarmInhibit		INTEGER,
				ommp81PlusFcReceiveLineCodeViolationDefectAlarmInhibit		INTEGER,
				ommp81PlusGfpCsfSignalFailAlarmInhibit				INTEGER,
				ommp81PlusGfpCsfLinkFailAlarmInhibit				INTEGER,
				ommp81PlusGfpCoreHeaderErrorAlarmInhibit			INTEGER,
				ommp81PlusGfpExtentionHeaderErrorAlarmInhibit			INTEGER,
				ommp81PlusXfpInputPowerFailureAlarmSeverity			DisplayString,
				ommp81PlusXfpOutputPowerFailureAlarmSeverity			DisplayString,
				ommp81PlusXfpHighTemperatureAlarmSeverity			DisplayString,
				ommp81PlusXfpLowTemperatureAlarmSeverity			DisplayString,
				ommp81PlusXfpHighTemperatureWarningSeverity			DisplayString,
				ommp81PlusXfpLowTemperatureWarningSeverity			DisplayString,
				ommp81PlusXfpHighBiasCurrentAlarmSeverity			DisplayString,
				ommp81PlusXfpLowBiasCurrentAlarmSeverity			DisplayString,
				ommp81PlusXfpHighBiasCurrentWarningSeverity			DisplayString,
				ommp81PlusXfpLowBiasCurrentWarningSeverity			DisplayString,
				ommp81PlusXfpInputHighPowerAlarmSeverity			DisplayString,
				ommp81PlusXfpInputLowPowerAlarmSeverity				DisplayString,
				ommp81PlusXfpInputHighPowerWarningSeverity			DisplayString,
				ommp81PlusXfpInputLowPowerWarningSeverity			DisplayString,
				ommp81PlusXfpOutputHighPowerAlarmSeverity			DisplayString,
				ommp81PlusXfpOutputLowPowerAlarmSeverity			DisplayString,
				ommp81PlusXfpOutputHighPowerWarningSeverity			DisplayString,
				ommp81PlusXfpOutputLowPowerWarningSeverity			DisplayString,
				ommp81PlusXfpHighSupplyVoltageAlarmSeverity			DisplayString,
				ommp81PlusXfpLowSupplyVoltageAlarmSeverity			DisplayString,
				ommp81PlusXfpHighSupplyVoltageWarningSeverity			DisplayString,
				ommp81PlusXfpLowSupplyVoltageWarningSeverity			DisplayString,
				ommp81PlusXfpPresenceAbsenceNotificationSeverity		DisplayString,
				ommp81PlusSfpInputPowerFailureAlarmSeverity			DisplayString,
				ommp81PlusSfpOutputPowerFailureAlarmSeverity			DisplayString,
				ommp81PlusSfpHighTemperatureAlarmSeverity			DisplayString,
				ommp81PlusSfpLowTemperatureAlarmSeverity			DisplayString,
				ommp81PlusSfpHighTemperatureWarningSeverity			DisplayString,
				ommp81PlusSfpLowTemperatureWarningSeverity			DisplayString,
				ommp81PlusSfpHighBiasCurrentAlarmSeverity			DisplayString,
				ommp81PlusSfpLowBiasCurrentAlarmSeverity			DisplayString,
				ommp81PlusSfpHighBiasCurrentWarningSeverity			DisplayString,
				ommp81PlusSfpLowBiasCurrentWarningSeverity			DisplayString,
				ommp81PlusSfpInputHighPowerAlarmSeverity			DisplayString,
				ommp81PlusSfpInputLowPowerAlarmSeverity				DisplayString,
				ommp81PlusSfpInputHighPowerWarningSeverity			DisplayString,
				ommp81PlusSfpInputLowPowerWarningSeverity			DisplayString,
				ommp81PlusSfpOutputHighPowerAlarmSeverity			DisplayString,
				ommp81PlusSfpOutputLowPowerAlarmSeverity			DisplayString,
				ommp81PlusSfpOutputHighPowerWarningSeverity			DisplayString,
				ommp81PlusSfpOutputLowPowerWarningSeverity			DisplayString,
				ommp81PlusSfpHighSupplyVoltageAlarmSeverity			DisplayString,
				ommp81PlusSfpLowSupplyVoltageAlarmSeverity			DisplayString,
				ommp81PlusSfpHighSupplyVoltageWarningSeverity			DisplayString,
				ommp81PlusSfpLowSupplyVoltageWarningSeverity			DisplayString,
				ommp81PlusSfpPresenceAbsenceNotificationSeverity		DisplayString,
				ommp81PlusSfpTransmitFaultPresenceAlarmSeverity			DisplayString,
				ommp81PlusOtuLossOfSignalAlarmSeverity				DisplayString,
				ommp81PlusOtuLossOfFrameAlarmSeverity				DisplayString,
				ommp81PlusOtuOutOfFrameAlarmSeverity				DisplayString,
				ommp81PlusOtuLossOfMultiFrameAlarmSeverity			DisplayString,
				ommp81PlusOtuOutOfMultiFrameAlarmSeverity			DisplayString,
				ommp81PlusOtuSignalFailAlarmSeverity				DisplayString,
				ommp81PlusOtuSignalDegradeAlarmSeverity				DisplayString,
				ommp81PlusOtuAlarmIndicationSignalAlarmSeverity			DisplayString,
				ommp81PlusOtuIncomingAlignmentErrorAlarmSeverity		DisplayString,
				ommp81PlusOtuTraceIdentifierMismatchAlarmSeverity		DisplayString,
				ommp81PlusOtuBackwardIncomingAlignmentErrorAlarmSeverity	DisplayString,
				ommp81PlusOtuBackwardDefectIndicationAlarmSeverity		DisplayString,
				ommp81PlusOduSignalFailAlarmSeverity				DisplayString,
				ommp81PlusOduSignalDegradeAlarmSeverity				DisplayString,
				ommp81PlusOduAlarmIndicationSignalAlarmSeverity			DisplayString,
				ommp81PlusOduTcm1IncomingAlignmentErrorAlarmSeverity		DisplayString,
				ommp81PlusOduTcm2IncomingAlignmentErrorAlarmSeverity		DisplayString,
				ommp81PlusOduTcm3IncomingAlignmentErrorAlarmSeverity		DisplayString,
				ommp81PlusOduTcm4IncomingAlignmentErrorAlarmSeverity		DisplayString,
				ommp81PlusOduTcm5IncomingAlignmentErrorAlarmSeverity		DisplayString,
				ommp81PlusOduTcm6IncomingAlignmentErrorAlarmSeverity		DisplayString,
				ommp81PlusOduTraceIdentifierMismatchAlarmSeverity		DisplayString,
				ommp81PlusOduLockedDefectAlarmSeverity				DisplayString,
				ommp81PlusOduOpenConnectionIndicationAlarmSeverity		DisplayString,
				ommp81PlusOduBackwardDefectIndicationAlarmSeverity		DisplayString,
				ommp81PlusOduTcm1BackwardIncomingAlignmentErrorAlarmSeverity	DisplayString,
				ommp81PlusOduTcm2BackwardIncomingAlignmentErrorAlarmSeverity	DisplayString,
				ommp81PlusOduTcm3BackwardIncomingAlignmentErrorAlarmSeverity	DisplayString,
				ommp81PlusOduTcm4BackwardIncomingAlignmentErrorAlarmSeverity	DisplayString,
				ommp81PlusOduTcm5BackwardIncomingAlignmentErrorAlarmSeverity	DisplayString,
				ommp81PlusOduTcm6BackwardIncomingAlignmentErrorAlarmSeverity	DisplayString,
				ommp81PlusOduLossOfFrameLossOfMultiframeAlarmSeverity		DisplayString,
				ommp81PlusOpuPayloadMismatchAlarmSeverity			DisplayString,
				ommp81PlusOchLossOfPayloadAlarmSeverity				DisplayString,
				ommp81PlusSdhLossOfSignalAlarmSeverity				DisplayString,
				ommp81PlusSdhOutOfFrameAlarmSeverity				DisplayString,
				ommp81PlusSdhLossOfFrameAlarmSeverity				DisplayString,
				ommp81PlusSdhRsAlarmIndicationSignalAlarmSeverity		DisplayString,
				ommp81PlusSdhRsTraceIdentifierMismatchAlarmSeverity		DisplayString,
				ommp81PlusSdhAuAlarmIndicationSignalAlarmSeverity		DisplayString,
				ommp81PlusSdhAuLossOfPointerAlarmSeverity			DisplayString,
				ommp81PlusSdhMsAlarmIndicationSignalAlarmSeverity		DisplayString,
				ommp81PlusSdhMsRemoteErrorIndicationAlarmSeverity		DisplayString,
				ommp81PlusSdhMsRemoteDefectIndicationAlarmSeverity		DisplayString,
				ommp81PlusSdhMsRemoteFailureIndicationAlarmSeverity		DisplayString,
				ommp81PlusSdhMsB2ExcessiveErrorAlarmSeverity			DisplayString,
				ommp81PlusSdhMsB2SignalDegradeAlarmSeverity			DisplayString,
				ommp81PlusSdhLossOfSequenceSynchronisationAlarmSeverity		DisplayString,
				ommp81PlusSdhLowerOrderPathPayloadLabelMismatchAlarmSeverity	DisplayString,
				ommp81PlusSdhLowerOrderPathUnequippedAlarmSeverity		DisplayString,
				ommp81PlusEthernetLossOfSignalAlarmSeverity			DisplayString,
				ommp81PlusEthernetLossOfSignalSyncAlarmSeverity			DisplayString,
				ommp81PlusEthernetLinkFailureAlarmSeverity			DisplayString,
				ommp81PlusEthernetAutoNegotiationAlarmSeverity			DisplayString,
				ommp81PlusEthernetFrameCheckSequenceAlarmSeverity		DisplayString,
				ommp81PlusEthernetCarrierStatusAlarmSeverity			DisplayString,
				ommp81PlusEthernetHighBerAlarmSeverity				DisplayString,
				ommp81PlusEthernetLocalFaultAlarmSeverity			DisplayString,
				ommp81PlusEthernetRemoteFaultAlarmSeverity			DisplayString,
				ommp81PlusFcTransmitDisparityInversionDefectAlarmSeverity	DisplayString,
				ommp81PlusFcTransmitDigitalLossOfLinkDefectAlarmSeverity	DisplayString,
				ommp81PlusFcTrasnmitLossOfSynchronizationDefectAlarmSeverity	DisplayString,
				ommp81PlusFcReceiveDigitalLossOfLinkDefectAlarmSeverity		DisplayString,
				ommp81PlusFcReceiveLossOfSynchronizationDefectAlarmSeverity	DisplayString,
				ommp81PlusFcReceiveTransitionDetectDefectAlarmSeverity		DisplayString,
				ommp81PlusFcReceiveAnalogLossOfSignalDefectAlarmSeverity	DisplayString,
				ommp81PlusFcReceiveLineCodeViolationDefectAlarmSeverity		DisplayString,
				ommp81PlusGfpCsfSignalFailAlarmSeverity				DisplayString,
				ommp81PlusGfpCsfLinkFailAlarmSeverity				DisplayString,
				ommp81PlusGfpCoreHeaderErrorAlarmSeverity			DisplayString,
				ommp81PlusGfpExtentionHeaderErrorAlarmSeverity			DisplayString,
				ommp81PlusConfigurationTableRowStatus				RowStatus
			}
		
	ommp81PlusCardSoftwareUpgrade OBJECT-TYPE		 
		SYNTAX  DisplayString
		MAX-ACCESS read-write
		STATUS current
		DESCRIPTION
			"Valid only as SET command.
			This property upgrades the software of the OMMP81-PLUS card
			It takes the path of the software release as
			a value
			-----------------------------
			ommp81PlusInterfaceNumber: 0
			-----------------------------
			Values:
			eg: /root/home/rel-2.0.0.tar.gz
			-----------------------------"
		::= { ommp81PlusConfigurationEntry 1 }

	ommp81PlusCardSignalMonitorState OBJECT-TYPE		 
		SYNTAX  INTEGER
		MAX-ACCESS read-write
		STATUS current
		DESCRIPTION
			"This property sets or gets the card's signal
			monitoring state. Disabling card signal monitoring 
			will not provide any signal alarms and performances
			information to the user.
			-----------------------------
			ommp81PlusInterfaceNumber: 0
			-----------------------------
			Values:
			1 - Card Signal Monitoring is enabled
			0 - Card Signal Monitoring is disabled
			-----------------------------"
		::= { ommp81PlusConfigurationEntry 2 }

	ommp81PlusCardOpticalMonitorState OBJECT-TYPE		 
		SYNTAX  INTEGER
		MAX-ACCESS read-write
		STATUS current
		DESCRIPTION
			"This property sets or gets the card's optical
			monitoring state. Disabling card signal monitoring 
			will not provide any signal alarms and performances
			information to the user.
			-----------------------------
			ommp81PlusInterfaceNumber: 0
			-----------------------------
			Values:
			1 - Card Optical Monitoring is enabled
			0 - Card Optical Monitoring is disabled
			-----------------------------"
		::= { ommp81PlusConfigurationEntry 3 }

	ommp81PlusCardSoftReset OBJECT-TYPE		 
		SYNTAX  INTEGER
		MAX-ACCESS read-write
		STATUS current
		DESCRIPTION
			"Valid only as a SET command.
			Reboots the Card, Reconfigures the Card 
			i.e All Configuration Parameter	like Laser State,
			Traffic configuration, Loopback, FEC, optical and 
			signal thresholds, switching mode,
			user choice of line path, auto-negotiation, 
			TTI messages will be restored to previous state
			-----------------------------
			ommp81PlusInterfaceNumber: 0
			-----------------------------
			Values:
			Dont care, any value
			eg: 0
			-----------------------------"
		::= { ommp81PlusConfigurationEntry 4 }

	ommp81PlusCardFactoryReset OBJECT-TYPE		 
		SYNTAX  INTEGER
		MAX-ACCESS read-write
		STATUS current
		DESCRIPTION
			"Valid only as a SET command.
			Sets the Card To Factory Default State
			i.e All User Configuration Parameters like Laser State,
			Traffic configuration, Loopback, FEC, optical and 
			signal thresholds, switching mode,
			user choice of line path, auto-negotiation, TTI messages
			will be set to default state
			-----------------------------
			ommp81PlusInterfaceNumber: 0
			-----------------------------
			Values:
			Dont care, any value
			eg: 0
			-----------------------------"
		::= { ommp81PlusConfigurationEntry 5 }

	ommp81PlusCardAccessStatus OBJECT-TYPE		 
		SYNTAX  INTEGER
		MAX-ACCESS read-write
		STATUS current
		DESCRIPTION
			"This property will tell whether the card is 
			accessible from EMS/LCT or not. Turning off the
			accessbility to the card, will not allow the user
			to access any configuration, alarm or performance
			of the card and also turns off fast alarm
			triggering, global alarm led indication
			-----------------------------
			ommp81PlusInterfaceNumber: 0
			-----------------------------
			Values:
			1 - Card is accessible from EMS/LCT
			0 - Card is inaccessible from EMS/LCT
			-----------------------------"
		::= { ommp81PlusConfigurationEntry 6 }
		
	ommp81PlusSyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that ilarticular server. 
					If we are not providing NTP server IP address 
					then the system will be synced with the NTP server 
					which is already been registered with card. 
					If both are absent then error message will be returned
					-----------------------------
						Interface : 0
					-----------------------------
						If we want to provide NTP server IP address then
						Value should be a valid IP address as shown below
						: 192.168.21.25
						
						If we don't want to provide NTP server address then no
						need to pass any value. 
					---------------------------"
  						
  		::= { ommp81PlusConfigurationEntry 7 }
  		
  	ommp81PlusSyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 192.168.21.25
							
						If we don't want to provide NTP server address, then no
						need to ilass any value. 
						---------------------------"
  						
  		::= { ommp81PlusConfigurationEntry 8 }
  		
  	ommp81PlusSyncRtcWithSystemTime	 OBJECT-TYPE
		SYNTAX  		DisplayString
  		MAX-ACCESS  	read-write
  		STATUS  		current
  		DESCRIPTION	 	" when we want to manually sync the time value
  						present in RTC with the time value in linux kernel
  						we can use this OID. With this set operation, 
  						the time available with linux kernel will be updated
  						into RTC. It is not required to provide any value for 
  						this operation"
  						
  		::= { ommp81PlusConfigurationEntry 9 }
  		
  	ommp81PlusUpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2017-10-31 15:20:44
						---------------------------"
						
  		::= { ommp81PlusConfigurationEntry 10 }
  		
  	ommp81PlusUpdateGivenTimeIntoRtc	 OBJECT-TYPE
		SYNTAX  		DisplayString
  		MAX-ACCESS  	read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD H:M:S
						
						Example: 2017-10-31 15:20:44
						---------------------------"
						
  		::= { ommp81PlusConfigurationEntry 11 }
  		
  	ommp81PlusSystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { ommp81PlusConfigurationEntry 12 }

--	ommp81PlusTrafficConfiguration OBJECT-TYPE		 
--		SYNTAX  DisplayString
--		MAX-ACCESS read-write
--		STATUS current
--		DESCRIPTION
--			"Set or get Traffic configuration for all ports
--			-----------------------------
--			ommp81PlusInterfaceNumber: 0
--			-----------------------------			
--			Value: 
--			At any instant to perform traffic configuration operation,
--			the traffic configuration values need to be passed for
--			all 8 client ports. The following are the traffic
--			configuration values, followed by an example:
--			00 - Un-configure 
--			01 - STM16
--			02 - STM4
--			03 - STM1
--			04 - GE-GFP-T
--			05 - GE-GFP-F
--			06 - FE-GFP-T
--			07 - FE-GFP-F
--			08 - FC-100
--			09 - FC-200
--			10 - OTU-1
--			eg: To set STM16, GE-GFP-F for CLIENT-1, CLIENT-2
--			repectively, the following value needs to be passed,
--			1,2,0,0,0,0,0,0 as a string in which the position
--			represents the port number
--			-----------------------------"
--		::= { ommp81PlusConfigurationEntry 41 }
		
	ommp81PlusTrafficConfiguration OBJECT-TYPE		 
		SYNTAX  INTEGER
		MAX-ACCESS read-write
		STATUS current
		DESCRIPTION
			"Set or get Traffic configuration for all ports
			-----------------------------
			ommp81PlusInterfaceNumber:
			1 to 8 - CLIENT-1 to CLIENT-8
			-----------------------------			
			Value: 
			00 - Un-configure 
			01 - STM16
			02 - STM4
			03 - STM1
			04 - GE-GFP-T
			05 - GE-GFP-F
			06 - FE-GFP-T
			07 - FE-GFP-F
			08 - FC-100
			09 - FC-200
			10 - OTU-1
			-----------------------------"
		::= { ommp81PlusConfigurationEntry 41 }

	ommp81PlusLoopbackState OBJECT-TYPE		 
		SYNTAX  INTEGER
		MAX-ACCESS read-write
		STATUS current
		DESCRIPTION
			"Set or get the loopback state for the
			requested port
			-----------------------------
			ommp81PlusInterfaceNumber:
			1 to 8 - CLIENT-1 to CLIENT-8
			9 - LINE-1
			-----------------------------
			Values: 
			00 - No Loopback   
			01 - Near End Loopback
			02 - Far End Loopback
			-----------------------------"
		::= { ommp81PlusConfigurationEntry 42 }

	ommp81PlusPortSignalMonitorState OBJECT-TYPE		 
		SYNTAX  INTEGER
		MAX-ACCESS read-write
		STATUS current
		DESCRIPTION
			"This property sets or gets the port's signal
			monitoring state. Disabling port signal monitoring 
			will not provide any signal alarms and performances
			information to the user.
			-----------------------------
			ommp81PlusInterfaceNumber:
			1 to 8 - CLIENT-1 to CLIENT-8
			9 - LINE-1
			-----------------------------
			Values:
			1 - Port Signal Monitoring is enabled
			0 - Port Signal Monitoring is disabled
			-----------------------------"
		::= { ommp81PlusConfigurationEntry 43 }

	ommp81PlusPortOpticalMonitorState OBJECT-TYPE		 
		SYNTAX  INTEGER
		MAX-ACCESS read-write
		STATUS current
		DESCRIPTION
			"This property sets or gets the port's optical
			monitoring state. Disabling port optical monitoring 
			will not provide any optical alarms and performances
			information to the user.
			-----------------------------
			ommp81PlusInterfaceNumber:
			1 to 8 - CLIENT-1 to CLIENT-8
			9 - LINE-1
			-----------------------------
			Values:
			1 - Port Optical Monitoring is enabled
			0 - Port Optical Monitoring is disabled
			-----------------------------"
		::= { ommp81PlusConfigurationEntry 44 }

	ommp81PlusClearSignalPerformance OBJECT-TYPE		 
		SYNTAX  INTEGER
		MAX-ACCESS read-write
		STATUS current
		DESCRIPTION
			"Valid only as a SET command.
			Clears signal performance for the requested port
			-----------------------------
			ommp81PlusInterfaceNumber:
			1 to 8 - CLIENT-1 to CLIENT-8
			9 - LINE-1
			-----------------------------
			Values:
			Dont care, any value
			eg: 0
			-----------------------------"
		::= { ommp81PlusConfigurationEntry 45 }

	ommp81PlusAlsState OBJECT-TYPE		 
		SYNTAX  INTEGER
		MAX-ACCESS read-write
		STATUS current
		DESCRIPTION
			"Set the Automatic Laser Switching(ALS) mode for
			for requested port. Based on the RX LOS state of the
			port, the transmit LASER state will be controlled
			according to the algorithm defined for ALS in
			ITUT 664 Standard
			-----------------------------
			ommp81PlusInterfaceNumber:
			1 to 8 - CLIENT-1 to CLIENT-8
			9 - LINE-1
			-----------------------------
			Values: 
			1 - Enable ALS state
			0 - Disable ALS state
			-----------------------------" 
		::= { ommp81PlusConfigurationEntry 46 }

	ommp81PlusAlsPulseRepetitionTime OBJECT-TYPE		 
		SYNTAX  INTEGER
		MAX-ACCESS read-write
		STATUS current
		DESCRIPTION
			"Pulse repetition time is the time for automatic 
			restart of XFP LASER once the ALS algorithm starts.
			-----------------------------
			ommp81PlusInterfaceNumber:
			1 to 8 - CLIENT-1 to CLIENT-8
			9 - LINE-1
			-----------------------------
			Values: 
			100 seconds to 300 seconds
			-----------------------------"
		::= { ommp81PlusConfigurationEntry 47 }

	ommp81PlusOtuFecConfiguration OBJECT-TYPE		 
		SYNTAX  INTEGER
		MAX-ACCESS read-write
		STATUS current
		DESCRIPTION
			"Set or Get FEC type for requested port configured with
			 OTU2/OTU1 traffic.  
			-----------------------------
			ommp81PlusInterfaceNumber:
			1 to 8 - CLIENT-1 to CLIENT-8
			9 - LINE-1
			-----------------------------
			Values: 
			00 - Zero FEC 
			01 - Reed-Solomon GFEC
			03 - UFEC(I.7 FEC, applicable for line port only)
			-----------------------------"
		::= { ommp81PlusConfigurationEntry 61 }

	ommp81PlusOtuSignalFailThreshold OBJECT-TYPE		 
		SYNTAX  INTEGER
		MAX-ACCESS read-write
		STATUS current
		DESCRIPTION
			"Set or Get SM Signal Failure 
			Threshold value for the requested port configured with 
			OTU2/OTU1 traffic.
			-----------------------------
			ommp81PlusInterfaceNumber:
			1 to 8 - CLIENT-1 to CLIENT-8
			9 - LINE-1
			-----------------------------
			Values: 
			03 - 1.E -03
			04 - 1.E -04
			05 - 1.E -05
			-----------------------------" 
		::= { ommp81PlusConfigurationEntry 62 }

	ommp81PlusOtuSignalDegradeThreshold OBJECT-TYPE		 
		SYNTAX  INTEGER
		MAX-ACCESS read-write
		STATUS current
		DESCRIPTION
			"Set or Get SM Signal Degrade 
			Threshold value for the requested port configured with 
			OTU2/OTU1 traffic.
			-----------------------------
			ommp81PlusInterfaceNumber:
			1 to 8 - CLIENT-1 to CLIENT-8
			9 - LINE-1
			-----------------------------
			Values:
			06 - 1.E -06
			07 - 1.E -07
			08 - 1.E -08
			09 - 1.E -09
			10 - 1.E -10(for line only)
			-----------------------------"
		::= { ommp81PlusConfigurationEntry 63 }

	ommp81PlusOtuAlarmIndicationSignalAlarmInsertion OBJECT-TYPE		 
		SYNTAX  INTEGER
		MAX-ACCESS read-write
		STATUS current
		DESCRIPTION
			"Inserts OTU-AIS maitainance signal for the requested
			port configured with OTU2/OTU1 traffic.
			-----------------------------
			ommp81PlusInterfaceNumber:
			1 to 8 - CLIENT-1 to CLIENT-8
			9 - LINE-1
			-----------------------------
			Values: 
			1 - Enable Insertion
			0 - Disable Insertion  
			-----------------------------"
		::= { ommp81PlusConfigurationEntry 64 }

	ommp81PlusOtuSapiTransmitTraceMessage OBJECT-TYPE
		SYNTAX DisplayString
		MAX-ACCESS read-write
		STATUS current
		DESCRIPTION
			"Set or get the 15 characters SAPI Transmit TTI message
			which is put into the outgoing OTU2/OTU1 frame. 
			-----------------------------
			ommp81PlusInterfaceNumber:
			1 to 8 - CLIENT-1 to CLIENT-8
			9 - LINE-1
			-----------------------------
			Values:
			eg: 123451234512345
			-----------------------------" 
		::= { ommp81PlusConfigurationEntry 65 }

	ommp81PlusOtuDapiTransmitTraceMessage OBJECT-TYPE
		SYNTAX DisplayString
		MAX-ACCESS read-write
		STATUS current
		DESCRIPTION
			"Set or get the 15 characters DAPI Transmit TTI message
			which is put into the outgoing OTU2/OTU1 frame. 
			-----------------------------
			ommp81PlusInterfaceNumber:
			1 to 8 - CLIENT-1 to CLIENT-8
			9 - LINE-1
			-----------------------------
			Values:
			eg: 123451234512345
			-----------------------------" 
		::= { ommp81PlusConfigurationEntry 66 }
		
	ommp81PlusOtuOperatorSpecificTransmitTraceMessage OBJECT-TYPE
		SYNTAX DisplayString
		MAX-ACCESS read-write
		STATUS current
		DESCRIPTION
			"Set or get the 32 characters Operator Specific Transmit
			TTI message which is put into the outgoing OTU2/OTU1
			frame. 
			-----------------------------
			ommp81PlusInterfaceNumber:
			1 to 8 - CLIENT-1 to CLIENT-8
			9 - LINE-1
			-----------------------------
			Values:
			eg: 12345123451234512345123451234500
			-----------------------------" 
		::= { ommp81PlusConfigurationEntry 67 }
		
	ommp81PlusOtuSapiExpectedTraceMessage OBJECT-TYPE
		SYNTAX DisplayString
		MAX-ACCESS read-write
		STATUS current
		DESCRIPTION
			"15 characters SM SAPI Expected TTI message - Message
			set here is used for comparison with the message present
			in SM SAPI field of the incoming OTU2/OTU1 frames.
			-----------------------------
			ommp81PlusInterfaceNumber:
			1 to 8 - CLIENT-1 to CLIENT-8
			9 - LINE-1
			-----------------------------
			Values:
			eg: 123451234512345
			-----------------------------" 
		::= { ommp81PlusConfigurationEntry 68 }
		
	ommp81PlusOtuDapiExpectedTraceMessage OBJECT-TYPE
		SYNTAX DisplayString
		MAX-ACCESS read-write
		STATUS current
		DESCRIPTION
			"15 characters SM DAPI Expected TTI message - Message
			set here is used for comparison with the message present
			in SM DAPI field of the incoming OTU2/OTU1 frames.
			-----------------------------
			ommp81PlusInterfaceNumber:
			1 to 8 - CLIENT-1 to CLIENT-8
			9 - LINE-1
			-----------------------------
			Values:
			eg: 123451234512345
			-----------------------------" 
		::= { ommp81PlusConfigurationEntry 69 }

	ommp81PlusOtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU2/OTU1 frames.
			-----------------------------
			ommp81PlusInterfaceNumber:
			1 to 8 - CLIENT-1 to CLIENT-8
			9 - LINE-1
			-----------------------------
			Values:
			eg: 12345123451234512345123451234500
			-----------------------------" 
		::= { ommp81PlusConfigurationEntry 70 }

	ommp81PlusOtuSapiReceivedTraceMessage OBJECT-TYPE
		SYNTAX DisplayString
		MAX-ACCESS read-only
		STATUS current
		DESCRIPTION
			"Gets the 15 characters SAPI TTI message
			which is extracted from the incoming OTU2/OTU1
			data stream.
			-----------------------------
			ommp81PlusInterfaceNumber:
			1 to 8 - CLIENT-1 to CLIENT-8
			9 - LINE-1
			-----------------------------
			Values:
			eg: 123451234512345
			-----------------------------" 
		::= { ommp81PlusConfigurationEntry 71 }

	ommp81PlusOtuDapiReceivedTraceMessage OBJECT-TYPE
		SYNTAX DisplayString
		MAX-ACCESS read-only
		STATUS current
		DESCRIPTION
			"Gets the 15 characters DAPI TTI message
			which is extracted from the incoming OTU2/OTU1 data
			stream.
			-----------------------------
			ommp81PlusInterfaceNumber:
			1 to 8 - CLIENT-1 to CLIENT-8
			9 - LINE-1
			-----------------------------
			Values:
			eg: 123451234512345
			-----------------------------" 
		::= { ommp81PlusConfigurationEntry 72 }
		
	ommp81PlusOtuOperatorSpecificReceivedTraceMessage OBJECT-TYPE
		SYNTAX DisplayString
		MAX-ACCESS read-only
		STATUS current
		DESCRIPTION
			"Gets the 32 characters DAPI TTI message
			which is extracted from the incoming OTU2/OTU1 data
			stream. 
			-----------------------------
			ommp81PlusInterfaceNumber:
			1 to 8 - CLIENT-1 to CLIENT-8
			9 - LINE-1
			-----------------------------
			Values:
			eg: 12345123451234512345123451234500
			-----------------------------" 
		::= { ommp81PlusConfigurationEntry 73 }

	ommp81PlusOduSignalFailThreshold OBJECT-TYPE		 
		SYNTAX  INTEGER
		MAX-ACCESS read-write
		STATUS current
		DESCRIPTION
			"Set or Get PM Signal Failure 
			Threshold value for the requested port configured with 
			OTU2/OTU1 traffic.
			-----------------------------
			ommp81PlusInterfaceNumber:
			1 to 8 - CLIENT-1 to CLIENT-8
			9 - LINE-1
			-----------------------------
			Values: 
			03 - 1.E -03
			04 - 1.E -04
			05 - 1.E -05
			-----------------------------" 
		::= { ommp81PlusConfigurationEntry 81 }

	ommp81PlusOduSignalDegradeThreshold OBJECT-TYPE		 
		SYNTAX  INTEGER
		MAX-ACCESS read-write
		STATUS current
		DESCRIPTION
			"Set or Get PM Signal Degrade 
			Threshold value for the requested port configured with 
			OTU2/OTU1 traffic.
			-----------------------------
			ommp81PlusInterfaceNumber:
			1 to 8 - CLIENT-1 to CLIENT-8
			9 - LINE-1
			-----------------------------
			Values: 
			06 - 1.E -06
			07 - 1.E -07
			08 - 1.E -08
			09 - 1.E -09
			10 - 1.E -10(for line only)
			-----------------------------" 
		::= { ommp81PlusConfigurationEntry 82 }

	ommp81PlusOduAlarmIndicationSignalAlarmInsertion OBJECT-TYPE		 
		SYNTAX  INTEGER
		MAX-ACCESS read-write
		STATUS current
		DESCRIPTION
			"Inserts ODU-AIS maintenance signal for the requested 
			port configured with OTU2/OTU1 traffic.
			-----------------------------
			ommp81PlusInterfaceNumber:
			1 to 8 - CLIENT-1 to CLIENT-8
			9 - LINE-1
			-----------------------------
			Values: 
			1 - Enable Insertion
			0 - Disable Insertion  
			-----------------------------"
		::= { ommp81PlusConfigurationEntry 83 }

	ommp81PlusOduLockedDefectAlarmInsertion OBJECT-TYPE		 
		SYNTAX  INTEGER
		MAX-ACCESS read-write
		STATUS current
		DESCRIPTION
			"Inserts ODU-LCK maintenance signal for the requested 
			port configured with OTU2/OTU1 traffic.
			-----------------------------
			ommp81PlusInterfaceNumber:
			1 to 8 - CLIENT-1 to CLIENT-8
			9 - LINE-1
			-----------------------------
			Values: 
			1 - Enable Insertion
			0 - Disable Insertion  
			-----------------------------"
		::= { ommp81PlusConfigurationEntry 84 }

	ommp81PlusOduOpenConnectionIndicationAlarmInsertion OBJECT-TYPE		 
		SYNTAX  INTEGER
		MAX-ACCESS read-write
		STATUS current
		DESCRIPTION
			"Inserts ODU-OCI maintenance signal for the requested 
			port configured with OTU2/OTU1 traffic.
			-----------------------------
			ommp81PlusInterfaceNumber:
			1 to 8 - CLIENT-1 to CLIENT-8
			9 - LINE-1
			-----------------------------
			Values: 
			1 - Enable Insertion
			0 - Disable Insertion  
			-----------------------------"
		::= { ommp81PlusConfigurationEntry 85 }

	ommp81PlusOduSapiTransmitTraceMessage OBJECT-TYPE
		SYNTAX DisplayString
		MAX-ACCESS read-write
		STATUS current
		DESCRIPTION
			"Set or get the 15 characters SAPI Transmit TTI message
			which is put into the outgoing OTU2/OTU1
			frame at the PM level. 
			-----------------------------
			ommp81PlusInterfaceNumber:
			1 to 8 - CLIENT-1 to CLIENT-8
			9 - LINE-1
			-----------------------------
			Values:
			eg: 123451234512345
			-----------------------------" 
		::= { ommp81PlusConfigurationEntry 86 }
		
	ommp81PlusOduDapiTransmitTraceMessage OBJECT-TYPE
		SYNTAX DisplayString
		MAX-ACCESS read-write
		STATUS current
		DESCRIPTION
			"Set or get the 15 characters DAPI Transmit TTI message
			which is put into the outgoing OTU2/OTU1
			frame at the PM level. 
			-----------------------------
			ommp81PlusInterfaceNumber:
			1 to 8 - CLIENT-1 to CLIENT-8
			9 - LINE-1
			-----------------------------
			Values:
			eg: 123451234512345
			-----------------------------" 
		::= { ommp81PlusConfigurationEntry 87 }
		
	ommp81PlusOduOperatorSpecificTransmitTraceMessage OBJECT-TYPE
		SYNTAX DisplayString
		MAX-ACCESS read-write
		STATUS current
		DESCRIPTION
			"Set or get the 32 characters Operator Specific Transmit
			TTI message which is put into the outgoing OTU2/OTU1
			frame at the PM level. 
			-----------------------------
			ommp81PlusInterfaceNumber:
			1 to 8 - CLIENT-1 to CLIENT-8
			9 - LINE-1
			-----------------------------
			Values:
			eg: 12345123451234512345123451234500
			-----------------------------" 
		::= { ommp81PlusConfigurationEntry 88 }
		
	ommp81PlusOduSapiExpectedTraceMessage OBJECT-TYPE
		SYNTAX DisplayString
		MAX-ACCESS read-write
		STATUS current
		DESCRIPTION
			"15 characters PM SAPI Expected TTI message - Message
			set here is used for comparison with the message present
			in PM SAPI field of the incoming OTU2/OTU1 frames.
			-----------------------------
			ommp81PlusInterfaceNumber:
			1 to 8 - CLIENT-1 to CLIENT-8
			9 - LINE-1
			-----------------------------
			Values:
			eg: 123451234512345
			-----------------------------" 
		::= { ommp81PlusConfigurationEntry 89 }

	ommp81PlusOduDapiExpectedTraceMessage OBJECT-TYPE
		SYNTAX DisplayString
		MAX-ACCESS read-write
		STATUS current
		DESCRIPTION
			"15 characters PM DAPI Expected TTI message - Message
			set here is used for comparison with the message present
			in PM DAPI field of the incoming OTU2/OTU1 frames.
			-----------------------------
			ommp81PlusInterfaceNumber:
			1 to 8 - CLIENT-1 to CLIENT-8
			9 - LINE-1
			-----------------------------
			Values:
			eg: 123451234512345
			-----------------------------" 
		::= { ommp81PlusConfigurationEntry 90 }
		
	ommp81PlusOduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU2/OTU1 frames.
			-----------------------------
			ommp81PlusInterfaceNumber:
			1 to 8 - CLIENT-1 to CLIENT-8
			9 - LINE-1
			-----------------------------
			Values:
			eg: 12345123451234512345123451234500
			-----------------------------" 
		::= { ommp81PlusConfigurationEntry 91 }

	ommp81PlusOduSapiReceivedTraceMessage OBJECT-TYPE
		SYNTAX DisplayString
		MAX-ACCESS read-only
		STATUS current
		DESCRIPTION
			"Gets the 15 characters SAPI TTI message
			which is extracted from the incoming OTU2/OTU1 data
			stream.
			-----------------------------
			ommp81PlusInterfaceNumber:
			1 to 8 - CLIENT-1 to CLIENT-8
			9 - LINE-1
			-----------------------------
			Values:
			eg: 123451234512345
			-----------------------------" 
		::= { ommp81PlusConfigurationEntry 92 }

	ommp81PlusOduDapiReceivedTraceMessage OBJECT-TYPE
		SYNTAX DisplayString
		MAX-ACCESS read-only
		STATUS current
		DESCRIPTION
			"Gets the 15 characters DAPI TTI message
			which is extracted from the incoming OTU2/OTU1
			data stream.
			-----------------------------
			ommp81PlusInterfaceNumber:
			1 to 8 - CLIENT-1 to CLIENT-8
			9 - LINE-1
			-----------------------------
			Values:
			eg: 123451234512345
			-----------------------------" 
		::= { ommp81PlusConfigurationEntry 93 }
		
	ommp81PlusOduOperatorSpecificReceivedTraceMessage OBJECT-TYPE
		SYNTAX DisplayString
		MAX-ACCESS read-only
		STATUS current
		DESCRIPTION
			"Gets the 32 characters DAPI TTI message
			which is extracted from the incoming OTU2/OTU1
			data stream.
			-----------------------------
			ommp81PlusInterfaceNumber:
			1 to 8 - CLIENT-1 to CLIENT-8
			9 - LINE-1
			-----------------------------
			Values:
			eg: 12345123451234512345123451234500
			-----------------------------" 
		::= { ommp81PlusConfigurationEntry 94 }

	ommp81PlusOpuTransmitPayloadType OBJECT-TYPE
		SYNTAX INTEGER
		MAX-ACCESS read-only
		STATUS current
		DESCRIPTION
			"A one-byte payload type signal is defined in the PSI[0]
			byte of the payload structure identifier to indicate the
			composition of the OPUk signal. Gets the payload type
			that is put into the outgoing OTU2/OTU1 datastream.
			-----------------------------
			ommp81PlusInterfaceNumber:
			1 to 8 - CLIENT-1 to CLIENT-8
			9 - LINE-1
			-----------------------------
			Values:
			eg: 20
			-----------------------------" 
		::= { ommp81PlusConfigurationEntry 95 }

	ommp81PlusOpuReceivedPayloadType OBJECT-TYPE		 
		SYNTAX  INTEGER
		MAX-ACCESS read-only
		STATUS current
		DESCRIPTION
			"A one-byte payload type signal is defined in the PSI[0]
			byte of the payload structure identifier to indicate the
			composition of the OPUk signal. Gets the payload type
			extracted from the incoming OTU2/OTU1 datastream.
			-----------------------------
			ommp81PlusInterfaceNumber:
			1 to 8 - CLIENT-1 to CLIENT-8
			9 - LINE-1
			-----------------------------
			Values:
			eg: 20
			-----------------------------"
		::= { ommp81PlusConfigurationEntry 96 }
		
	ommp81PlusSdhMsB2ExcessiveErrorThreshold OBJECT-TYPE		 
		SYNTAX  INTEGER
		MAX-ACCESS read-write
		STATUS current
		DESCRIPTION
			"Set or Get B2 Signal Failure Threshold value for the 
			requested port configured with STM-1/4/16 traffic.
			-----------------------------
			ommp81PlusInterfaceNumber:
			1 to 8 - CLIENT-1 to CLIENT-8
			-----------------------------
			Values:
			03 - 1.E -03
			04 - 1.E -04
			05 - 1.E -05
			-----------------------------"
		::= { ommp81PlusConfigurationEntry 101 }

	ommp81PlusSdhMsB2SignalDegradeThreshold OBJECT-TYPE		 
		SYNTAX  INTEGER
		MAX-ACCESS read-write
		STATUS current
		DESCRIPTION
			"Set or Get B2 Signal Degrade Threshold value for the 
			requested port configured with STM-1/4/16 traffic.
			-----------------------------
			ommp81PlusInterfaceNumber:
			1 to 8 - CLIENT-1 to CLIENT-8
			-----------------------------
			Values:
			06 - 1.E -06
			07 - 1.E -07
			08 - 1.E -08
			09 - 1.E -09
			10 - 1.E -10
			11 - 1.E -11
			-----------------------------"
		::= { ommp81PlusConfigurationEntry 102 }

	ommp81PlusEthernetAutoNegotiation OBJECT-TYPE		 
		SYNTAX  INTEGER
		MAX-ACCESS read-write
		STATUS current
		DESCRIPTION
			"Set or Get the Auto-negotiation mode for the
			requested port configured with GE-GFP-F/GE-GFP-T traffic.
			Enabling auto negotiation will automatically establish
			the link between link-partners on basis of speed,
			flow-control and duplexity.
			If disabled, the link status between the link-partners
			cannot be restored after the link is broken.
			-----------------------------
			ommp81PlusInterfaceNumber:
			1 to 8 - CLIENT-1 to CLIENT-8
			-----------------------------
			Value:
			1 - Enable Auto-Negotiation
			0 - Disable Auto-negotiation
			-----------------------------"
		::= { ommp81PlusConfigurationEntry 111 }
		
	ommp81PlusCalibrateHyphyXfiSerdes OBJECT-TYPE		 
		SYNTAX  INTEGER
		MAX-ACCESS read-write
		STATUS current
		DESCRIPTION
			"Valid only as SET command.
			For every card which is come freshly manufactured from
			the factory, the XFI serdes of the line ports need to
			be calibrated in hyphy w.r.t to OTU2 signal, since the
			serdes in all the mapper chips will not be the same.
			-----------------------------
			ommp81PlusInterfaceNumber:0
			-----------------------------
			Values:
			9 - LINE-1
			-----------------------------"
		::= { ommp81PlusConfigurationEntry 121 }			

	ommp81PlusTunableXfpLaserWavelength OBJECT-TYPE		 
		SYNTAX  INTEGER
		MAX-ACCESS read-write
		STATUS current
		DESCRIPTION
			"Set or Get the XFP wavelength for the requested port
			-----------------------------
			ommp81PlusInterfaceNumber:
			9 - LINE-1
			-----------------------------
			Values:
			eg: 1529.944
			-----------------------------"
		::= { ommp81PlusConfigurationEntry 131 }

	ommp81PlusTunableXfpLaserChannelNumber OBJECT-TYPE		 
		SYNTAX  INTEGER
		MAX-ACCESS read-write
		STATUS current
		DESCRIPTION
			"Set or Get the XFP Channel Number for the the requested
			port
			-----------------------------
			ommp81PlusInterfaceNumber:
			9 - LINE-1
			-----------------------------
			Values:
			eg: 10
			-----------------------------"
		::= { ommp81PlusConfigurationEntry 132 }

	ommp81PlusXfpLaserState OBJECT-TYPE		 
		SYNTAX  INTEGER
		MAX-ACCESS read-write
		STATUS current
		DESCRIPTION
			"Set or Get the XFP LASER state for the the requested
			port
			-----------------------------
			ommp81PlusInterfaceNumber:
			9 - LINE-1
			-----------------------------
			Values: 
			00 - Laser OFF
			01 - Laser ON
			-----------------------------"
		::= { ommp81PlusConfigurationEntry 133 }

	ommp81PlusXfpReset OBJECT-TYPE		 
		SYNTAX  INTEGER
		MAX-ACCESS read-write
		STATUS current
		DESCRIPTION
			"Valid only as a SET command.
			Resets the XFP.
			-----------------------------
			ommp81PlusInterfaceNumber:
			9 - LINE-1
			-----------------------------
			Values: 
			Dont care, any value
			eg: 0
			-----------------------------"
		::= { ommp81PlusConfigurationEntry 134 }

	ommp81PlusXfpPowerDownMode OBJECT-TYPE		 
		SYNTAX  INTEGER
		MAX-ACCESS read-write
		STATUS current
		DESCRIPTION
			"Valid only as a SET command.
			Sets the XFP in the Power Down mode i.e. low power 
			consumption mode.
			-----------------------------
			ommp81PlusInterfaceNumber:
			9 - LINE-1
			-----------------------------
			Values: 
			01 - power down XFP
			-----------------------------"
		::= { ommp81PlusConfigurationEntry 135 }

	ommp81PlusXfpLineLoopback OBJECT-TYPE		 
		SYNTAX  INTEGER
		MAX-ACCESS read-write
		STATUS current
		DESCRIPTION
			"Set or Get line loopback in XFP			
			----------------------------
			ommp81PlusInterfaceNumber:
			9 - LINE-1
			-----------------------------
			Values: 
			1 - Enable XFP Line Loopback
			0 - Disable XFP Line Loopback
			-----------------------------"
		::= { ommp81PlusConfigurationEntry 136 }

	ommp81PlusXfpXfiLoopback OBJECT-TYPE		 
		SYNTAX  INTEGER
		MAX-ACCESS read-write
		STATUS current
		DESCRIPTION
			"Set or Get Xfi loopback in XFP			
			----------------------------
			ommp81PlusInterfaceNumber:
			9 - LINE-1
			-----------------------------
			Values: 
			1 - Enable XFP Xfi Loopback
			0 - Disable XFP Xfi Loopback
			-----------------------------"
		::= { ommp81PlusConfigurationEntry 137 }

	ommp81PlusXfpAmplitudeThresholdOfReceiverForFecControl OBJECT-TYPE		 
		SYNTAX  INTEGER
		MAX-ACCESS read-write
		STATUS current
		DESCRIPTION
			"Set or Get amplitude threshold of receiver for FEC control			
			----------------------------
			ommp81PlusInterfaceNumber:
			9 - LINE-1
			-----------------------------
			Values: 
			eg: Reserved for further study
			-----------------------------"
		::= { ommp81PlusConfigurationEntry 138 }

	ommp81PlusXfpPhaseInEyeDiagramForFecControl OBJECT-TYPE		 
		SYNTAX  INTEGER
		MAX-ACCESS read-write
		STATUS current
		DESCRIPTION
			"Set or Get XFP phase in eye diagram for FEC control			
			----------------------------
			ommp81PlusInterfaceNumber:
			9 - LINE-1
			-----------------------------
			Values: 
			eg: Reserved for further study
			-----------------------------"
		::= { ommp81PlusConfigurationEntry 139 }

	ommp81PlusXfpSystemReportingBer OBJECT-TYPE		 
		SYNTAX  INTEGER
		MAX-ACCESS read-write
		STATUS current
		DESCRIPTION
			"Set or Get XFP system reporting BER			
			----------------------------
			ommp81PlusInterfaceNumber:
			9 - LINE-1
			-----------------------------
			Values: 
			eg: Reserved for further study
			-----------------------------"
		::= { ommp81PlusConfigurationEntry 140 }

	ommp81PlusXfpHighTemperatureAlarmThreshold OBJECT-TYPE
		SYNTAX DisplayString
		MAX-ACCESS read-write
		STATUS current
		DESCRIPTION
			"Set or Get High Temperature Alarm Threshold
			(in degree celsius) for the requested port
			-----------------------------
			ommp81PlusInterfaceNumber:
			9 - LINE-1
			-----------------------------
			Values: 
			eg: 65 
			-----------------------------" 
		::= { ommp81PlusConfigurationEntry 141 }
		
	ommp81PlusXfpLowTemperatureAlarmThreshold OBJECT-TYPE
		SYNTAX DisplayString
		MAX-ACCESS read-write
		STATUS current
		DESCRIPTION
			"Set or Get Low Temperature Alarm Threshold
			(in degree celsius) for the requested port
			-----------------------------
			ommp81PlusInterfaceNumber:
			9 - LINE-1
			-----------------------------
			Values: 
			eg: 5 
			-----------------------------" 
		::= { ommp81PlusConfigurationEntry 142 }
		
	ommp81PlusXfpHighTemperatureWarningThreshold OBJECT-TYPE
		SYNTAX DisplayString
		MAX-ACCESS read-write
		STATUS current
		DESCRIPTION
			"Set or Get High Temperature Warning Threshold
			(in degree celsius) for the requested port
			-----------------------------
			ommp81PlusInterfaceNumber:
			9 - LINE-1
			-----------------------------
			Values: 
			eg: 60 
			-----------------------------"
		::= { ommp81PlusConfigurationEntry 143 }
		
	ommp81PlusXfpLowTemperatureWarningThreshold OBJECT-TYPE
		SYNTAX DisplayString
		MAX-ACCESS read-write
		STATUS current
		DESCRIPTION
			"Set or Get Low Temperature Warning Threshold
			(in degree celsius) for the requested port
			-----------------------------
			ommp81PlusInterfaceNumber:
			9 - LINE-1
			-----------------------------
			Values: 
			eg: 10 
			-----------------------------"
		::= { ommp81PlusConfigurationEntry 144 }

	ommp81PlusXfpHighBiasCurrentAlarmThreshold OBJECT-TYPE
		SYNTAX DisplayString
		MAX-ACCESS read-write
		STATUS current
		DESCRIPTION
			"Set or Get High Bias Current Alarm Threshold
			(in milli ampere) for the requested port
			-----------------------------
			ommp81PlusInterfaceNumber:
			9 - LINE-1
			-----------------------------
			Values:
			eg: 35.6
			-----------------------------"			
		::= { ommp81PlusConfigurationEntry 145 }
		
	ommp81PlusXfpLowBiasCurrentAlarmThreshold OBJECT-TYPE
		SYNTAX DisplayString
		MAX-ACCESS read-write
		STATUS current
		DESCRIPTION
			"Set or Get Low Bias Current Alarm Threshold
			(in milli ampere) for the requested port
			-----------------------------
			ommp81PlusInterfaceNumber:
			9 - LINE-1
			-----------------------------
			Values:
			eg: 31.1
			-----------------------------"
		::= { ommp81PlusConfigurationEntry 146 }
		
	ommp81PlusXfpHighBiasCurrentWarningThreshold OBJECT-TYPE
		SYNTAX DisplayString
		MAX-ACCESS read-write
		STATUS current
		DESCRIPTION
			"Set or Get High Bias Current Warning Threshold
			(in milli ampere) for the requested port
			-----------------------------
			ommp81PlusInterfaceNumber:
			9 - LINE-1
			-----------------------------
			Values:
			eg: 34.5
			-----------------------------"
		::= { ommp81PlusConfigurationEntry 147 }
		
	ommp81PlusXfpLowBiasCurrentWarningThreshold OBJECT-TYPE
		SYNTAX DisplayString
		MAX-ACCESS read-write
		STATUS current
		DESCRIPTION
			"Set or Get Low Bias Current Warning Threshold
			(in milli ampere) for the requested port
			-----------------------------
			ommp81PlusInterfaceNumber:
			9 - LINE-1
			-----------------------------
			Values:
			eg: 32.8
			-----------------------------"
		::= { ommp81PlusConfigurationEntry 148 }
		
	ommp81PlusXfpInputHighPowerAlarmThreshold OBJECT-TYPE
		SYNTAX DisplayString
		MAX-ACCESS read-write
		STATUS current
		DESCRIPTION
			"Set or Get Input High Power Alarm Threshold
			(in dbm) for the requested port
			-----------------------------
			ommp81PlusInterfaceNumber:
			9 - LINE-1
			-----------------------------
			Values:
			eg: -9.1
			-----------------------------"
		::= { ommp81PlusConfigurationEntry 149 }

	ommp81PlusXfpInputLowPowerAlarmThreshold OBJECT-TYPE
		SYNTAX DisplayString
		MAX-ACCESS read-write
		STATUS current
		DESCRIPTION
			"Set or Get Input Low Power Alarm Threshold
			(in dbm) for the requested port
			-----------------------------
			ommp81PlusInterfaceNumber:
			9 - LINE-1
			-----------------------------
			Values:
			eg: -35.6
			-----------------------------"
		::= { ommp81PlusConfigurationEntry 150 }
		
	ommp81PlusXfpInputHighPowerWarningThreshold OBJECT-TYPE
		SYNTAX DisplayString
		MAX-ACCESS read-write
		STATUS current
		DESCRIPTION
			"Set or Get Input High Power Warning Threshold
			(in dbm) for the requested port
			-----------------------------
			ommp81PlusInterfaceNumber:
			9 - LINE-1
			-----------------------------
			Values:
			eg: -11.2
			-----------------------------"
		::= { ommp81PlusConfigurationEntry 151 }
		
	ommp81PlusXfpInputLowPowerWarningThreshold OBJECT-TYPE
		SYNTAX DisplayString
		MAX-ACCESS read-write
		STATUS current
		DESCRIPTION
			"Set or Get Input Low Power Warning Threshold
			(in dbm) for the requested port
			-----------------------------
			ommp81PlusInterfaceNumber:
			9 - LINE-1
			-----------------------------
			Values:
			eg: -31.3
			-----------------------------"
		::= { ommp81PlusConfigurationEntry 152 }
		
	ommp81PlusXfpOutputHighPowerAlarmThreshold OBJECT-TYPE
		SYNTAX DisplayString
		MAX-ACCESS read-write
		STATUS current
		DESCRIPTION
			"Set or Get Output High Power Alarm Threshold
			(in dbm) for the requested port
			-----------------------------
			ommp81PlusInterfaceNumber:
			9 - LINE-1
			-----------------------------
			Values:
			eg: +2.0
			-----------------------------"
		::= { ommp81PlusConfigurationEntry 153 }

	ommp81PlusXfpOutputLowPowerAlarmThreshold OBJECT-TYPE
		SYNTAX DisplayString
		MAX-ACCESS read-write
		STATUS current
		DESCRIPTION
			"Set or Get Output Low Power Alarm Threshold
			(in dbm) for the requested port
			-----------------------------
			ommp81PlusInterfaceNumber:
			9 - LINE-1
			-----------------------------
			Values:
			eg: -3.5
			-----------------------------"
		::= { ommp81PlusConfigurationEntry 154 }
		
	ommp81PlusXfpOutputHighPowerWarningThreshold OBJECT-TYPE
		SYNTAX DisplayString
		MAX-ACCESS read-write
		STATUS current
		DESCRIPTION
			"Set or Get Output High Power Warning Threshold
			(in dbm) for the requested port
			-----------------------------
			ommp81PlusInterfaceNumber:
			9 - LINE-1
			-----------------------------
			Values:
			eg: +1.3
			-----------------------------"
		::= { ommp81PlusConfigurationEntry 155 }
		
	ommp81PlusXfpOutputLowPowerWarningThreshold OBJECT-TYPE
		SYNTAX DisplayString
		MAX-ACCESS read-write
		STATUS current
		DESCRIPTION
			"Set or Get Output Low Power Warning Threshold
			(in dbm) for the requested port
			-----------------------------
			ommp81PlusInterfaceNumber:
			9 - LINE-1
			-----------------------------
			Values:
			eg: -2.5
			-----------------------------"
		::= { ommp81PlusConfigurationEntry 156 }
		
	ommp81PlusXfpHighSupplyVoltageAlarmThreshold OBJECT-TYPE
		SYNTAX DisplayString
		MAX-ACCESS read-write
		STATUS current
		DESCRIPTION
			"Set or Get High Supply Voltage Alarm Threshold
			(in volts) for the requested port
			-----------------------------
			ommp81PlusInterfaceNumber:
			9 - LINE-1
			-----------------------------
			Values:
			eg: +3.3
			-----------------------------"
		::= { ommp81PlusConfigurationEntry 157 }

	ommp81PlusXfpLowSupplyVoltageAlarmThreshold OBJECT-TYPE
		SYNTAX DisplayString
		MAX-ACCESS read-write
		STATUS current
		DESCRIPTION
			"Set or Get Low Supply Voltage Alarm Threshold
			(in volts) for the requested port
			-----------------------------
			ommp81PlusInterfaceNumber:
			9 - LINE-1
			-----------------------------
			Values:
			eg: +3.0
			-----------------------------"
		::= { ommp81PlusConfigurationEntry 158 }
		
	ommp81PlusXfpHighSupplyVoltageWarningThreshold OBJECT-TYPE
		SYNTAX DisplayString
		MAX-ACCESS read-write
		STATUS current
		DESCRIPTION
			"Set or Get High Supply Voltage Warning Threshold
			(in volts) for the requested port
			-----------------------------
			ommp81PlusInterfaceNumber:
			9 - LINE-1
			-----------------------------
			Values:
			eg: +3.2
			-----------------------------"
		::= { ommp81PlusConfigurationEntry 159 }
		
	ommp81PlusXfpLowSupplyVoltageWarningThreshold OBJECT-TYPE
		SYNTAX DisplayString
		MAX-ACCESS read-write
		STATUS current
		DESCRIPTION
			"Set or Get Low Supply Voltage Warning Threshold
			(in volts) for the requested port
			-----------------------------
			ommp81PlusInterfaceNumber:
			9 - LINE-1
			-----------------------------
			Values:
			eg: +3.1
			-----------------------------"
		::= { ommp81PlusConfigurationEntry 160 }

	ommp81PlusSfpLaserState OBJECT-TYPE		 
		SYNTAX  INTEGER
		MAX-ACCESS read-write
		STATUS current
		DESCRIPTION
			"Set or Get the SFP LASER state for the the requested
			port
			-----------------------------
			ommp81PlusInterfaceNumber:
			1 to 8 - CLIENT-1 to CLIENT-8
			-----------------------------
			Values: 
			01 - Laser ON
			00 - Laser OFF
			-----------------------------" 
		::= { ommp81PlusConfigurationEntry 181 }

	ommp81PlusSfpHighTemperatureAlarmThreshold OBJECT-TYPE
		SYNTAX DisplayString
		MAX-ACCESS read-write
		STATUS current
		DESCRIPTION
			"Set or Get High Temperature Alarm Threshold
			(in degree celsius) for the requested port
			-----------------------------
			ommp81PlusInterfaceNumber:
			1 to 8 - CLIENT-1 to CLIENT-8
			-----------------------------
			Values: 
			eg: 65 
			-----------------------------" 
		::= { ommp81PlusConfigurationEntry 182 }
		
	ommp81PlusSfpLowTemperatureAlarmThreshold OBJECT-TYPE
		SYNTAX DisplayString
		MAX-ACCESS read-write
		STATUS current
		DESCRIPTION
			"Set or Get Low Temperature Alarm Threshold
			(in degree celsius) for the requested port
			-----------------------------
			ommp81PlusInterfaceNumber:
			1 to 8 - CLIENT-1 to CLIENT-8
			-----------------------------
			Values: 
			eg: 5 
			-----------------------------" 
		::= { ommp81PlusConfigurationEntry 183 }
		
	ommp81PlusSfpHighTemperatureWarningThreshold OBJECT-TYPE
		SYNTAX DisplayString
		MAX-ACCESS read-write
		STATUS current
		DESCRIPTION
			"Set or Get High Temperature Warning Threshold
			(in degree celsius) for the requested port
			-----------------------------
			ommp81PlusInterfaceNumber:
			1 to 8 - CLIENT-1 to CLIENT-8
			-----------------------------
			Values: 
			eg: 60 
			-----------------------------"
		::= { ommp81PlusConfigurationEntry 184 }
		
	ommp81PlusSfpLowTemperatureWarningThreshold OBJECT-TYPE
		SYNTAX DisplayString
		MAX-ACCESS read-write
		STATUS current
		DESCRIPTION
			"Set or Get Low Temperature Warning Threshold
			(in degree celsius) for the requested port
			-----------------------------
			ommp81PlusInterfaceNumber:
			1 to 8 - CLIENT-1 to CLIENT-8
			-----------------------------
			Values: 
			eg: 10 
			-----------------------------"
		::= { ommp81PlusConfigurationEntry 185 }

	ommp81PlusSfpHighBiasCurrentAlarmThreshold OBJECT-TYPE
		SYNTAX DisplayString
		MAX-ACCESS read-write
		STATUS current
		DESCRIPTION
			"Set or Get High Bias Current Alarm Threshold
			(in milli ampere) for the requested port
			-----------------------------
			ommp81PlusInterfaceNumber:
			1 to 8 - CLIENT-1 to CLIENT-8
			-----------------------------
			Values:
			eg: 35.6
			-----------------------------"			
		::= { ommp81PlusConfigurationEntry 186 }
		
	ommp81PlusSfpLowBiasCurrentAlarmThreshold OBJECT-TYPE
		SYNTAX DisplayString
		MAX-ACCESS read-write
		STATUS current
		DESCRIPTION
			"Set or Get Low Bias Current Alarm Threshold
			(in milli ampere) for the requested port
			-----------------------------
			ommp81PlusInterfaceNumber:
			1 to 8 - CLIENT-1 to CLIENT-8
			-----------------------------
			Values:
			eg: 31.1
			-----------------------------"
		::= { ommp81PlusConfigurationEntry 187 }
		
	ommp81PlusSfpHighBiasCurrentWarningThreshold OBJECT-TYPE
		SYNTAX DisplayString
		MAX-ACCESS read-write
		STATUS current
		DESCRIPTION
			"Set or Get High Bias Current Warning Threshold
			(in milli ampere) for the requested port
			-----------------------------
			ommp81PlusInterfaceNumber:
			1 to 8 - CLIENT-1 to CLIENT-8
			-----------------------------
			Values:
			eg: 34.5
			-----------------------------"
		::= { ommp81PlusConfigurationEntry 188 }
		
	ommp81PlusSfpLowBiasCurrentWarningThreshold OBJECT-TYPE
		SYNTAX DisplayString
		MAX-ACCESS read-write
		STATUS current
		DESCRIPTION
			"Set or Get Low Bias Current Alarm Threshold
			(in milli ampere) for the requested port
			-----------------------------
			ommp81PlusInterfaceNumber:
			1 to 8 - CLIENT-1 to CLIENT-8
			-----------------------------
			Values:
			eg: 32.8
			-----------------------------"
		::= { ommp81PlusConfigurationEntry 189 }
		
	ommp81PlusSfpInputHighPowerAlarmThreshold OBJECT-TYPE
		SYNTAX DisplayString
		MAX-ACCESS read-write
		STATUS current
		DESCRIPTION
			"Set or Get Input High Power Alarm Threshold
			(in dbm) for the requested port
			-----------------------------
			ommp81PlusInterfaceNumber:
			1 to 8 - CLIENT-1 to CLIENT-8
			-----------------------------
			Values:
			eg: -9.1
			-----------------------------"
		::= { ommp81PlusConfigurationEntry 190 }

	ommp81PlusSfpInputLowPowerAlarmThreshold OBJECT-TYPE
		SYNTAX DisplayString
		MAX-ACCESS read-write
		STATUS current
		DESCRIPTION
			"Set or Get Input Low Power Alarm Threshold
			(in dbm) for the requested port
			-----------------------------
			ommp81PlusInterfaceNumber:
			1 to 8 - CLIENT-1 to CLIENT-8
			-----------------------------
			Values:
			eg: -35.6
			-----------------------------"
		::= { ommp81PlusConfigurationEntry 191 }
		
	ommp81PlusSfpInputHighPowerWarningThreshold OBJECT-TYPE
		SYNTAX DisplayString
		MAX-ACCESS read-write
		STATUS current
		DESCRIPTION
			"Set or Get Input High Power Warning Threshold
			(in dbm) for the requested port
			-----------------------------
			ommp81PlusInterfaceNumber:
			1 to 8 - CLIENT-1 to CLIENT-8
			-----------------------------
			Values:
			eg: -11.2
			-----------------------------"
		::= { ommp81PlusConfigurationEntry 192 }
		
	ommp81PlusSfpInputLowPowerWarningThreshold OBJECT-TYPE
		SYNTAX DisplayString
		MAX-ACCESS read-write
		STATUS current
		DESCRIPTION
			"Set or Get Input Low Power Warning Threshold
			(in dbm) for the requested port
			-----------------------------
			ommp81PlusInterfaceNumber:
			1 to 8 - CLIENT-1 to CLIENT-8
			-----------------------------
			Values:
			eg: -31.3
			-----------------------------"
		::= { ommp81PlusConfigurationEntry 193 }
		
	ommp81PlusSfpOutputHighPowerAlarmThreshold OBJECT-TYPE
		SYNTAX DisplayString
		MAX-ACCESS read-write
		STATUS current
		DESCRIPTION
			"Set or Get Output High Power Alarm Threshold
			(in dbm) for the requested port
			-----------------------------
			ommp81PlusInterfaceNumber:
			1 to 8 - CLIENT-1 to CLIENT-8
			-----------------------------
			Values:
			eg: +2.0
			-----------------------------"
		::= { ommp81PlusConfigurationEntry 194 }

	ommp81PlusSfpOutputLowPowerAlarmThreshold OBJECT-TYPE
		SYNTAX DisplayString
		MAX-ACCESS read-write
		STATUS current
		DESCRIPTION
			"Set or Get Output Low Power Alarm Threshold
			(in dbm) for the requested port
			-----------------------------
			ommp81PlusInterfaceNumber:
			1 to 8 - CLIENT-1 to CLIENT-8
			-----------------------------
			Values:
			eg: -3.5
			-----------------------------"
		::= { ommp81PlusConfigurationEntry 195 }
		
	ommp81PlusSfpOutputHighPowerWarningThreshold OBJECT-TYPE
		SYNTAX DisplayString
		MAX-ACCESS read-write
		STATUS current
		DESCRIPTION
			"Set or Get Output High Power Warning Threshold
			(in dbm) for the requested port
			-----------------------------
			ommp81PlusInterfaceNumber:
			1 to 8 - CLIENT-1 to CLIENT-8
			-----------------------------
			Values:
			eg: +1.3
			-----------------------------"
		::= { ommp81PlusConfigurationEntry 196 }
		
	ommp81PlusSfpOutputLowPowerWarningThreshold OBJECT-TYPE
		SYNTAX DisplayString
		MAX-ACCESS read-write
		STATUS current
		DESCRIPTION
			"Set or Get Output Low Power Warning Threshold
			(in dbm) for the requested port
			-----------------------------
			ommp81PlusInterfaceNumber:
			1 to 8 - CLIENT-1 to CLIENT-8
			-----------------------------
			Values:
			eg: -2.5
			-----------------------------"
		::= { ommp81PlusConfigurationEntry 197 }
		
	ommp81PlusSfpHighSupplyVoltageAlarmThreshold OBJECT-TYPE
		SYNTAX DisplayString
		MAX-ACCESS read-write
		STATUS current
		DESCRIPTION
			"Set or Get High Supply Voltage Alarm Threshold
			(in volts) for the requested port
			-----------------------------
			ommp81PlusInterfaceNumber:
			1 to 8 - CLIENT-1 to CLIENT-8
			-----------------------------
			Values:
			eg: +3.3
			-----------------------------"
		::= { ommp81PlusConfigurationEntry 198 }

	ommp81PlusSfpLowSupplyVoltageAlarmThreshold OBJECT-TYPE
		SYNTAX DisplayString
		MAX-ACCESS read-write
		STATUS current
		DESCRIPTION
			"Set or Get Low Supply Voltage Alarm Threshold
			(in volts) for the requested port
			-----------------------------
			ommp81PlusInterfaceNumber:
			1 to 8 - CLIENT-1 to CLIENT-8
			-----------------------------
			Values:
			eg: +3.0
			-----------------------------"
		::= { ommp81PlusConfigurationEntry 199 }
		
	ommp81PlusSfpHighSupplyVoltageWarningThreshold OBJECT-TYPE
		SYNTAX DisplayString
		MAX-ACCESS read-write
		STATUS current
		DESCRIPTION
			"Set or Get High Supply Voltage Warning Threshold
			(in volts) for the requested port
			-----------------------------
			ommp81PlusInterfaceNumber:
			1 to 8 - CLIENT-1 to CLIENT-8
			-----------------------------
			Values:
			eg: +3.2
			-----------------------------"
		::= { ommp81PlusConfigurationEntry 200 }
		
	ommp81PlusSfpLowSupplyVoltageWarningThreshold OBJECT-TYPE
		SYNTAX DisplayString
		MAX-ACCESS read-write
		STATUS current
		DESCRIPTION
			"Set or Get Low Supply Voltage Warning Threshold
			(in volts) for the requested port
			-----------------------------
			ommp81PlusInterfaceNumber:
			1 to 8 - CLIENT-1 to CLIENT-8
			-----------------------------
			Values:
			eg: +3.1
			-----------------------------"
		::= { ommp81PlusConfigurationEntry 201 }

	ommp81PlusXfpInputPowerFailureAlarmInhibit  OBJECT-TYPE
		SYNTAX  INTEGER
		MAX-ACCESS  read-write
		STATUS  current
		DESCRIPTION
			"Inhibits OMMP81-PLUS XFP Input Power Failure Alarm
			for the requested port
			-----------------------------
			ommp81PlusInterfaceNumber:
			9 - LINE-1
			-----------------------------
			Value:
			1 - Inhibit
			0 - Do Not Inhibit
			-----------------------------"
	::= { ommp81PlusConfigurationEntry 301 }

	ommp81PlusXfpOutputPowerFailureAlarmInhibit  OBJECT-TYPE
		SYNTAX  INTEGER
		MAX-ACCESS  read-write
		STATUS  current
		DESCRIPTION
			"Inhibits OMMP81-PLUS XFP Output Power Failure Alarm
			for the requested port
			-----------------------------
			ommp81PlusInterfaceNumber:
			9 - LINE-1
			-----------------------------
			Value:
			1 - Inhibit
			0 - Do Not Inhibit
			-----------------------------"
	::= { ommp81PlusConfigurationEntry 302 }

	ommp81PlusXfpHighTemperatureAlarmInhibit  OBJECT-TYPE
		SYNTAX  INTEGER
		MAX-ACCESS  read-write
		STATUS  current
		DESCRIPTION
			"Inhibits OMMP81-PLUS XFP High Temperature Alarm
			for the requested port
			-----------------------------
			ommp81PlusInterfaceNumber:
			9 - LINE-1
			-----------------------------
			Value:
			1 - Inhibit
			0 - Do Not Inhibit
			-----------------------------"
	::= { ommp81PlusConfigurationEntry 303 }

	ommp81PlusXfpLowTemperatureAlarmInhibit  OBJECT-TYPE
		SYNTAX  INTEGER
		MAX-ACCESS  read-write
		STATUS  current
		DESCRIPTION
			"Inhibits OMMP81-PLUS XFP Low Temperature Alarm
			for the requested port
			-----------------------------
			ommp81PlusInterfaceNumber:
			9 - LINE-1
			-----------------------------
			Value:
			1 - Inhibit
			0 - Do Not Inhibit
			-----------------------------"
	::= { ommp81PlusConfigurationEntry 304 }

	ommp81PlusXfpHighTemperatureWarningInhibit  OBJECT-TYPE
		SYNTAX  INTEGER
		MAX-ACCESS  read-write
		STATUS  current
		DESCRIPTION
			"Inhibits OMMP81-PLUS XFP High Temperature Warning
			for the requested port
			-----------------------------
			ommp81PlusInterfaceNumber:
			9 - LINE-1
			-----------------------------
			Value:
			1 - Inhibit
			0 - Do Not Inhibit
			-----------------------------"
	::= { ommp81PlusConfigurationEntry 305 }

	ommp81PlusXfpLowTemperatureWarningInhibit  OBJECT-TYPE
		SYNTAX  INTEGER
		MAX-ACCESS  read-write
		STATUS  current
		DESCRIPTION
			"Inhibits OMMP81-PLUS XFP Low Temperature Warning
			for the requested port
			-----------------------------
			ommp81PlusInterfaceNumber:
			9 - LINE-1
			-----------------------------
			Value:
			1 - Inhibit
			0 - Do Not Inhibit
			-----------------------------"
	::= { ommp81PlusConfigurationEntry 306 }

	ommp81PlusXfpHighBiasCurrentAlarmInhibit  OBJECT-TYPE
		SYNTAX  INTEGER
		MAX-ACCESS  read-write
		STATUS  current
		DESCRIPTION
			"Inhibits OMMP81-PLUS XFP High Bias Current Alarm
			for the requested port
			-----------------------------
			ommp81PlusInterfaceNumber:
			9 - LINE-1
			-----------------------------
			Value:
			1 - Inhibit
			0 - Do Not Inhibit
			-----------------------------"
	::= { ommp81PlusConfigurationEntry 307 }

	ommp81PlusXfpLowBiasCurrentAlarmInhibit  OBJECT-TYPE
		SYNTAX  INTEGER
		MAX-ACCESS  read-write
		STATUS  current
		DESCRIPTION
			"Inhibits OMMP81-PLUS XFP Low Bias Current Alarm
			for the requested port
			-----------------------------
			ommp81PlusInterfaceNumber:
			9 - LINE-1
			-----------------------------
			Value:
			1 - Inhibit
			0 - Do Not Inhibit
			-----------------------------"
	::= { ommp81PlusConfigurationEntry 308 }

	ommp81PlusXfpHighBiasCurrentWarningInhibit  OBJECT-TYPE
		SYNTAX  INTEGER
		MAX-ACCESS  read-write
		STATUS  current
		DESCRIPTION
			"Inhibits OMMP81-PLUS XFP High Bias Current Warning
			for the requested port
			-----------------------------
			ommp81PlusInterfaceNumber:
			9 - LINE-1
			-----------------------------
			Value:
			1 - Inhibit
			0 - Do Not Inhibit
			-----------------------------"
	::= { ommp81PlusConfigurationEntry 309 }

	ommp81PlusXfpLowBiasCurrentWarningInhibit  OBJECT-TYPE
		SYNTAX  INTEGER
		MAX-ACCESS  read-write
		STATUS  current
		DESCRIPTION
			"Inhibits OMMP81-PLUS XFP Low Bias Current Warning
			for the requested port
			-----------------------------
			ommp81PlusInterfaceNumber:
			9 - LINE-1
			-----------------------------
			Value:
			1 - Inhibit
			0 - Do Not Inhibit
			-----------------------------"
	::= { ommp81PlusConfigurationEntry 310 }

	ommp81PlusXfpInputHighPowerAlarmInhibit  OBJECT-TYPE
		SYNTAX  INTEGER
		MAX-ACCESS  read-write
		STATUS  current
		DESCRIPTION
			"Inhibits OMMP81-PLUS XFP Input High Power Alarm
			for the requested port
			-----------------------------
			ommp81PlusInterfaceNumber:
			9 - LINE-1
			-----------------------------
			Value:
			1 - Inhibit
			0 - Do Not Inhibit
			-----------------------------"
	::= { ommp81PlusConfigurationEntry 311 }

	ommp81PlusXfpInputLowPowerAlarmInhibit  OBJECT-TYPE
		SYNTAX  INTEGER
		MAX-ACCESS  read-write
		STATUS  current
		DESCRIPTION
			"Inhibits OMMP81-PLUS XFP Input Low Power Alarm
			for the requested port
			-----------------------------
			ommp81PlusInterfaceNumber:
			9 - LINE-1
			-----------------------------
			Value:
			1 - Inhibit
			0 - Do Not Inhibit
			-----------------------------"
	::= { ommp81PlusConfigurationEntry 312 }

	ommp81PlusXfpInputHighPowerWarningInhibit  OBJECT-TYPE
		SYNTAX  INTEGER
		MAX-ACCESS  read-write
		STATUS  current
		DESCRIPTION
			"Inhibits OMMP81-PLUS XFP Input High Power Warning
			for the requested port
			-----------------------------
			ommp81PlusInterfaceNumber:
			9 - LINE-1
			-----------------------------
			Value:
			1 - Inhibit
			0 - Do Not Inhibit
			-----------------------------"
	::= { ommp81PlusConfigurationEntry 313 }

	ommp81PlusXfpInputLowPowerWarningInhibit  OBJECT-TYPE
		SYNTAX  INTEGER
		MAX-ACCESS  read-write
		STATUS  current
		DESCRIPTION
			"Inhibits OMMP81-PLUS XFP Input Low Power Warning
			for the requested port
			-----------------------------
			ommp81PlusInterfaceNumber:
			9 - LINE-1
			-----------------------------
			Value:
			1 - Inhibit
			0 - Do Not Inhibit
			-----------------------------"
	::= { ommp81PlusConfigurationEntry 314 }

	ommp81PlusXfpOutputHighPowerAlarmInhibit  OBJECT-TYPE
		SYNTAX  INTEGER
		MAX-ACCESS  read-write
		STATUS  current
		DESCRIPTION
			"Inhibits OMMP81-PLUS XFP Output High Power Alarm
			for the requested port
			-----------------------------
			ommp81PlusInterfaceNumber:
			9 - LINE-1
			-----------------------------
			Value:
			1 - Inhibit
			0 - Do Not Inhibit
			-----------------------------"
	::= { ommp81PlusConfigurationEntry 315 }

	ommp81PlusXfpOutputLowPowerAlarmInhibit  OBJECT-TYPE
		SYNTAX  INTEGER
		MAX-ACCESS  read-write
		STATUS  current
		DESCRIPTION
			"Inhibits OMMP81-PLUS XFP Output Low Power Alarm
			for the requested port
			-----------------------------
			ommp81PlusInterfaceNumber:
			9 - LINE-1
			-----------------------------
			Value:
			1 - Inhibit
			0 - Do Not Inhibit
			-----------------------------"
	::= { ommp81PlusConfigurationEntry 316 }

	ommp81PlusXfpOutputHighPowerWarningInhibit  OBJECT-TYPE
		SYNTAX  INTEGER
		MAX-ACCESS  read-write
		STATUS  current
		DESCRIPTION
			"Inhibits OMMP81-PLUS XFP Output High Power Warning
			for the requested port
			-----------------------------
			ommp81PlusInterfaceNumber:
			9 - LINE-1
			-----------------------------
			Value:
			1 - Inhibit
			0 - Do Not Inhibit
			-----------------------------"
	::= { ommp81PlusConfigurationEntry 317 }

	ommp81PlusXfpOutputLowPowerWarningInhibit  OBJECT-TYPE
		SYNTAX  INTEGER
		MAX-ACCESS  read-write
		STATUS  current
		DESCRIPTION
			"Inhibits OMMP81-PLUS XFP Output Low Power Warning
			for the requested port
			-----------------------------
			ommp81PlusInterfaceNumber:
			9 - LINE-1
			-----------------------------
			Value:
			1 - Inhibit
			0 - Do Not Inhibit
			-----------------------------"
	::= { ommp81PlusConfigurationEntry 318 }

	ommp81PlusXfpHighSupplyVoltageAlarmInhibit  OBJECT-TYPE
		SYNTAX  INTEGER
		MAX-ACCESS  read-write
		STATUS  current
		DESCRIPTION
			"Inhibits OMMP81-PLUS XFP High Supply Voltage Alarm
			for the requested port
			-----------------------------
			ommp81PlusInterfaceNumber:
			9 - LINE-1
			-----------------------------
			Value:
			1 - Inhibit
			0 - Do Not Inhibit
			-----------------------------"
	::= { ommp81PlusConfigurationEntry 319 }

	ommp81PlusXfpLowSupplyVoltageAlarmInhibit  OBJECT-TYPE
		SYNTAX  INTEGER
		MAX-ACCESS  read-write
		STATUS  current
		DESCRIPTION
			"Inhibits OMMP81-PLUS XFP Low Supply Voltage Alarm
			for the requested port
			-----------------------------
			ommp81PlusInterfaceNumber:
			9 - LINE-1
			-----------------------------
			Value:
			1 - Inhibit
			0 - Do Not Inhibit
			-----------------------------"
	::= { ommp81PlusConfigurationEntry 320 }

	ommp81PlusXfpHighSupplyVoltageWarningInhibit  OBJECT-TYPE
		SYNTAX  INTEGER
		MAX-ACCESS  read-write
		STATUS  current
		DESCRIPTION
			"Inhibits OMMP81-PLUS XFP High Supply Voltage Warning
			for the requested port
			-----------------------------
			ommp81PlusInterfaceNumber:
			9 - LINE-1
			-----------------------------
			Value:
			1 - Inhibit
			0 - Do Not Inhibit
			-----------------------------"
	::= { ommp81PlusConfigurationEntry 321 }

	ommp81PlusXfpLowSupplyVoltageWarningInhibit  OBJECT-TYPE
		SYNTAX  INTEGER
		MAX-ACCESS  read-write
		STATUS  current
		DESCRIPTION
			"Inhibits OMMP81-PLUS XFP Low Supply Voltage Warning
			for the requested port
			-----------------------------
			ommp81PlusInterfaceNumber:
			9 - LINE-1
			-----------------------------
			Value:
			1 - Inhibit
			0 - Do Not Inhibit
			-----------------------------"
	::= { ommp81PlusConfigurationEntry 322 }

	ommp81PlusXfpPresenceAbsenceNotificationInhibit  OBJECT-TYPE
		SYNTAX  INTEGER
		MAX-ACCESS  read-write
		STATUS  current
		DESCRIPTION
			"Inhibits OMMP81-PLUS XFP Presence Absence Notification
			for the requested port
			-----------------------------
			ommp81PlusInterfaceNumber:
			9 - LINE-1
			-----------------------------
			Value:
			1 - Inhibit
			0 - Do Not Inhibit
			-----------------------------"
	::= { ommp81PlusConfigurationEntry 323 }

	ommp81PlusSfpInputPowerFailureAlarmInhibit  OBJECT-TYPE
		SYNTAX  INTEGER
		MAX-ACCESS  read-write
		STATUS  current
		DESCRIPTION
			"Inhibits OMMP81-PLUS SFP Input Power Failure Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 341 }

	ommp81PlusSfpOutputPowerFailureAlarmInhibit  OBJECT-TYPE
		SYNTAX  INTEGER
		MAX-ACCESS  read-write
		STATUS  current
		DESCRIPTION
			"Inhibits OMMP81-PLUS SFP Output Power Failure Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 342 }

	ommp81PlusSfpHighTemperatureAlarmInhibit  OBJECT-TYPE
		SYNTAX  INTEGER
		MAX-ACCESS  read-write
		STATUS  current
		DESCRIPTION
			"Inhibits OMMP81-PLUS SFP High Temperature Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 343 }

	ommp81PlusSfpLowTemperatureAlarmInhibit  OBJECT-TYPE
		SYNTAX  INTEGER
		MAX-ACCESS  read-write
		STATUS  current
		DESCRIPTION
			"Inhibits OMMP81-PLUS SFP Low Temperature Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 344 }

	ommp81PlusSfpHighTemperatureWarningInhibit  OBJECT-TYPE
		SYNTAX  INTEGER
		MAX-ACCESS  read-write
		STATUS  current
		DESCRIPTION
			"Inhibits OMMP81-PLUS SFP High Temperature Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 345 }

	ommp81PlusSfpLowTemperatureWarningInhibit  OBJECT-TYPE
		SYNTAX  INTEGER
		MAX-ACCESS  read-write
		STATUS  current
		DESCRIPTION
			"Inhibits OMMP81-PLUS SFP Low Temperature Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 346 }

	ommp81PlusSfpHighBiasCurrentAlarmInhibit  OBJECT-TYPE
		SYNTAX  INTEGER
		MAX-ACCESS  read-write
		STATUS  current
		DESCRIPTION
			"Inhibits OMMP81-PLUS SFP High Bias Current Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 347 }

	ommp81PlusSfpLowBiasCurrentAlarmInhibit  OBJECT-TYPE
		SYNTAX  INTEGER
		MAX-ACCESS  read-write
		STATUS  current
		DESCRIPTION
			"Inhibits OMMP81-PLUS SFP Low Bias Current Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 348 }

	ommp81PlusSfpHighBiasCurrentWarningInhibit  OBJECT-TYPE
		SYNTAX  INTEGER
		MAX-ACCESS  read-write
		STATUS  current
		DESCRIPTION
			"Inhibits OMMP81-PLUS SFP High Bias Current Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 349 }

	ommp81PlusSfpLowBiasCurrentWarningInhibit  OBJECT-TYPE
		SYNTAX  INTEGER
		MAX-ACCESS  read-write
		STATUS  current
		DESCRIPTION
			"Inhibits OMMP81-PLUS SFP Low Bias Current Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 350 }

	ommp81PlusSfpInputHighPowerAlarmInhibit  OBJECT-TYPE
		SYNTAX  INTEGER
		MAX-ACCESS  read-write
		STATUS  current
		DESCRIPTION
			"Inhibits OMMP81-PLUS SFP Input High Power Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 351 }

	ommp81PlusSfpInputLowPowerAlarmInhibit  OBJECT-TYPE
		SYNTAX  INTEGER
		MAX-ACCESS  read-write
		STATUS  current
		DESCRIPTION
			"Inhibits OMMP81-PLUS SFP Input Low Power Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 352 }

	ommp81PlusSfpInputHighPowerWarningInhibit  OBJECT-TYPE
		SYNTAX  INTEGER
		MAX-ACCESS  read-write
		STATUS  current
		DESCRIPTION
			"Inhibits OMMP81-PLUS SFP Input High Power Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 353 }

	ommp81PlusSfpInputLowPowerWarningInhibit  OBJECT-TYPE
		SYNTAX  INTEGER
		MAX-ACCESS  read-write
		STATUS  current
		DESCRIPTION
			"Inhibits OMMP81-PLUS SFP Input Low Power Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 354 }

	ommp81PlusSfpOutputHighPowerAlarmInhibit  OBJECT-TYPE
		SYNTAX  INTEGER
		MAX-ACCESS  read-write
		STATUS  current
		DESCRIPTION
			"Inhibits OMMP81-PLUS SFP Output High Power Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 355 }

	ommp81PlusSfpOutputLowPowerAlarmInhibit  OBJECT-TYPE
		SYNTAX  INTEGER
		MAX-ACCESS  read-write
		STATUS  current
		DESCRIPTION
			"Inhibits OMMP81-PLUS SFP Output Low Power Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 356 }

	ommp81PlusSfpOutputHighPowerWarningInhibit  OBJECT-TYPE
		SYNTAX  INTEGER
		MAX-ACCESS  read-write
		STATUS  current
		DESCRIPTION
			"Inhibits OMMP81-PLUS SFP Output High Power Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 357 }

	ommp81PlusSfpOutputLowPowerWarningInhibit  OBJECT-TYPE
		SYNTAX  INTEGER
		MAX-ACCESS  read-write
		STATUS  current
		DESCRIPTION
			"Inhibits OMMP81-PLUS SFP Output Low Power Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 358 }

	ommp81PlusSfpHighSupplyVoltageAlarmInhibit  OBJECT-TYPE
		SYNTAX  INTEGER
		MAX-ACCESS  read-write
		STATUS  current
		DESCRIPTION
			"Inhibits OMMP81-PLUS SFP High Supply Voltage Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 359 }

	ommp81PlusSfpLowSupplyVoltageAlarmInhibit  OBJECT-TYPE
		SYNTAX  INTEGER
		MAX-ACCESS  read-write
		STATUS  current
		DESCRIPTION
			"Inhibits OMMP81-PLUS SFP Low Supply Voltage Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 360 }

	ommp81PlusSfpHighSupplyVoltageWarningInhibit  OBJECT-TYPE
		SYNTAX  INTEGER
		MAX-ACCESS  read-write
		STATUS  current
		DESCRIPTION
			"Inhibits OMMP81-PLUS SFP High Supply Voltage Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 361 }

	ommp81PlusSfpLowSupplyVoltageWarningInhibit  OBJECT-TYPE
		SYNTAX  INTEGER
		MAX-ACCESS  read-write
		STATUS  current
		DESCRIPTION
			"Inhibits OMMP81-PLUS SFP Low Supply Voltage Warning
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 362 }

	ommp81PlusSfpPresenceAbsenceNotificationInhibit  OBJECT-TYPE
		SYNTAX  INTEGER
		MAX-ACCESS  read-write
		STATUS  current
		DESCRIPTION
			"Inhibits OMMP81-PLUS SFP Presence Absence Notification
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 363 }

	ommp81PlusSfpTransmitFaultPresenceAlarmInhibit  OBJECT-TYPE
		SYNTAX  INTEGER
		MAX-ACCESS  read-write
		STATUS  current
		DESCRIPTION
			"Inhibits OMMP81-PLUS SFP Transmit Fault Presence Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 364 }

	ommp81PlusOtuLossOfSignalAlarmInhibit  OBJECT-TYPE
		SYNTAX  INTEGER
		MAX-ACCESS  read-write
		STATUS  current
		DESCRIPTION
			"Inhibits OMMP81-PLUS OTU Loss Of Signal Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 381 }

	ommp81PlusOtuLossOfFrameAlarmInhibit  OBJECT-TYPE
		SYNTAX  INTEGER
		MAX-ACCESS  read-write
		STATUS  current
		DESCRIPTION
			"Inhibits OMMP81-PLUS OTU Loss Of Frame Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 382 }

	ommp81PlusOtuOutOfFrameAlarmInhibit  OBJECT-TYPE
		SYNTAX  INTEGER
		MAX-ACCESS  read-write
		STATUS  current
		DESCRIPTION
			"Inhibits OMMP81-PLUS OTU Out Of Frame Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 383 }

	ommp81PlusOtuLossOfMultiFrameAlarmInhibit  OBJECT-TYPE
		SYNTAX  INTEGER
		MAX-ACCESS  read-write
		STATUS  current
		DESCRIPTION
			"Inhibits OMMP81-PLUS OTU Loss Of Multi Frame Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 384 }

	ommp81PlusOtuOutOfMultiFrameAlarmInhibit  OBJECT-TYPE
		SYNTAX  INTEGER
		MAX-ACCESS  read-write
		STATUS  current
		DESCRIPTION
			"Inhibits OMMP81-PLUS OTU Out Of Multi Frame Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 385 }

	ommp81PlusOtuSignalFailAlarmInhibit  OBJECT-TYPE
		SYNTAX  INTEGER
		MAX-ACCESS  read-write
		STATUS  current
		DESCRIPTION
			"Inhibits OMMP81-PLUS OTU Signal Fail Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 386 }

	ommp81PlusOtuSignalDegradeAlarmInhibit  OBJECT-TYPE
		SYNTAX  INTEGER
		MAX-ACCESS  read-write
		STATUS  current
		DESCRIPTION
			"Inhibits OMMP81-PLUS OTU Signal Degrade Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 387 }

	ommp81PlusOtuAlarmIndicationSignalAlarmInhibit  OBJECT-TYPE
		SYNTAX  INTEGER
		MAX-ACCESS  read-write
		STATUS  current
		DESCRIPTION
			"Inhibits OMMP81-PLUS OTU Alarm Indication Signal Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 388 }

	ommp81PlusOtuIncomingAlignmentErrorAlarmInhibit  OBJECT-TYPE
		SYNTAX  INTEGER
		MAX-ACCESS  read-write
		STATUS  current
		DESCRIPTION
			"Inhibits OMMP81-PLUS OTU Incoming Alignment Error Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 389 }

	ommp81PlusOtuTraceIdentifierMismatchAlarmInhibit  OBJECT-TYPE
		SYNTAX  INTEGER
		MAX-ACCESS  read-write
		STATUS  current
		DESCRIPTION
			"Inhibits OMMP81-PLUS OTU Trace Identifier Mismatch Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 390 }

	ommp81PlusOtuBackwardIncomingAlignmentErrorAlarmInhibit  OBJECT-TYPE
		SYNTAX  INTEGER
		MAX-ACCESS  read-write
		STATUS  current
		DESCRIPTION
			"Inhibits OMMP81-PLUS OTU Backward Incoming Alignment Error Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 391 }

	ommp81PlusOtuBackwardDefectIndicationAlarmInhibit  OBJECT-TYPE
		SYNTAX  INTEGER
		MAX-ACCESS  read-write
		STATUS  current
		DESCRIPTION
			"Inhibits OMMP81-PLUS OTU Backward Defect Indication Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 392 }

	ommp81PlusOduSignalFailAlarmInhibit  OBJECT-TYPE
		SYNTAX  INTEGER
		MAX-ACCESS  read-write
		STATUS  current
		DESCRIPTION
			"Inhibits OMMP81-PLUS ODU Signal Fail Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 411 }

	ommp81PlusOduSignalDegradeAlarmInhibit  OBJECT-TYPE
		SYNTAX  INTEGER
		MAX-ACCESS  read-write
		STATUS  current
		DESCRIPTION
			"Inhibits OMMP81-PLUS ODU Signal Degrade Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 412 }

	ommp81PlusOduAlarmIndicationSignalAlarmInhibit  OBJECT-TYPE
		SYNTAX  INTEGER
		MAX-ACCESS  read-write
		STATUS  current
		DESCRIPTION
			"Inhibits OMMP81-PLUS ODU Alarm Indication Signal Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 413 }

	ommp81PlusOduTcm1IncomingAlignmentErrorAlarmInhibit  OBJECT-TYPE
		SYNTAX  INTEGER
		MAX-ACCESS  read-write
		STATUS  current
		DESCRIPTION
			"Inhibits OMMP81-PLUS ODU TCM1 Incoming Alignment Error
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 414 }

	ommp81PlusOduTcm2IncomingAlignmentErrorAlarmInhibit  OBJECT-TYPE
		SYNTAX  INTEGER
		MAX-ACCESS  read-write
		STATUS  current
		DESCRIPTION
			"Inhibits OMMP81-PLUS ODU TCM2 Incoming Alignment Error
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 415 }

	ommp81PlusOduTcm3IncomingAlignmentErrorAlarmInhibit  OBJECT-TYPE
		SYNTAX  INTEGER
		MAX-ACCESS  read-write
		STATUS  current
		DESCRIPTION
			"Inhibits OMMP81-PLUS ODU TCM3 Incoming Alignment Error
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 416 }

	ommp81PlusOduTcm4IncomingAlignmentErrorAlarmInhibit  OBJECT-TYPE
		SYNTAX  INTEGER
		MAX-ACCESS  read-write
		STATUS  current
		DESCRIPTION
			"Inhibits OMMP81-PLUS ODU TCM4 Incoming Alignment Error
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 417 }

	ommp81PlusOduTcm5IncomingAlignmentErrorAlarmInhibit  OBJECT-TYPE
		SYNTAX  INTEGER
		MAX-ACCESS  read-write
		STATUS  current
		DESCRIPTION
			"Inhibits OMMP81-PLUS ODU TCM5 Incoming Alignment Error
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 418 }

	ommp81PlusOduTcm6IncomingAlignmentErrorAlarmInhibit  OBJECT-TYPE
		SYNTAX  INTEGER
		MAX-ACCESS  read-write
		STATUS  current
		DESCRIPTION
			"Inhibits OMMP81-PLUS ODU TCM6 Incoming Alignment Error
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 419 }

	ommp81PlusOduTraceIdentifierMismatchAlarmInhibit  OBJECT-TYPE
		SYNTAX  INTEGER
		MAX-ACCESS  read-write
		STATUS  current
		DESCRIPTION
			"Inhibits OMMP81-PLUS ODU Trace Identifier Mismatch
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 420 }

	ommp81PlusOduLockedDefectAlarmInhibit  OBJECT-TYPE
		SYNTAX  INTEGER
		MAX-ACCESS  read-write
		STATUS  current
		DESCRIPTION
			"Inhibits OMMP81-PLUS ODU Locked Defect Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 421 }

	ommp81PlusOduOpenConnectionIndicationAlarmInhibit  OBJECT-TYPE
		SYNTAX  INTEGER
		MAX-ACCESS  read-write
		STATUS  current
		DESCRIPTION
			"Inhibits OMMP81-PLUS ODU Open Connection Indication
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 422 }

	ommp81PlusOduBackwardDefectIndicationAlarmInhibit  OBJECT-TYPE
		SYNTAX  INTEGER
		MAX-ACCESS  read-write
		STATUS  current
		DESCRIPTION
			"Inhibits OMMP81-PLUS ODU Backward Defect Indication
			Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 423 }

	ommp81PlusOduTcm1BackwardIncomingAlignmentErrorAlarmInhibit  OBJECT-TYPE
		SYNTAX  INTEGER
		MAX-ACCESS  read-write
		STATUS  current
		DESCRIPTION
			"Inhibits OMMP81-PLUS ODU TCM1 Backward Incoming
			Alignment Error Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 424 }

	ommp81PlusOduTcm2BackwardIncomingAlignmentErrorAlarmInhibit  OBJECT-TYPE
		SYNTAX  INTEGER
		MAX-ACCESS  read-write
		STATUS  current
		DESCRIPTION
			"Inhibits OMMP81-PLUS ODU TCM2 Backward Incoming
			Alignment Error Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 425 }

	ommp81PlusOduTcm3BackwardIncomingAlignmentErrorAlarmInhibit  OBJECT-TYPE
		SYNTAX  INTEGER
		MAX-ACCESS  read-write
		STATUS  current
		DESCRIPTION
			"Inhibits OMMP81-PLUS ODU TCM3 Backward Incoming
			Alignment Error Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 426 }

	ommp81PlusOduTcm4BackwardIncomingAlignmentErrorAlarmInhibit  OBJECT-TYPE
		SYNTAX  INTEGER
		MAX-ACCESS  read-write
		STATUS  current
		DESCRIPTION
			"Inhibits OMMP81-PLUS ODU TCM4 Backward Incoming
			Alignment Error Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 427 }

	ommp81PlusOduTcm5BackwardIncomingAlignmentErrorAlarmInhibit  OBJECT-TYPE
		SYNTAX  INTEGER
		MAX-ACCESS  read-write
		STATUS  current
		DESCRIPTION
			"Inhibits OMMP81-PLUS ODU TCM5 Backward Incoming
			Alignment Error Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 428 }

	ommp81PlusOduTcm6BackwardIncomingAlignmentErrorAlarmInhibit  OBJECT-TYPE
		SYNTAX  INTEGER
		MAX-ACCESS  read-write
		STATUS  current
		DESCRIPTION
			"Inhibits OMMP81-PLUS ODU TCM6 Backward Incoming
			Alignment Error Alarm for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 429 }

	ommp81PlusOduLossOfFrameLossOfMultiframeAlarmInhibit  OBJECT-TYPE
		SYNTAX  INTEGER
		MAX-ACCESS  read-write
		STATUS  current
		DESCRIPTION
			"Inhibits OMMP81-PLUS ODU Loss Of Frame Loss Of
			Multiframe Alarm for the requested port
			-----------------------------
			ommp81PlusInterfaceNumber:
			1, 2, 3, 4 - Slice number
			-----------------------------
			Value:
			1 - Inhibit
			0 - Do Not Inhibit
			-----------------------------"
	::= { ommp81PlusConfigurationEntry 430 }

	ommp81PlusOpuPayloadMismatchAlarmInhibit  OBJECT-TYPE
		SYNTAX  INTEGER
		MAX-ACCESS  read-write
		STATUS  current
		DESCRIPTION
			"Inhibits OMMP81-PLUS OPU Payload Mismatch Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 435 }

	ommp81PlusOchLossOfPayloadAlarmInhibit  OBJECT-TYPE
		SYNTAX  INTEGER
		MAX-ACCESS  read-write
		STATUS  current
		DESCRIPTION
			"Inhibits OMMP81-PLUS OCH Loss Of Payload Alarm
			for the requested port
			-----------------------------
			ommp81PlusInterfaceNumber:
			1 to 8 - CLIENT-1 to CLIENT-8
			9 - LINE-1
			-----------------------------
			Value:
			1 - Inhibit
			0 - Do Not Inhibit
			-----------------------------"
	::= { ommp81PlusConfigurationEntry 436 }

	ommp81PlusSdhLossOfSignalAlarmInhibit  OBJECT-TYPE
		SYNTAX  INTEGER
		MAX-ACCESS  read-write
		STATUS  current
		DESCRIPTION
			"Inhibits OMMP81-PLUS SDH Loss Of Signal Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 441 }

	ommp81PlusSdhOutOfFrameAlarmInhibit  OBJECT-TYPE
		SYNTAX  INTEGER
		MAX-ACCESS  read-write
		STATUS  current
		DESCRIPTION
			"Inhibits OMMP81-PLUS SDH Out Of Frame Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 442 }

	ommp81PlusSdhLossOfFrameAlarmInhibit  OBJECT-TYPE
		SYNTAX  INTEGER
		MAX-ACCESS  read-write
		STATUS  current
		DESCRIPTION
			"Inhibits OMMP81-PLUS SDH Loss Of Frame Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 443 }

	ommp81PlusSdhRsAlarmIndicationSignalAlarmInhibit  OBJECT-TYPE
		SYNTAX  INTEGER
		MAX-ACCESS  read-write
		STATUS  current
		DESCRIPTION
			"Inhibits OMMP81-PLUS SDH Rs Alarm Indication Signal
			Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 444 }

	ommp81PlusSdhRsTraceIdentifierMismatchAlarmInhibit  OBJECT-TYPE
		SYNTAX  INTEGER
		MAX-ACCESS  read-write
		STATUS  current
		DESCRIPTION
			"Inhibits OMMP81-PLUS SDH Rs Trace Identifier
			Mismatch Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 445 }

	ommp81PlusSdhAuAlarmIndicationSignalAlarmInhibit  OBJECT-TYPE
		SYNTAX  INTEGER
		MAX-ACCESS  read-write
		STATUS  current
		DESCRIPTION
			"Inhibits OMMP81-PLUS SDH Au Alarm Indication Signal
			Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 446 }

	ommp81PlusSdhAuLossOfPointerAlarmInhibit  OBJECT-TYPE
		SYNTAX  INTEGER
		MAX-ACCESS  read-write
		STATUS  current
		DESCRIPTION
			"Inhibits OMMP81-PLUS SDH Au Loss Of Pointer Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 447 }

	ommp81PlusSdhMsAlarmIndicationSignalAlarmInhibit  OBJECT-TYPE
		SYNTAX  INTEGER
		MAX-ACCESS  read-write
		STATUS  current
		DESCRIPTION
			"Inhibits OMMP81-PLUS SDH Ms Alarm Indication Signal
			Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 448 }

	ommp81PlusSdhMsRemoteErrorIndicationAlarmInhibit  OBJECT-TYPE
		SYNTAX  INTEGER
		MAX-ACCESS  read-write
		STATUS  current
		DESCRIPTION
			"Inhibits OMMP81-PLUS SDH Ms Remote Error Indication
			Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 449 }

	ommp81PlusSdhMsRemoteDefectIndicationAlarmInhibit  OBJECT-TYPE
		SYNTAX  INTEGER
		MAX-ACCESS  read-write
		STATUS  current
		DESCRIPTION
			"Inhibits OMMP81-PLUS SDH Ms Remote Defect Indication
			Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 450 }

	ommp81PlusSdhMsRemoteFailureIndicationAlarmInhibit  OBJECT-TYPE
		SYNTAX  INTEGER
		MAX-ACCESS  read-write
		STATUS  current
		DESCRIPTION
			"Inhibits OMMP81-PLUS SDH Ms Remote Failure Indication
			Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 451 }

	ommp81PlusSdhMsB2ExcessiveErrorAlarmInhibit  OBJECT-TYPE
		SYNTAX  INTEGER
		MAX-ACCESS  read-write
		STATUS  current
		DESCRIPTION
			"Inhibits OMMP81-PLUS SDH Ms B2 Signal Fail Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 452 }

	ommp81PlusSdhMsB2SignalDegradeAlarmInhibit  OBJECT-TYPE
		SYNTAX  INTEGER
		MAX-ACCESS  read-write
		STATUS  current
		DESCRIPTION
			"Inhibits OMMP81-PLUS SDH Ms B2 Signal Degrade Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 453 }

	ommp81PlusSdhLossOfSequenceSynchronisationAlarmInhibit  OBJECT-TYPE
		SYNTAX  INTEGER
		MAX-ACCESS  read-write
		STATUS  current
		DESCRIPTION
			"Inhibits OMMP81-PLUS SDH Loss Of Sequence 
			Synchronisation Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 454 }

	ommp81PlusSdhLowerOrderPathPayloadLabelMismatchAlarmInhibit  OBJECT-TYPE
		SYNTAX  INTEGER
		MAX-ACCESS  read-write
		STATUS  current
		DESCRIPTION
			"Inhibits OMMP81-PLUS SDH Lower Order Path Payload
			Label Mismatch Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 455 }

	ommp81PlusSdhLowerOrderPathUnequippedAlarmInhibit  OBJECT-TYPE
		SYNTAX  INTEGER
		MAX-ACCESS  read-write
		STATUS  current
		DESCRIPTION
			"Inhibits OMMP81-PLUS SDH Lower Order Path Unequipped
			Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 456 }

	ommp81PlusEthernetLossOfSignalAlarmInhibit  OBJECT-TYPE
		SYNTAX  INTEGER
		MAX-ACCESS  read-write
		STATUS  current
		DESCRIPTION
			"Inhibits OMMP81-PLUS Ethernet Loss Of Signal Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 471 }

	ommp81PlusEthernetLossOfSignalSyncAlarmInhibit  OBJECT-TYPE
		SYNTAX  INTEGER
		MAX-ACCESS  read-write
		STATUS  current
		DESCRIPTION
			"Inhibits OMMP81-PLUS Ethernet Loss Of Signal Sync Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 472 }

	ommp81PlusEthernetLinkFailureAlarmInhibit  OBJECT-TYPE
		SYNTAX  INTEGER
		MAX-ACCESS  read-write
		STATUS  current
		DESCRIPTION
			"Inhibits OMMP81-PLUS Ethernet Link Failure Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 473 }

	ommp81PlusEthernetAutoNegotiationAlarmInhibit  OBJECT-TYPE
		SYNTAX  INTEGER
		MAX-ACCESS  read-write
		STATUS  current
		DESCRIPTION
			"Inhibits OMMP81-PLUS Ethernet Auto Negotiation Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 474 }

	ommp81PlusEthernetFrameCheckSequenceAlarmInhibit  OBJECT-TYPE
		SYNTAX  INTEGER
		MAX-ACCESS  read-write
		STATUS  current
		DESCRIPTION
			"Inhibits OMMP81-PLUS Ethernet Frame Check Sequence Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 475 }

	ommp81PlusEthernetCarrierStatusAlarmInhibit  OBJECT-TYPE
		SYNTAX  INTEGER
		MAX-ACCESS  read-write
		STATUS  current
		DESCRIPTION
			"Inhibits OMMP81-PLUS Ethernet Carrier Status Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 476 }

	ommp81PlusEthernetHighBerAlarmInhibit  OBJECT-TYPE
		SYNTAX  INTEGER
		MAX-ACCESS  read-write
		STATUS  current
		DESCRIPTION
			"Inhibits OMMP81-PLUS Ethernet High Ber Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 477 }

	ommp81PlusEthernetLocalFaultAlarmInhibit  OBJECT-TYPE
		SYNTAX  INTEGER
		MAX-ACCESS  read-write
		STATUS  current
		DESCRIPTION
			"Inhibits OMMP81-PLUS Ethernet Local Fault Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 478 }

	ommp81PlusEthernetRemoteFaultAlarmInhibit  OBJECT-TYPE
		SYNTAX  INTEGER
		MAX-ACCESS  read-write
		STATUS  current
		DESCRIPTION
			"Inhibits OMMP81-PLUS Ethernet Remote Fault Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 479 }

	ommp81PlusFcTransmitDisparityInversionDefectAlarmInhibit  OBJECT-TYPE
		SYNTAX  INTEGER
		MAX-ACCESS  read-write
		STATUS  current
		DESCRIPTION
			"Inhibits OMMP81-PLUS FC Transmit Disparity Inversion 
			Defect Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 491 }

	ommp81PlusFcTransmitDigitalLossOfLinkDefectAlarmInhibit  OBJECT-TYPE
		SYNTAX  INTEGER
		MAX-ACCESS  read-write
		STATUS  current
		DESCRIPTION
			"Inhibits OMMP81-PLUS FC Transmit Digital Loss Of Link
			Defect Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 492 }

	ommp81PlusFcTrasnmitLossOfSynchronizationDefectAlarmInhibit  OBJECT-TYPE
		SYNTAX  INTEGER
		MAX-ACCESS  read-write
		STATUS  current
		DESCRIPTION
			"Inhibits OMMP81-PLUS FC Transmit Loss of 
			Synchronization Defect Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 493 }

	ommp81PlusFcReceiveDigitalLossOfLinkDefectAlarmInhibit  OBJECT-TYPE
		SYNTAX  INTEGER
		MAX-ACCESS  read-write
		STATUS  current
		DESCRIPTION
			"Inhibits OMMP81-PLUS FC Receive Digital Loss of 
			Link Defect Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 494 }

	ommp81PlusFcReceiveLossOfSynchronizationDefectAlarmInhibit  OBJECT-TYPE
		SYNTAX  INTEGER
		MAX-ACCESS  read-write
		STATUS  current
		DESCRIPTION
			"Inhibits OMMP81-PLUS FC Receive Loss Of Synchronization
			Defect Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 495 }

	ommp81PlusFcReceiveTransitionDetectDefectAlarmInhibit  OBJECT-TYPE
		SYNTAX  INTEGER
		MAX-ACCESS  read-write
		STATUS  current
		DESCRIPTION
			"Inhibits OMMP81-PLUS FC Receive Transition Detect 
			Defect Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 496 }

	ommp81PlusFcReceiveAnalogLossOfSignalDefectAlarmInhibit  OBJECT-TYPE
		SYNTAX  INTEGER
		MAX-ACCESS  read-write
		STATUS  current
		DESCRIPTION
			"Inhibits OMMP81-PLUS FC Receive Analog Loss Of Signal 
			Defect Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 497 }

	ommp81PlusFcReceiveLineCodeViolationDefectAlarmInhibit  OBJECT-TYPE
		SYNTAX  INTEGER
		MAX-ACCESS  read-write
		STATUS  current
		DESCRIPTION
			"Inhibits OMMP81-PLUS FC Receive Line Code Violation 
			Defect Alarm for the requested port
			-----------------------------
			ommp81PlusInterfaceNumber:
			1 to 8 - CLIENT-1 to CLIENT-8
			-----------------------------
			Value:
			1 - Inhibit
			0 - Do Not Inhibit
			-----------------------------"
	::= { ommp81PlusConfigurationEntry 498 }

	ommp81PlusGfpCsfSignalFailAlarmInhibit  OBJECT-TYPE
		SYNTAX  INTEGER
		MAX-ACCESS  read-write
		STATUS  current
		DESCRIPTION
			"Inhibits OMMP81-PLUS GFP Csf Signal Failure Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 511 }

	ommp81PlusGfpCsfLinkFailAlarmInhibit  OBJECT-TYPE
		SYNTAX  INTEGER
		MAX-ACCESS  read-write
		STATUS  current
		DESCRIPTION
			"Inhibits OMMP81-PLUS GFP Csf Link Failure Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 512 }

	ommp81PlusGfpCoreHeaderErrorAlarmInhibit  OBJECT-TYPE
		SYNTAX  INTEGER
		MAX-ACCESS  read-write
		STATUS  current
		DESCRIPTION
			"Inhibits OMMP81-PLUS GFP Core Header Error Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 513 }

	ommp81PlusGfpExtentionHeaderErrorAlarmInhibit  OBJECT-TYPE
		SYNTAX  INTEGER
		MAX-ACCESS  read-write
		STATUS  current
		DESCRIPTION
			"Inhibits OMMP81-PLUS GFP Extention Header Error Alarm
			for the requested port
			-----------------------------
			ommp81PlusInterfaceNumber:
			1 to 8 - CLIENT-1 to CLIENT-8
			-----------------------------
			Value:
			1 - Inhibit
			0 - Do Not Inhibit
			-----------------------------"
	::= { ommp81PlusConfigurationEntry 514 }

	ommp81PlusXfpInputPowerFailureAlarmSeverity OBJECT-TYPE
		SYNTAX  DisplayString
		MAX-ACCESS  read-write
		STATUS  current
		DESCRIPTION
			"Set or Get the alarm severity level of the
			OMMP81-PLUS XFP Input Power Failure Alarm   
			for requested port
			-----------------------------
			ommp81PlusInterfaceNumber:
			9 - LINE-1
			-----------------------------
			Value:
			critical
			major
			minor
			deferred
			---------------------------"
	::= { ommp81PlusConfigurationEntry 601 }

	ommp81PlusXfpOutputPowerFailureAlarmSeverity OBJECT-TYPE
		SYNTAX  DisplayString
		MAX-ACCESS  read-write
		STATUS  current
		DESCRIPTION
			"Set or Get the alarm severity level of the
			OMMP81-PLUS XFP Output Power Failure Alarm   
			for requested port
			-----------------------------
			ommp81PlusInterfaceNumber:
			9 - LINE-1
			-----------------------------
			Value:
			critical
			major
			minor
			deferred
			---------------------------"
	::= { ommp81PlusConfigurationEntry 602 }

	ommp81PlusXfpHighTemperatureAlarmSeverity OBJECT-TYPE
		SYNTAX  DisplayString
		MAX-ACCESS  read-write
		STATUS  current
		DESCRIPTION
			"Set or Get the alarm severity level of the
			OMMP81-PLUS XFP High Temperature Alarm   
			for requested port
			-----------------------------
			ommp81PlusInterfaceNumber:
			9 - LINE-1
			-----------------------------
			Value:
			critical
			major
			minor
			deferred
			---------------------------"
	::= { ommp81PlusConfigurationEntry 603 }

	ommp81PlusXfpLowTemperatureAlarmSeverity OBJECT-TYPE
		SYNTAX  DisplayString
		MAX-ACCESS  read-write
		STATUS  current
		DESCRIPTION
			"Set or Get the alarm severity level of the
			OMMP81-PLUS XFP Low Temperature Alarm   
			for requested port
			-----------------------------
			ommp81PlusInterfaceNumber:
			9 - LINE-1
			-----------------------------
			Value:
			critical
			major
			minor
			deferred
			---------------------------"
	::= { ommp81PlusConfigurationEntry 604 }

	ommp81PlusXfpHighTemperatureWarningSeverity OBJECT-TYPE
		SYNTAX  DisplayString
		MAX-ACCESS  read-write
		STATUS  current
		DESCRIPTION
			"Set or Get the alarm severity level of the
			OMMP81-PLUS XFP High Temperature Warning   
			for requested port
			-----------------------------
			ommp81PlusInterfaceNumber:
			9 - LINE-1
			-----------------------------
			Value:
			critical
			major
			minor
			deferred
			---------------------------"
	::= { ommp81PlusConfigurationEntry 605 }

	ommp81PlusXfpLowTemperatureWarningSeverity OBJECT-TYPE
		SYNTAX  DisplayString
		MAX-ACCESS  read-write
		STATUS  current
		DESCRIPTION
			"Set or Get the alarm severity level of the
			OMMP81-PLUS XFP Low Temperature Warning   
			for requested port
			-----------------------------
			ommp81PlusInterfaceNumber:
			9 - LINE-1
			-----------------------------
			Value:
			critical
			major
			minor
			deferred
			---------------------------"
	::= { ommp81PlusConfigurationEntry 606 }

	ommp81PlusXfpHighBiasCurrentAlarmSeverity OBJECT-TYPE
		SYNTAX  DisplayString
		MAX-ACCESS  read-write
		STATUS  current
		DESCRIPTION
			"Set or Get the alarm severity level of the
			OMMP81-PLUS XFP High Bias Current Alarm   
			for requested port
			-----------------------------
			ommp81PlusInterfaceNumber:
			9 - LINE-1
			-----------------------------
			Value:
			critical
			major
			minor
			deferred
			---------------------------"
	::= { ommp81PlusConfigurationEntry 607 }

	ommp81PlusXfpLowBiasCurrentAlarmSeverity OBJECT-TYPE
		SYNTAX  DisplayString
		MAX-ACCESS  read-write
		STATUS  current
		DESCRIPTION
			"Set or Get the alarm severity level of the
			OMMP81-PLUS XFP Low Bias Current Alarm   
			for requested port
			-----------------------------
			ommp81PlusInterfaceNumber:
			9 - LINE-1
			-----------------------------
			Value:
			critical
			major
			minor
			deferred
			---------------------------"
	::= { ommp81PlusConfigurationEntry 608 }

	ommp81PlusXfpHighBiasCurrentWarningSeverity OBJECT-TYPE
		SYNTAX  DisplayString
		MAX-ACCESS  read-write
		STATUS  current
		DESCRIPTION
			"Set or Get the alarm severity level of the
			OMMP81-PLUS XFP High Bias Current Warning   
			for requested port
			-----------------------------
			ommp81PlusInterfaceNumber:
			9 - LINE-1
			-----------------------------
			Value:
			critical
			major
			minor
			deferred
			---------------------------"
	::= { ommp81PlusConfigurationEntry 609 }

	ommp81PlusXfpLowBiasCurrentWarningSeverity OBJECT-TYPE
		SYNTAX  DisplayString
		MAX-ACCESS  read-write
		STATUS  current
		DESCRIPTION
			"Set or Get the alarm severity level of the
			OMMP81-PLUS XFP Low Bias Current Warning   
			for requested port
			-----------------------------
			ommp81PlusInterfaceNumber:
			9 - LINE-1
			-----------------------------
			Value:
			critical
			major
			minor
			deferred
			---------------------------"
	::= { ommp81PlusConfigurationEntry 610 }

	ommp81PlusXfpInputHighPowerAlarmSeverity OBJECT-TYPE
		SYNTAX  DisplayString
		MAX-ACCESS  read-write
		STATUS  current
		DESCRIPTION
			"Set or Get the alarm severity level of the
			OMMP81-PLUS XFP Input High Power Alarm   
			for requested port
			-----------------------------
			ommp81PlusInterfaceNumber:
			9 - LINE-1
			-----------------------------
			Value:
			critical
			major
			minor
			deferred
			---------------------------"
	::= { ommp81PlusConfigurationEntry 611 }

	ommp81PlusXfpInputLowPowerAlarmSeverity OBJECT-TYPE
		SYNTAX  DisplayString
		MAX-ACCESS  read-write
		STATUS  current
		DESCRIPTION
			"Set or Get the alarm severity level of the
			OMMP81-PLUS XFP Input Low Power Alarm   
			for requested port
			-----------------------------
			ommp81PlusInterfaceNumber:
			9 - LINE-1
			-----------------------------
			Value:
			critical
			major
			minor
			deferred
			---------------------------"
	::= { ommp81PlusConfigurationEntry 612 }

	ommp81PlusXfpInputHighPowerWarningSeverity OBJECT-TYPE
		SYNTAX  DisplayString
		MAX-ACCESS  read-write
		STATUS  current
		DESCRIPTION
			"Set or Get the alarm severity level of the
			OMMP81-PLUS XFP Input High Power Warning   
			for requested port
			-----------------------------
			ommp81PlusInterfaceNumber:
			9 - LINE-1
			-----------------------------
			Value:
			critical
			major
			minor
			deferred
			---------------------------"
	::= { ommp81PlusConfigurationEntry 613 }

	ommp81PlusXfpInputLowPowerWarningSeverity OBJECT-TYPE
		SYNTAX  DisplayString
		MAX-ACCESS  read-write
		STATUS  current
		DESCRIPTION
			"Set or Get the alarm severity level of the
			OMMP81-PLUS XFP Input Low Power Warning   
			for requested port
			-----------------------------
			ommp81PlusInterfaceNumber:
			9 - LINE-1
			-----------------------------
			Value:
			critical
			major
			minor
			deferred
			---------------------------"
	::= { ommp81PlusConfigurationEntry 614 }

	ommp81PlusXfpOutputHighPowerAlarmSeverity OBJECT-TYPE
		SYNTAX  DisplayString
		MAX-ACCESS  read-write
		STATUS  current
		DESCRIPTION
			"Set or Get the alarm severity level of the
			OMMP81-PLUS XFP Output High Power Alarm   
			for requested port
			-----------------------------
			ommp81PlusInterfaceNumber:
			9 - LINE-1
			-----------------------------
			Value:
			critical
			major
			minor
			deferred
			---------------------------"
	::= { ommp81PlusConfigurationEntry 615 }

	ommp81PlusXfpOutputLowPowerAlarmSeverity OBJECT-TYPE
		SYNTAX  DisplayString
		MAX-ACCESS  read-write
		STATUS  current
		DESCRIPTION
			"Set or Get the alarm severity level of the
			OMMP81-PLUS XFP Output Low Power Alarm   
			for requested port
			-----------------------------
			ommp81PlusInterfaceNumber:
			9 - LINE-1
			-----------------------------
			Value:
			critical
			major
			minor
			deferred
			---------------------------"
	::= { ommp81PlusConfigurationEntry 616 }

	ommp81PlusXfpOutputHighPowerWarningSeverity OBJECT-TYPE
		SYNTAX  DisplayString
		MAX-ACCESS  read-write
		STATUS  current
		DESCRIPTION
			"Set or Get the alarm severity level of the
			OMMP81-PLUS XFP Output High Power Warning   
			for requested port
			-----------------------------
			ommp81PlusInterfaceNumber:
			9 - LINE-1
			-----------------------------
			Value:
			critical
			major
			minor
			deferred
			---------------------------"
	::= { ommp81PlusConfigurationEntry 617 }

	ommp81PlusXfpOutputLowPowerWarningSeverity OBJECT-TYPE
		SYNTAX  DisplayString
		MAX-ACCESS  read-write
		STATUS  current
		DESCRIPTION
			"Set or Get the alarm severity level of the
			OMMP81-PLUS XFP Output Low Power Warning   
			for requested port
			-----------------------------
			ommp81PlusInterfaceNumber:
			9 - LINE-1
			-----------------------------
			Value:
			critical
			major
			minor
			deferred
			---------------------------"
	::= { ommp81PlusConfigurationEntry 618 }

	ommp81PlusXfpHighSupplyVoltageAlarmSeverity OBJECT-TYPE
		SYNTAX  DisplayString
		MAX-ACCESS  read-write
		STATUS  current
		DESCRIPTION
			"Set or Get the alarm severity level of the
			OMMP81-PLUS XFP High Supply Voltage Alarm   
			for requested port
			-----------------------------
			ommp81PlusInterfaceNumber:
			9 - LINE-1
			-----------------------------
			Value:
			critical
			major
			minor
			deferred
			---------------------------"
	::= { ommp81PlusConfigurationEntry 619 }

	ommp81PlusXfpLowSupplyVoltageAlarmSeverity OBJECT-TYPE
		SYNTAX  DisplayString
		MAX-ACCESS  read-write
		STATUS  current
		DESCRIPTION
			"Set or Get the alarm severity level of the
			OMMP81-PLUS XFP Low Supply Voltage Alarm   
			for requested port
			-----------------------------
			ommp81PlusInterfaceNumber:
			9 - LINE-1
			-----------------------------
			Value:
			critical
			major
			minor
			deferred
			---------------------------"
	::= { ommp81PlusConfigurationEntry 620 }

	ommp81PlusXfpHighSupplyVoltageWarningSeverity OBJECT-TYPE
		SYNTAX  DisplayString
		MAX-ACCESS  read-write
		STATUS  current
		DESCRIPTION
			"Set or Get the alarm severity level of the
			OMMP81-PLUS XFP High Supply Voltage Warning   
			for requested port
			-----------------------------
			ommp81PlusInterfaceNumber:
			9 - LINE-1
			-----------------------------
			Value:
			critical
			major
			minor
			deferred
			---------------------------"
	::= { ommp81PlusConfigurationEntry 621 }

	ommp81PlusXfpLowSupplyVoltageWarningSeverity OBJECT-TYPE
		SYNTAX  DisplayString
		MAX-ACCESS  read-write
		STATUS  current
		DESCRIPTION
			"Set or Get the alarm severity level of the
			OMMP81-PLUS XFP Low Supply Voltage Warning   
			for requested port
			-----------------------------
			ommp81PlusInterfaceNumber:
			9 - LINE-1
			-----------------------------
			Value:
			critical
			major
			minor
			deferred
			---------------------------"
	::= { ommp81PlusConfigurationEntry 622 }

	ommp81PlusXfpPresenceAbsenceNotificationSeverity OBJECT-TYPE
		SYNTAX  DisplayString
		MAX-ACCESS  read-write
		STATUS  current
		DESCRIPTION
			"Set or Get the alarm severity level of the
			OMMP81-PLUS XFP Presence Absence Notification   
			for requested port
			-----------------------------
			ommp81PlusInterfaceNumber:
			9 - LINE-1
			-----------------------------
			Value:
			critical
			major
			minor
			deferred
			---------------------------"
	::= { ommp81PlusConfigurationEntry 623 }

	ommp81PlusSfpInputPowerFailureAlarmSeverity OBJECT-TYPE
		SYNTAX  DisplayString
		MAX-ACCESS  read-write
		STATUS  current
		DESCRIPTION
			"Set or Get the alarm severity level of the
			OMMP81-PLUS SFP Input Power Failure Alarm   
			for requested port
			-----------------------------
			ommp81PlusInterfaceNumber:
			1 to 8 - CLIENT-1 to CLIENT-8
			-----------------------------
			Value:
			critical
			major
			minor
			deferred
			---------------------------"
	::= { ommp81PlusConfigurationEntry 641 }

	ommp81PlusSfpOutputPowerFailureAlarmSeverity OBJECT-TYPE
		SYNTAX  DisplayString
		MAX-ACCESS  read-write
		STATUS  current
		DESCRIPTION
			"Set or Get the alarm severity level of the
			OMMP81-PLUS SFP Output Power Failure Alarm   
			for requested port
			-----------------------------
			ommp81PlusInterfaceNumber:
			1 to 8 - CLIENT-1 to CLIENT-8
			-----------------------------
			Value:
			critical
			major
			minor
			deferred
			---------------------------"
	::= { ommp81PlusConfigurationEntry 642 }

	ommp81PlusSfpHighTemperatureAlarmSeverity OBJECT-TYPE
		SYNTAX  DisplayString
		MAX-ACCESS  read-write
		STATUS  current
		DESCRIPTION
			"Set or Get the alarm severity level of the
			OMMP81-PLUS SFP High Temperature Alarm   
			for requested port
			-----------------------------
			ommp81PlusInterfaceNumber:
			1 to 8 - CLIENT-1 to CLIENT-8
			-----------------------------
			Value:
			critical
			major
			minor
			deferred
			---------------------------"
	::= { ommp81PlusConfigurationEntry 643 }

	ommp81PlusSfpLowTemperatureAlarmSeverity OBJECT-TYPE
		SYNTAX  DisplayString
		MAX-ACCESS  read-write
		STATUS  current
		DESCRIPTION
			"Set or Get the alarm severity level of the
			OMMP81-PLUS SFP Low Temperature Alarm   
			for requested port
			-----------------------------
			ommp81PlusInterfaceNumber:
			1 to 8 - CLIENT-1 to CLIENT-8
			-----------------------------
			Value:
			critical
			major
			minor
			deferred
			---------------------------"
	::= { ommp81PlusConfigurationEntry 644 }

	ommp81PlusSfpHighTemperatureWarningSeverity OBJECT-TYPE
		SYNTAX  DisplayString
		MAX-ACCESS  read-write
		STATUS  current
		DESCRIPTION
			"Set or Get the alarm severity level of the
			OMMP81-PLUS SFP High Temperature Warning   
			for requested port
			-----------------------------
			ommp81PlusInterfaceNumber:
			1 to 8 - CLIENT-1 to CLIENT-8
			-----------------------------
			Value:
			critical
			major
			minor
			deferred
			---------------------------"
	::= { ommp81PlusConfigurationEntry 645 }

	ommp81PlusSfpLowTemperatureWarningSeverity OBJECT-TYPE
		SYNTAX  DisplayString
		MAX-ACCESS  read-write
		STATUS  current
		DESCRIPTION
			"Set or Get the alarm severity level of the
			OMMP81-PLUS SFP Low Temperature Warning   
			for requested port
			-----------------------------
			ommp81PlusInterfaceNumber:
			1 to 8 - CLIENT-1 to CLIENT-8
			-----------------------------
			Value:
			critical
			major
			minor
			deferred
			---------------------------"
	::= { ommp81PlusConfigurationEntry 646 }

	ommp81PlusSfpHighBiasCurrentAlarmSeverity OBJECT-TYPE
		SYNTAX  DisplayString
		MAX-ACCESS  read-write
		STATUS  current
		DESCRIPTION
			"Set or Get the alarm severity level of the
			OMMP81-PLUS SFP High Bias Current Alarm   
			for requested port
			-----------------------------
			ommp81PlusInterfaceNumber:
			1 to 8 - CLIENT-1 to CLIENT-8
			-----------------------------
			Value:
			critical
			major
			minor
			deferred
			---------------------------"
	::= { ommp81PlusConfigurationEntry 647 }

	ommp81PlusSfpLowBiasCurrentAlarmSeverity OBJECT-TYPE
		SYNTAX  DisplayString
		MAX-ACCESS  read-write
		STATUS  current
		DESCRIPTION
			"Set or Get the alarm severity level of the
			OMMP81-PLUS SFP Low Bias Current Alarm   
			for requested port
			-----------------------------
			ommp81PlusInterfaceNumber:
			1 to 8 - CLIENT-1 to CLIENT-8
			-----------------------------
			Value:
			critical
			major
			minor
			deferred
			---------------------------"
	::= { ommp81PlusConfigurationEntry 648 }

	ommp81PlusSfpHighBiasCurrentWarningSeverity OBJECT-TYPE
		SYNTAX  DisplayString
		MAX-ACCESS  read-write
		STATUS  current
		DESCRIPTION
			"Set or Get the alarm severity level of the
			OMMP81-PLUS SFP High Bias Current Warning   
			for requested port
			-----------------------------
			ommp81PlusInterfaceNumber:
			1 to 8 - CLIENT-1 to CLIENT-8
			-----------------------------
			Value:
			critical
			major
			minor
			deferred
			---------------------------"
	::= { ommp81PlusConfigurationEntry 649 }

	ommp81PlusSfpLowBiasCurrentWarningSeverity OBJECT-TYPE
		SYNTAX  DisplayString
		MAX-ACCESS  read-write
		STATUS  current
		DESCRIPTION
			"Set or Get the alarm severity level of the
			OMMP81-PLUS SFP Low Bias Current Warning   
			for requested port
			-----------------------------
			ommp81PlusInterfaceNumber:
			1 to 8 - CLIENT-1 to CLIENT-8
			-----------------------------
			Value:
			critical
			major
			minor
			deferred
			---------------------------"
	::= { ommp81PlusConfigurationEntry 650 }

	ommp81PlusSfpInputHighPowerAlarmSeverity OBJECT-TYPE
		SYNTAX  DisplayString
		MAX-ACCESS  read-write
		STATUS  current
		DESCRIPTION
			"Set or Get the alarm severity level of the
			OMMP81-PLUS SFP Input High Power Alarm   
			for requested port
			-----------------------------
			ommp81PlusInterfaceNumber:
			1 to 8 - CLIENT-1 to CLIENT-8
			-----------------------------
			Value:
			critical
			major
			minor
			deferred
			---------------------------"
	::= { ommp81PlusConfigurationEntry 651 }

	ommp81PlusSfpInputLowPowerAlarmSeverity OBJECT-TYPE
		SYNTAX  DisplayString
		MAX-ACCESS  read-write
		STATUS  current
		DESCRIPTION
			"Set or Get the alarm severity level of the
			OMMP81-PLUS SFP Input Low Power Alarm   
			for requested port
			-----------------------------
			ommp81PlusInterfaceNumber:
			1 to 8 - CLIENT-1 to CLIENT-8
			-----------------------------
			Value:
			critical
			major
			minor
			deferred
			---------------------------"
	::= { ommp81PlusConfigurationEntry 652 }

	ommp81PlusSfpInputHighPowerWarningSeverity OBJECT-TYPE
		SYNTAX  DisplayString
		MAX-ACCESS  read-write
		STATUS  current
		DESCRIPTION
			"Set or Get the alarm severity level of the
			OMMP81-PLUS SFP Input High Power Warning   
			for requested port
			-----------------------------
			ommp81PlusInterfaceNumber:
			1 to 8 - CLIENT-1 to CLIENT-8
			-----------------------------
			Value:
			critical
			major
			minor
			deferred
			---------------------------"
	::= { ommp81PlusConfigurationEntry 653 }

	ommp81PlusSfpInputLowPowerWarningSeverity OBJECT-TYPE
		SYNTAX  DisplayString
		MAX-ACCESS  read-write
		STATUS  current
		DESCRIPTION
			"Set or Get the alarm severity level of the
			OMMP81-PLUS SFP Input Low Power Warning   
			for requested port
			-----------------------------
			ommp81PlusInterfaceNumber:
			1 to 8 - CLIENT-1 to CLIENT-8
			-----------------------------
			Value:
			critical
			major
			minor
			deferred
			---------------------------"
	::= { ommp81PlusConfigurationEntry 654 }

	ommp81PlusSfpOutputHighPowerAlarmSeverity OBJECT-TYPE
		SYNTAX  DisplayString
		MAX-ACCESS  read-write
		STATUS  current
		DESCRIPTION
			"Set or Get the alarm severity level of the
			OMMP81-PLUS SFP Output High Power Alarm   
			for requested port
			-----------------------------
			ommp81PlusInterfaceNumber:
			1 to 8 - CLIENT-1 to CLIENT-8
			-----------------------------
			Value:
			critical
			major
			minor
			deferred
			---------------------------"
	::= { ommp81PlusConfigurationEntry 655 }

	ommp81PlusSfpOutputLowPowerAlarmSeverity OBJECT-TYPE
		SYNTAX  DisplayString
		MAX-ACCESS  read-write
		STATUS  current
		DESCRIPTION
			"Set or Get the alarm severity level of the
			OMMP81-PLUS SFP Output Low Power Alarm   
			for requested port
			-----------------------------
			ommp81PlusInterfaceNumber:
			1 to 8 - CLIENT-1 to CLIENT-8
			-----------------------------
			Value:
			critical
			major
			minor
			deferred
			---------------------------"
	::= { ommp81PlusConfigurationEntry 656 }

	ommp81PlusSfpOutputHighPowerWarningSeverity OBJECT-TYPE
		SYNTAX  DisplayString
		MAX-ACCESS  read-write
		STATUS  current
		DESCRIPTION
			"Set or Get the alarm severity level of the
			OMMP81-PLUS SFP Output High Power Warning   
			for requested port
			-----------------------------
			ommp81PlusInterfaceNumber:
			1 to 8 - CLIENT-1 to CLIENT-8
			-----------------------------
			Value:
			critical
			major
			minor
			deferred
			---------------------------"
	::= { ommp81PlusConfigurationEntry 657 }

	ommp81PlusSfpOutputLowPowerWarningSeverity OBJECT-TYPE
		SYNTAX  DisplayString
		MAX-ACCESS  read-write
		STATUS  current
		DESCRIPTION
			"Set or Get the alarm severity level of the
			OMMP81-PLUS SFP Output Low Power Warning   
			for requested port
			-----------------------------
			ommp81PlusInterfaceNumber:
			1 to 8 - CLIENT-1 to CLIENT-8
			-----------------------------
			Value:
			critical
			major
			minor
			deferred
			---------------------------"
	::= { ommp81PlusConfigurationEntry 658 }

	ommp81PlusSfpHighSupplyVoltageAlarmSeverity OBJECT-TYPE
		SYNTAX  DisplayString
		MAX-ACCESS  read-write
		STATUS  current
		DESCRIPTION
			"Set or Get the alarm severity level of the
			OMMP81-PLUS SFP High Supply Voltage Alarm   
			for requested port
			-----------------------------
			ommp81PlusInterfaceNumber:
			1 to 8 - CLIENT-1 to CLIENT-8
			-----------------------------
			Value:
			critical
			major
			minor
			deferred
			---------------------------"
	::= { ommp81PlusConfigurationEntry 659 }

	ommp81PlusSfpLowSupplyVoltageAlarmSeverity OBJECT-TYPE
		SYNTAX  DisplayString
		MAX-ACCESS  read-write
		STATUS  current
		DESCRIPTION
			"Set or Get the alarm severity level of the
			OMMP81-PLUS SFP Low Supply Voltage Alarm   
			for requested port
			-----------------------------
			ommp81PlusInterfaceNumber:
			1 to 8 - CLIENT-1 to CLIENT-8
			-----------------------------
			Value:
			critical
			major
			minor
			deferred
			---------------------------"
	::= { ommp81PlusConfigurationEntry 660 }

	ommp81PlusSfpHighSupplyVoltageWarningSeverity OBJECT-TYPE
		SYNTAX  DisplayString
		MAX-ACCESS  read-write
		STATUS  current
		DESCRIPTION
			"Set or Get the alarm severity level of the
			OMMP81-PLUS SFP High Supply Voltage Warning   
			for requested port
			-----------------------------
			ommp81PlusInterfaceNumber:
			1 to 8 - CLIENT-1 to CLIENT-8
			-----------------------------
			Value:
			critical
			major
			minor
			deferred
			---------------------------"
	::= { ommp81PlusConfigurationEntry 661 }

	ommp81PlusSfpLowSupplyVoltageWarningSeverity OBJECT-TYPE
		SYNTAX  DisplayString
		MAX-ACCESS  read-write
		STATUS  current
		DESCRIPTION
			"Set or Get the alarm severity level of the
			OMMP81-PLUS SFP Low Supply Voltage Warning   
			for requested port
			-----------------------------
			ommp81PlusInterfaceNumber:
			1 to 8 - CLIENT-1 to CLIENT-8
			-----------------------------
			Value:
			critical
			major
			minor
			deferred
			---------------------------"
	::= { ommp81PlusConfigurationEntry 662 }

	ommp81PlusSfpPresenceAbsenceNotificationSeverity OBJECT-TYPE
		SYNTAX  DisplayString
		MAX-ACCESS  read-write
		STATUS  current
		DESCRIPTION
			"Set or Get the alarm severity level of the
			OMMP81-PLUS SFP Presence Absence Notification   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 663 }

	ommp81PlusSfpTransmitFaultPresenceAlarmSeverity OBJECT-TYPE
		SYNTAX  DisplayString
		MAX-ACCESS  read-write
		STATUS  current
		DESCRIPTION
			"Set or Get the alarm severity level of the
			OMMP81-PLUS SFP Transmit Fault Presence Alarm   
			for requested port
			-----------------------------
			ommp81PlusInterfaceNumber:
			1 to 8 - CLIENT-1 to CLIENT-8
			-----------------------------
			Value:
			critical
			major
			minor
			deferred
			---------------------------"
	::= { ommp81PlusConfigurationEntry 664 }

	ommp81PlusOtuLossOfSignalAlarmSeverity OBJECT-TYPE
		SYNTAX  DisplayString
		MAX-ACCESS  read-write
		STATUS  current
		DESCRIPTION
			"Set or Get the alarm severity level of the
			OMMP81-PLUS OTU Loss Of Signal Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 681 }

	ommp81PlusOtuLossOfFrameAlarmSeverity OBJECT-TYPE
		SYNTAX  DisplayString
		MAX-ACCESS  read-write
		STATUS  current
		DESCRIPTION
			"Set or Get the alarm severity level of the
			OMMP81-PLUS OTU Loss Of Frame Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 682 }

	ommp81PlusOtuOutOfFrameAlarmSeverity OBJECT-TYPE
		SYNTAX  DisplayString
		MAX-ACCESS  read-write
		STATUS  current
		DESCRIPTION
			"Set or Get the alarm severity level of the
			OMMP81-PLUS OTU Out Of Frame Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 683 }

	ommp81PlusOtuLossOfMultiFrameAlarmSeverity OBJECT-TYPE
		SYNTAX  DisplayString
		MAX-ACCESS  read-write
		STATUS  current
		DESCRIPTION
			"Set or Get the alarm severity level of the
			OMMP81-PLUS OTU Loss Of Multi Frame Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 684 }

	ommp81PlusOtuOutOfMultiFrameAlarmSeverity OBJECT-TYPE
		SYNTAX  DisplayString
		MAX-ACCESS  read-write
		STATUS  current
		DESCRIPTION
			"Set or Get the alarm severity level of the
			OMMP81-PLUS OTU Out Of Multi Frame Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 685 }

	ommp81PlusOtuSignalFailAlarmSeverity OBJECT-TYPE
		SYNTAX  DisplayString
		MAX-ACCESS  read-write
		STATUS  current
		DESCRIPTION
			"Set or Get the alarm severity level of the
			OMMP81-PLUS OTU Signal Fail Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 686 }

	ommp81PlusOtuSignalDegradeAlarmSeverity OBJECT-TYPE
		SYNTAX  DisplayString
		MAX-ACCESS  read-write
		STATUS  current
		DESCRIPTION
			"Set or Get the alarm severity level of the
			OMMP81-PLUS OTU Signal Degrade Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 687 }

	ommp81PlusOtuAlarmIndicationSignalAlarmSeverity OBJECT-TYPE
		SYNTAX  DisplayString
		MAX-ACCESS  read-write
		STATUS  current
		DESCRIPTION
			"Set or Get the alarm severity level of the
			OMMP81-PLUS OTU Alarm Indication Signal Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 688 }

	ommp81PlusOtuIncomingAlignmentErrorAlarmSeverity OBJECT-TYPE
		SYNTAX  DisplayString
		MAX-ACCESS  read-write
		STATUS  current
		DESCRIPTION
			"Set or Get the alarm severity level of the
			OMMP81-PLUS OTU Incoming Alignment Error Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 689 }

	ommp81PlusOtuTraceIdentifierMismatchAlarmSeverity OBJECT-TYPE
		SYNTAX  DisplayString
		MAX-ACCESS  read-write
		STATUS  current
		DESCRIPTION
			"Set or Get the alarm severity level of the
			OMMP81-PLUS OTU Trace Identifier Mismatch Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 690 }

	ommp81PlusOtuBackwardIncomingAlignmentErrorAlarmSeverity OBJECT-TYPE
		SYNTAX  DisplayString
		MAX-ACCESS  read-write
		STATUS  current
		DESCRIPTION
			"Set or Get the alarm severity level of the
			OMMP81-PLUS OTU Backward Incoming Alignment Error Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 691 }

	ommp81PlusOtuBackwardDefectIndicationAlarmSeverity OBJECT-TYPE
		SYNTAX  DisplayString
		MAX-ACCESS  read-write
		STATUS  current
		DESCRIPTION
			"Set or Get the alarm severity level of the
			OMMP81-PLUS OTU Backward Defect Indication Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 692 }

	ommp81PlusOduSignalFailAlarmSeverity OBJECT-TYPE
		SYNTAX  DisplayString
		MAX-ACCESS  read-write
		STATUS  current
		DESCRIPTION
			"Set or Get the alarm severity level of the
			OMMP81-PLUS ODU Signal Fail Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 711 }

	ommp81PlusOduSignalDegradeAlarmSeverity OBJECT-TYPE
		SYNTAX  DisplayString
		MAX-ACCESS  read-write
		STATUS  current
		DESCRIPTION
			"Set or Get the alarm severity level of the
			OMMP81-PLUS ODU Signal Degrade Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 712 }

	ommp81PlusOduAlarmIndicationSignalAlarmSeverity OBJECT-TYPE
		SYNTAX  DisplayString
		MAX-ACCESS  read-write
		STATUS  current
		DESCRIPTION
			"Set or Get the alarm severity level of the
			OMMP81-PLUS ODU Alarm Indication Signal Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 713 }

	ommp81PlusOduTcm1IncomingAlignmentErrorAlarmSeverity OBJECT-TYPE
		SYNTAX  DisplayString
		MAX-ACCESS  read-write
		STATUS  current
		DESCRIPTION
			"Set or Get the alarm severity level of the
			OMMP81-PLUS ODU TCM1 Incoming Alignment Error Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 714 }

	ommp81PlusOduTcm2IncomingAlignmentErrorAlarmSeverity OBJECT-TYPE
		SYNTAX  DisplayString
		MAX-ACCESS  read-write
		STATUS  current
		DESCRIPTION
			"Set or Get the alarm severity level of the
			OMMP81-PLUS ODU TCM2 Incoming Alignment Error Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 715 }

	ommp81PlusOduTcm3IncomingAlignmentErrorAlarmSeverity OBJECT-TYPE
		SYNTAX  DisplayString
		MAX-ACCESS  read-write
		STATUS  current
		DESCRIPTION
			"Set or Get the alarm severity level of the
			OMMP81-PLUS ODU TCM3 Incoming Alignment Error Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 716 }

	ommp81PlusOduTcm4IncomingAlignmentErrorAlarmSeverity OBJECT-TYPE
		SYNTAX  DisplayString
		MAX-ACCESS  read-write
		STATUS  current
		DESCRIPTION
			"Set or Get the alarm severity level of the
			OMMP81-PLUS ODU TCM4 Incoming Alignment Error Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 717 }

	ommp81PlusOduTcm5IncomingAlignmentErrorAlarmSeverity OBJECT-TYPE
		SYNTAX  DisplayString
		MAX-ACCESS  read-write
		STATUS  current
		DESCRIPTION
			"Set or Get the alarm severity level of the
			OMMP81-PLUS ODU TCM5 Incoming Alignment Error Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 718 }

	ommp81PlusOduTcm6IncomingAlignmentErrorAlarmSeverity OBJECT-TYPE
		SYNTAX  DisplayString
		MAX-ACCESS  read-write
		STATUS  current
		DESCRIPTION
			"Set or Get the alarm severity level of the
			OMMP81-PLUS ODU TCM6 Incoming Alignment Error Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 719 }

	ommp81PlusOduTraceIdentifierMismatchAlarmSeverity OBJECT-TYPE
		SYNTAX  DisplayString
		MAX-ACCESS  read-write
		STATUS  current
		DESCRIPTION
			"Set or Get the alarm severity level of the
			OMMP81-PLUS ODU Trace Identifier Mismatch Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 720 }

	ommp81PlusOduLockedDefectAlarmSeverity OBJECT-TYPE
		SYNTAX  DisplayString
		MAX-ACCESS  read-write
		STATUS  current
		DESCRIPTION
			"Set or Get the alarm severity level of the
			OMMP81-PLUS ODU Locked Defect Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 721 }

	ommp81PlusOduOpenConnectionIndicationAlarmSeverity OBJECT-TYPE
		SYNTAX  DisplayString
		MAX-ACCESS  read-write
		STATUS  current
		DESCRIPTION
			"Set or Get the alarm severity level of the
			OMMP81-PLUS ODU Open Connection Indication Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 722 }

	ommp81PlusOduBackwardDefectIndicationAlarmSeverity OBJECT-TYPE
		SYNTAX  DisplayString
		MAX-ACCESS  read-write
		STATUS  current
		DESCRIPTION
			"Set or Get the alarm severity level of the
			OMMP81-PLUS ODU Backward Defect Indication Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 723 }

	ommp81PlusOduTcm1BackwardIncomingAlignmentErrorAlarmSeverity OBJECT-TYPE
		SYNTAX  DisplayString
		MAX-ACCESS  read-write
		STATUS  current
		DESCRIPTION
			"Set or Get the alarm severity level of the
			OMMP81-PLUS ODU TCM1 Backward Incoming Alignment Error
			Alarm for requested port
			-----------------------------
			ommp81PlusInterfaceNumber:
			1 to 8 - CLIENT-1 to CLIENT-8
			9 - LINE-1
			-----------------------------
			Value:
			critical
			major
			minor
			deferred
			---------------------------"
	::= { ommp81PlusConfigurationEntry 724 }

	ommp81PlusOduTcm2BackwardIncomingAlignmentErrorAlarmSeverity OBJECT-TYPE
		SYNTAX  DisplayString
		MAX-ACCESS  read-write
		STATUS  current
		DESCRIPTION
			"Set or Get the alarm severity level of the
			OMMP81-PLUS ODU TCM2 Backward Incoming Alignment Error
			Alarm for requested port
			-----------------------------
			ommp81PlusInterfaceNumber:
			1 to 8 - CLIENT-1 to CLIENT-8
			9 - LINE-1
			-----------------------------
			Value:
			critical
			major
			minor
			deferred
			---------------------------"
	::= { ommp81PlusConfigurationEntry 725 }

	ommp81PlusOduTcm3BackwardIncomingAlignmentErrorAlarmSeverity OBJECT-TYPE
		SYNTAX  DisplayString
		MAX-ACCESS  read-write
		STATUS  current
		DESCRIPTION
			"Set or Get the alarm severity level of the
			OMMP81-PLUS ODU TCM3 Backward Incoming Alignment Error
			Alarm for requested port
			-----------------------------
			ommp81PlusInterfaceNumber:
			1 to 8 - CLIENT-1 to CLIENT-8
			9 - LINE-1
			-----------------------------
			Value:
			critical
			major
			minor
			deferred
			---------------------------"
	::= { ommp81PlusConfigurationEntry 726 }

	ommp81PlusOduTcm4BackwardIncomingAlignmentErrorAlarmSeverity OBJECT-TYPE
		SYNTAX  DisplayString
		MAX-ACCESS  read-write
		STATUS  current
		DESCRIPTION
			"Set or Get the alarm severity level of the
			OMMP81-PLUS ODU TCM4 Backward Incoming Alignment Error
			Alarm for requested port
			-----------------------------
			ommp81PlusInterfaceNumber:
			1 to 8 - CLIENT-1 to CLIENT-8
			9 - LINE-1
			-----------------------------
			Value:
			critical
			major
			minor
			deferred
			---------------------------"
	::= { ommp81PlusConfigurationEntry 727 }

	ommp81PlusOduTcm5BackwardIncomingAlignmentErrorAlarmSeverity OBJECT-TYPE
		SYNTAX  DisplayString
		MAX-ACCESS  read-write
		STATUS  current
		DESCRIPTION
			"Set or Get the alarm severity level of the
			OMMP81-PLUS ODU TCM5 Backward Incoming Alignment Error
			Alarm for requested port
			-----------------------------
			ommp81PlusInterfaceNumber:
			1 to 8 - CLIENT-1 to CLIENT-8
			9 - LINE-1
			-----------------------------
			Value:
			critical
			major
			minor
			deferred
			---------------------------"
	::= { ommp81PlusConfigurationEntry 728 }

	ommp81PlusOduTcm6BackwardIncomingAlignmentErrorAlarmSeverity OBJECT-TYPE
		SYNTAX  DisplayString
		MAX-ACCESS  read-write
		STATUS  current
		DESCRIPTION
			"Set or Get the alarm severity level of the
			OMMP81-PLUS ODU TCM6 Backward Incoming Alignment Error
			Alarm for requested port
			-----------------------------
			ommp81PlusInterfaceNumber:
			1 to 8 - CLIENT-1 to CLIENT-8
			9 - LINE-1
			-----------------------------
			Value:
			critical
			major
			minor
			deferred
			---------------------------"
	::= { ommp81PlusConfigurationEntry 729 }

	ommp81PlusOduLossOfFrameLossOfMultiframeAlarmSeverity OBJECT-TYPE
		SYNTAX  DisplayString
		MAX-ACCESS  read-write
		STATUS  current
		DESCRIPTION
			"Set or Get the alarm severity level of the
			OMMP81-PLUS ODU Loss Of Frame Loss Of Multiframe Alarm   
			for requested port
			-----------------------------
			ommp81PlusInterfaceNumber:
			1, 2, 3, 4 - Slice number
			-----------------------------
			Value:
			critical
			major
			minor
			deferred
			---------------------------"
	::= { ommp81PlusConfigurationEntry 730 }

	ommp81PlusOpuPayloadMismatchAlarmSeverity OBJECT-TYPE
		SYNTAX  DisplayString
		MAX-ACCESS  read-write
		STATUS  current
		DESCRIPTION
			"Set or Get the alarm severity level of the
			OMMP81-PLUS OPU Payload Mismatch Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 735 }

	ommp81PlusOchLossOfPayloadAlarmSeverity OBJECT-TYPE
		SYNTAX  DisplayString
		MAX-ACCESS  read-write
		STATUS  current
		DESCRIPTION
			"Set or Get the alarm severity level of the
			OMMP81-PLUS OCH Loss Of Payload Alarm   
			for requested port
			-----------------------------
			ommp81PlusInterfaceNumber:
			1 to 8 - CLIENT-1 to CLIENT-8
			9 - LINE-1
			-----------------------------
			Value:
			critical
			major
			minor
			deferred
			---------------------------"
	::= { ommp81PlusConfigurationEntry 736 }

	ommp81PlusSdhLossOfSignalAlarmSeverity OBJECT-TYPE
		SYNTAX  DisplayString
		MAX-ACCESS  read-write
		STATUS  current
		DESCRIPTION
			"Set or Get the alarm severity level of the
			OMMP81-PLUS SDH Loss Of Signal Alarm   
			for requested port
			-----------------------------
			ommp81PlusInterfaceNumber:
			1 to 8 - CLIENT-1 to CLIENT-8
			-----------------------------
			Value:
			critical
			major
			minor
			deferred
			---------------------------"
	::= { ommp81PlusConfigurationEntry 741 }

	ommp81PlusSdhOutOfFrameAlarmSeverity OBJECT-TYPE
		SYNTAX  DisplayString
		MAX-ACCESS  read-write
		STATUS  current
		DESCRIPTION
			"Set or Get the alarm severity level of the
			OMMP81-PLUS SDH Out Of Frame Alarm   
			for requested port
			-----------------------------
			ommp81PlusInterfaceNumber:
			1 to 8 - CLIENT-1 to CLIENT-8,
			-----------------------------
			Value:
			critical
			major
			minor
			deferred
			---------------------------"
	::= { ommp81PlusConfigurationEntry 742 }

	ommp81PlusSdhLossOfFrameAlarmSeverity OBJECT-TYPE
		SYNTAX  DisplayString
		MAX-ACCESS  read-write
		STATUS  current
		DESCRIPTION
			"Set or Get the alarm severity level of the
			OMMP81-PLUS SDH Loss Of Frame Alarm   
			for requested port
			-----------------------------
			ommp81PlusInterfaceNumber:
			1 to 8 - CLIENT-1 to CLIENT-8
			-----------------------------
			Value:
			critical
			major
			minor
			deferred
			---------------------------"
	::= { ommp81PlusConfigurationEntry 743 }

	ommp81PlusSdhRsAlarmIndicationSignalAlarmSeverity OBJECT-TYPE
		SYNTAX  DisplayString
		MAX-ACCESS  read-write
		STATUS  current
		DESCRIPTION
			"Set or Get the alarm severity level of the
			OMMP81-PLUS SDH Rs Alarm Indication Signal Alarm   
			for requested port
			-----------------------------
			ommp81PlusInterfaceNumber:
			1 to 8 - CLIENT-1 to CLIENT-8
			-----------------------------
			Value:
			critical
			major
			minor
			deferred
			---------------------------"
	::= { ommp81PlusConfigurationEntry 744 }

	ommp81PlusSdhRsTraceIdentifierMismatchAlarmSeverity OBJECT-TYPE
		SYNTAX  DisplayString
		MAX-ACCESS  read-write
		STATUS  current
		DESCRIPTION
			"Set or Get the alarm severity level of the
			OMMP81-PLUS SDH Rs Trace Identifier Mismatch Alarm   
			for requested port
			-----------------------------
			ommp81PlusInterfaceNumber:
			1 to 8 - CLIENT-1 to CLIENT-8
			-----------------------------
			Value:
			critical
			major
			minor
			deferred
			---------------------------"
	::= { ommp81PlusConfigurationEntry 745 }

	ommp81PlusSdhAuAlarmIndicationSignalAlarmSeverity OBJECT-TYPE
		SYNTAX  DisplayString
		MAX-ACCESS  read-write
		STATUS  current
		DESCRIPTION
			"Set or Get the alarm severity level of the
			OMMP81-PLUS SDH Au Alarm Indication Signal Alarm   
			for requested port
			-----------------------------
			ommp81PlusInterfaceNumber:
			1 to 8 - CLIENT-1 to CLIENT-8
			-----------------------------
			Value:
			critical
			major
			minor
			deferred
			---------------------------"
	::= { ommp81PlusConfigurationEntry 746 }

	ommp81PlusSdhAuLossOfPointerAlarmSeverity OBJECT-TYPE
		SYNTAX  DisplayString
		MAX-ACCESS  read-write
		STATUS  current
		DESCRIPTION
			"Set or Get the alarm severity level of the
			OMMP81-PLUS SDH Au Loss Of Pointer Alarm   
			for requested port
			-----------------------------
			ommp81PlusInterfaceNumber:
			1 to 8 - CLIENT-1 to CLIENT-8
			-----------------------------
			Value:
			critical
			major
			minor
			deferred
			---------------------------"
	::= { ommp81PlusConfigurationEntry 747 }

	ommp81PlusSdhMsAlarmIndicationSignalAlarmSeverity OBJECT-TYPE
		SYNTAX  DisplayString
		MAX-ACCESS  read-write
		STATUS  current
		DESCRIPTION
			"Set or Get the alarm severity level of the
			OMMP81-PLUS SDH Ms Alarm Indication Signal Alarm   
			for requested port
			-----------------------------
			ommp81PlusInterfaceNumber:
			1 to 8 - CLIENT-1 to CLIENT-8
			-----------------------------
			Value:
			critical
			major
			minor
			deferred
			---------------------------"
	::= { ommp81PlusConfigurationEntry 748 }

	ommp81PlusSdhMsRemoteErrorIndicationAlarmSeverity OBJECT-TYPE
		SYNTAX  DisplayString
		MAX-ACCESS  read-write
		STATUS  current
		DESCRIPTION
			"Set or Get the alarm severity level of the
			OMMP81-PLUS SDH Ms Remote Error Indication Alarm   
			for requested port
			-----------------------------
			ommp81PlusInterfaceNumber:
			1 to 8 - CLIENT-1 to CLIENT-8
			-----------------------------
			Value:
			critical
			major
			minor
			deferred
			---------------------------"
	::= { ommp81PlusConfigurationEntry 749 }

	ommp81PlusSdhMsRemoteDefectIndicationAlarmSeverity OBJECT-TYPE
		SYNTAX  DisplayString
		MAX-ACCESS  read-write
		STATUS  current
		DESCRIPTION
			"Set or Get the alarm severity level of the
			OMMP81-PLUS SDH Ms Remote Defect Indication Alarm   
			for requested port
			-----------------------------
			ommp81PlusInterfaceNumber:
			1 to 8 - CLIENT-1 to CLIENT-8
			-----------------------------
			Value:
			critical
			major
			minor
			deferred
			---------------------------"
	::= { ommp81PlusConfigurationEntry 750 }

	ommp81PlusSdhMsRemoteFailureIndicationAlarmSeverity OBJECT-TYPE
		SYNTAX  DisplayString
		MAX-ACCESS  read-write
		STATUS  current
		DESCRIPTION
			"Set or Get the alarm severity level of the
			OMMP81-PLUS SDH Ms Remote Failure Indication Alarm   
			for requested port
			-----------------------------
			ommp81PlusInterfaceNumber:
			1 to 8 - CLIENT-1 to CLIENT-8
			-----------------------------
			Value:
			critical
			major
			minor
			deferred
			---------------------------"
	::= { ommp81PlusConfigurationEntry 751 }

	ommp81PlusSdhMsB2ExcessiveErrorAlarmSeverity OBJECT-TYPE
		SYNTAX  DisplayString
		MAX-ACCESS  read-write
		STATUS  current
		DESCRIPTION
			"Set or Get the alarm severity level of the
			OMMP81-PLUS SDH Ms B2 Signal Fail Alarm   
			for requested port
			-----------------------------
			ommp81PlusInterfaceNumber:
			1 to 8 - CLIENT-1 to CLIENT-8
			-----------------------------
			Value:
			critical
			major
			minor
			deferred
			---------------------------"
	::= { ommp81PlusConfigurationEntry 752 }

	ommp81PlusSdhMsB2SignalDegradeAlarmSeverity OBJECT-TYPE
		SYNTAX  DisplayString
		MAX-ACCESS  read-write
		STATUS  current
		DESCRIPTION
			"Set or Get the alarm severity level of the
			OMMP81-PLUS SDH Ms B2 Signal Degrade Alarm   
			for requested port
			-----------------------------
			ommp81PlusInterfaceNumber:
			1 to 8 - CLIENT-1 to CLIENT-8
			-----------------------------
			Value:
			critical
			major
			minor
			deferred
			---------------------------"
	::= { ommp81PlusConfigurationEntry 753 }

	ommp81PlusSdhLossOfSequenceSynchronisationAlarmSeverity OBJECT-TYPE
		SYNTAX  DisplayString
		MAX-ACCESS  read-write
		STATUS  current
		DESCRIPTION
			"Set or Get the alarm severity level of the
			OMMP81-PLUS SDH Loss Of Sequence Synchronisation Alarm   
			for requested port
			-----------------------------
			ommp81PlusInterfaceNumber:
			1 to 8 - CLIENT-1 to CLIENT-8
			-----------------------------
			Value:
			critical
			major
			minor
			deferred
			---------------------------"
	::= { ommp81PlusConfigurationEntry 754 }

	ommp81PlusSdhLowerOrderPathPayloadLabelMismatchAlarmSeverity OBJECT-TYPE
		SYNTAX  DisplayString
		MAX-ACCESS  read-write
		STATUS  current
		DESCRIPTION
			"Set or Get the alarm severity level of the
			OMMP81-PLUS SDH Lower Order Path Payload Label Mismatch Alarm   
			for requested port
			-----------------------------
			ommp81PlusInterfaceNumber:
			1 to 8 - CLIENT-1 to CLIENT-8
			-----------------------------
			Value:
			critical
			major
			minor
			deferred
			---------------------------"
	::= { ommp81PlusConfigurationEntry 755 }

	ommp81PlusSdhLowerOrderPathUnequippedAlarmSeverity OBJECT-TYPE
		SYNTAX  DisplayString
		MAX-ACCESS  read-write
		STATUS  current
		DESCRIPTION
			"Set or Get the alarm severity level of the
			OMMP81-PLUS SDH Lower Order Path Unequipped Alarm   
			for requested port
			-----------------------------
			ommp81PlusInterfaceNumber:
			1 to 8 - CLIENT-1 to CLIENT-8
			-----------------------------
			Value:
			critical
			major
			minor
			deferred
			---------------------------"
	::= { ommp81PlusConfigurationEntry 756 }

	ommp81PlusEthernetLossOfSignalAlarmSeverity OBJECT-TYPE
		SYNTAX  DisplayString
		MAX-ACCESS  read-write
		STATUS  current
		DESCRIPTION
			"Set or Get the alarm severity level of the
			OMMP81-PLUS Ethernet Loss Of Signal Alarm   
			for requested port
			-----------------------------
			ommp81PlusInterfaceNumber:
			1 to 8 - CLIENT-1 to CLIENT-8
			-----------------------------
			Value:
			critical
			major
			minor
			deferred
			---------------------------"
	::= { ommp81PlusConfigurationEntry 771 }

	ommp81PlusEthernetLossOfSignalSyncAlarmSeverity OBJECT-TYPE
		SYNTAX  DisplayString
		MAX-ACCESS  read-write
		STATUS  current
		DESCRIPTION
			"Set or Get the alarm severity level of the
			OMMP81-PLUS Ethernet Loss Of Signal Sync Alarm   
			for requested port
			-----------------------------
			ommp81PlusInterfaceNumber:
			1 to 8 - CLIENT-1 to CLIENT-8
			-----------------------------
			Value:
			critical
			major
			minor
			deferred
			---------------------------"
	::= { ommp81PlusConfigurationEntry 772 }

	ommp81PlusEthernetLinkFailureAlarmSeverity OBJECT-TYPE
		SYNTAX  DisplayString
		MAX-ACCESS  read-write
		STATUS  current
		DESCRIPTION
			"Set or Get the alarm severity level of the
			OMMP81-PLUS Ethernet Link Failure Alarm   
			for requested port
			-----------------------------
			ommp81PlusInterfaceNumber:
			1 to 8 - CLIENT-1 to CLIENT-8
			-----------------------------
			Value:
			critical
			major
			minor
			deferred
			---------------------------"
	::= { ommp81PlusConfigurationEntry 773 }

	ommp81PlusEthernetAutoNegotiationAlarmSeverity OBJECT-TYPE
		SYNTAX  DisplayString
		MAX-ACCESS  read-write
		STATUS  current
		DESCRIPTION
			"Set or Get the alarm severity level of the
			OMMP81-PLUS Ethernet Auto Negotiation Alarm   
			for requested port
			-----------------------------
			ommp81PlusInterfaceNumber:
			1 to 8 - CLIENT-1 to CLIENT-8
			-----------------------------
			Value:
			critical
			major
			minor
			deferred
			---------------------------"
	::= { ommp81PlusConfigurationEntry 774 }

	ommp81PlusEthernetFrameCheckSequenceAlarmSeverity OBJECT-TYPE
		SYNTAX  DisplayString
		MAX-ACCESS  read-write
		STATUS  current
		DESCRIPTION
			"Set or Get the alarm severity level of the
			OMMP81-PLUS Ethernet Frame Check Sequence Alarm   
			for requested port
			-----------------------------
			ommp81PlusInterfaceNumber:
			1 to 8 - CLIENT-1 to CLIENT-8
			-----------------------------
			Value:
			critical
			major
			minor
			deferred
			---------------------------"
	::= { ommp81PlusConfigurationEntry 775 }

	ommp81PlusEthernetCarrierStatusAlarmSeverity OBJECT-TYPE
		SYNTAX  DisplayString
		MAX-ACCESS  read-write
		STATUS  current
		DESCRIPTION
			"Set or Get the alarm severity level of the
			OMMP81-PLUS Ethernet Carrier Status Alarm   
			for requested port
			-----------------------------
			ommp81PlusInterfaceNumber:
			1 to 8 - CLIENT-1 to CLIENT-8
			-----------------------------
			Value:
			critical
			major
			minor
			deferred
			---------------------------"
	::= { ommp81PlusConfigurationEntry 776 }

	ommp81PlusEthernetHighBerAlarmSeverity OBJECT-TYPE
		SYNTAX  DisplayString
		MAX-ACCESS  read-write
		STATUS  current
		DESCRIPTION
			"Set or Get the alarm severity level of the
			OMMP81-PLUS Ethernet High Ber Alarm   
			for requested port
			-----------------------------
			ommp81PlusInterfaceNumber:
			1 to 8 - CLIENT-1 to CLIENT-8
			-----------------------------
			Value:
			critical
			major
			minor
			deferred
			---------------------------"
	::= { ommp81PlusConfigurationEntry 777 }

	ommp81PlusEthernetLocalFaultAlarmSeverity OBJECT-TYPE
		SYNTAX  DisplayString
		MAX-ACCESS  read-write
		STATUS  current
		DESCRIPTION
			"Set or Get the alarm severity level of the
			OMMP81-PLUS Ethernet Local Fault Alarm   
			for requested port
			-----------------------------
			ommp81PlusInterfaceNumber:
			1 to 8 - CLIENT-1 to CLIENT-8
			-----------------------------
			Value:
			critical
			major
			minor
			deferred
			---------------------------"
	::= { ommp81PlusConfigurationEntry 778 }

	ommp81PlusEthernetRemoteFaultAlarmSeverity OBJECT-TYPE
		SYNTAX  DisplayString
		MAX-ACCESS  read-write
		STATUS  current
		DESCRIPTION
			"Set or Get the alarm severity level of the
			OMMP81-PLUS Ethernet Remote Fault Alarm   
			for requested port
			-----------------------------
			ommp81PlusInterfaceNumber:
			1 to 8 - CLIENT-1 to CLIENT-8
			-----------------------------
			Value:
			critical
			major
			minor
			deferred
			---------------------------"
	::= { ommp81PlusConfigurationEntry 779 }

	ommp81PlusFcTransmitDisparityInversionDefectAlarmSeverity OBJECT-TYPE
		SYNTAX  DisplayString
		MAX-ACCESS  read-write
		STATUS  current
		DESCRIPTION
			"Set or Get the alarm severity level of the
			OMMP81-PLUS FC Transmit Disparity Inversion Defect Alarm
			for requested port
			-----------------------------
			ommp81PlusInterfaceNumber:
			1 to 8 - CLIENT-1 to CLIENT-8
			-----------------------------
			Value:
			critical
			major
			minor
			deferred
			---------------------------"
	::= { ommp81PlusConfigurationEntry 791 }

	ommp81PlusFcTransmitDigitalLossOfLinkDefectAlarmSeverity OBJECT-TYPE
		SYNTAX  DisplayString
		MAX-ACCESS  read-write
		STATUS  current
		DESCRIPTION
			"Set or Get the alarm severity level of the
			OMMP81-PLUS FC Transmit Digital Loss Of Link Defect 
			Alarm for requested port
			-----------------------------
			ommp81PlusInterfaceNumber:
			1 to 8 - CLIENT-1 to CLIENT-8
			-----------------------------
			Value:
			critical
			major
			minor
			deferred
			---------------------------"
	::= { ommp81PlusConfigurationEntry 792 }

	ommp81PlusFcTrasnmitLossOfSynchronizationDefectAlarmSeverity OBJECT-TYPE
		SYNTAX  DisplayString
		MAX-ACCESS  read-write
		STATUS  current
		DESCRIPTION
			"Set or Get the alarm severity level of the
			OMMP81-PLUS FC Transmit Loss Of Synchronization Defect 
			Alarm  for requested port
			-----------------------------
			ommp81PlusInterfaceNumber:
			1 to 8 - CLIENT-1 to CLIENT-8
			-----------------------------
			Value:
			critical
			major
			minor
			deferred
			---------------------------"
	::= { ommp81PlusConfigurationEntry 793 }

	ommp81PlusFcReceiveDigitalLossOfLinkDefectAlarmSeverity OBJECT-TYPE
		SYNTAX  DisplayString
		MAX-ACCESS  read-write
		STATUS  current
		DESCRIPTION
			"Set or Get the alarm severity level of the
			OMMP81-PLUS FC Receive Digital Loss Of Link Defect Alarm  
			for requested port
			-----------------------------
			ommp81PlusInterfaceNumber:
			1 to 8 - CLIENT-1 to CLIENT-8
			-----------------------------
			Value:
			critical
			major
			minor
			deferred
			---------------------------"
	::= { ommp81PlusConfigurationEntry 794 }

	ommp81PlusFcReceiveLossOfSynchronizationDefectAlarmSeverity OBJECT-TYPE
		SYNTAX  DisplayString
		MAX-ACCESS  read-write
		STATUS  current
		DESCRIPTION
			"Set or Get the alarm severity level of the
			OMMP81-PLUS FC Receive Loss Of Synchronization Defect
			Alarm for requested port
			-----------------------------
			ommp81PlusInterfaceNumber:
			1 to 8 - CLIENT-1 to CLIENT-8
			-----------------------------
			Value:
			critical
			major
			minor
			deferred
			---------------------------"
	::= { ommp81PlusConfigurationEntry 795 }

	ommp81PlusFcReceiveTransitionDetectDefectAlarmSeverity OBJECT-TYPE
		SYNTAX  DisplayString
		MAX-ACCESS  read-write
		STATUS  current
		DESCRIPTION
			"Set or Get the alarm severity level of the
			OMMP81-PLUS FC Receive Transition Detect Defect Alarm   
			for requested port
			-----------------------------
			ommp81PlusInterfaceNumber:
			1 to 8 - CLIENT-1 to CLIENT-8
			-----------------------------
			Value:
			critical
			major
			minor
			deferred
			---------------------------"
	::= { ommp81PlusConfigurationEntry 796 }

	ommp81PlusFcReceiveAnalogLossOfSignalDefectAlarmSeverity OBJECT-TYPE
		SYNTAX  DisplayString
		MAX-ACCESS  read-write
		STATUS  current
		DESCRIPTION
			"Set or Get the alarm severity level of the
			OMMP81-PLUS FC Receive Analog Loss Of Signal Defect
			Alarm for requested port
			-----------------------------
			ommp81PlusInterfaceNumber:
			1 to 8 - CLIENT-1 to CLIENT-8
			-----------------------------
			Value:
			critical
			major
			minor
			deferred
			---------------------------"
	::= { ommp81PlusConfigurationEntry 797 }

	ommp81PlusFcReceiveLineCodeViolationDefectAlarmSeverity OBJECT-TYPE
		SYNTAX  DisplayString
		MAX-ACCESS  read-write
		STATUS  current
		DESCRIPTION
			"Set or Get the alarm severity level of the
			OMMP81-PLUS FC Receive Line Code Violation 
			Defect Alarm for the requested port
			-----------------------------
			ommp81PlusInterfaceNumber:
			1 to 8 - CLIENT-1 to CLIENT-8
			-----------------------------
			Value:
			critical
			major
			minor
			deferred
			---------------------------"
	::= { ommp81PlusConfigurationEntry 798 }

	ommp81PlusGfpCsfSignalFailAlarmSeverity OBJECT-TYPE
		SYNTAX  DisplayString
		MAX-ACCESS  read-write
		STATUS  current
		DESCRIPTION
			"Set or Get the alarm severity level of the
			OMMP81-PLUS GFP Csf Signal Failure Alarm   
			for requested port
			-----------------------------
			ommp81PlusInterfaceNumber:
			1 to 8 - CLIENT-1 to CLIENT-8
			-----------------------------
			Value:
			critical
			major
			minor
			deferred
			---------------------------"
	::= { ommp81PlusConfigurationEntry 811 }

	ommp81PlusGfpCsfLinkFailAlarmSeverity OBJECT-TYPE
		SYNTAX  DisplayString
		MAX-ACCESS  read-write
		STATUS  current
		DESCRIPTION
			"Set or Get the alarm severity level of the
			OMMP81-PLUS GFP Csf Link Failure Alarm   
			for requested port
			-----------------------------
			ommp81PlusInterfaceNumber:
			1 to 8 - CLIENT-1 to CLIENT-8
			-----------------------------
			Value:
			critical
			major
			minor
			deferred
			---------------------------"
	::= { ommp81PlusConfigurationEntry 812 }

	ommp81PlusGfpCoreHeaderErrorAlarmSeverity OBJECT-TYPE
		SYNTAX  DisplayString
		MAX-ACCESS  read-write
		STATUS  current
		DESCRIPTION
			"Set or Get the alarm severity level of the
			OMMP81-PLUS GFP Core Header Error Alarm   
			for requested port
			-----------------------------
			ommp81PlusInterfaceNumber:
			1 to 8 - CLIENT-1 to CLIENT-8
			-----------------------------
			Value:
			critical
			major
			minor
			deferred
			---------------------------"
	::= { ommp81PlusConfigurationEntry 813 }

	ommp81PlusGfpExtentionHeaderErrorAlarmSeverity OBJECT-TYPE
		SYNTAX  DisplayString
		MAX-ACCESS  read-write
		STATUS  current
		DESCRIPTION
			"Set or Get the alarm severity level of the
			OMMP81-PLUS GFP Extention Header Error Alarm   
			for requested port
			-----------------------------
			ommp81PlusInterfaceNumber:
			1 to 8 - CLIENT-1 to CLIENT-8
			-----------------------------
			Value:
			critical
			major
			minor
			deferred
			---------------------------"
	::= { ommp81PlusConfigurationEntry 814 }

	ommp81PlusConfigurationTableRowStatus OBJECT-TYPE
              SYNTAX      RowStatus
              MAX-ACCESS  read-write
              STATUS      current
              DESCRIPTION
			"*****************************
			This is MIB realted property,
			NOT to be considered as a card property
			*****************************"
              ::= { ommp81PlusConfigurationEntry 815 }	


--*****************************************************************************
--				    ALARMS
--*****************************************************************************
                 
	ommp81PlusAlarmQueryTable OBJECT-TYPE
	      SYNTAX  SEQUENCE OF Ommp81PlusAlarmQueryEntry 
              MAX-ACCESS  not-accessible
              STATUS  current
              DESCRIPTION
                      "Gives Optical and Signal Alarms status of the OMMP81-PLUS card"
		::= { ommp81PlusAlarmQuery 1 }	

	ommp81PlusAlarmQueryEntry   OBJECT-TYPE
              SYNTAX  Ommp81PlusAlarmQueryEntry 
              MAX-ACCESS  not-accessible
              STATUS  current
              DESCRIPTION 
              	""
		INDEX   { node, rack , subRack , slot , ommp81PlusInterfaceNumber }
		::= { ommp81PlusAlarmQueryTable 1 }
	
	Ommp81PlusAlarmQueryEntry ::= 
			SEQUENCE {					
					ommp81PlusXfpInputPowerFailureAlarm					DisplayString,
					ommp81PlusXfpOutputPowerFailureAlarm					DisplayString,
					ommp81PlusXfpHighTemperatureAlarm					DisplayString,
					ommp81PlusXfpLowTemperatureAlarm					DisplayString,
					ommp81PlusXfpHighTemperatureWarning					DisplayString,
					ommp81PlusXfpLowTemperatureWarning					DisplayString,
					ommp81PlusXfpHighBiasCurrentAlarm					DisplayString,
					ommp81PlusXfpLowBiasCurrentAlarm					DisplayString,
					ommp81PlusXfpHighBiasCurrentWarning					DisplayString,
					ommp81PlusXfpLowBiasCurrentWarning					DisplayString,
					ommp81PlusXfpInputHighPowerAlarm					DisplayString,
					ommp81PlusXfpInputLowPowerAlarm						DisplayString,
					ommp81PlusXfpInputHighPowerWarning					DisplayString,
					ommp81PlusXfpInputLowPowerWarning					DisplayString,
					ommp81PlusXfpOutputHighPowerAlarm					DisplayString,
					ommp81PlusXfpOutputLowPowerAlarm					DisplayString,
					ommp81PlusXfpOutputHighPowerWarning					DisplayString,
					ommp81PlusXfpOutputLowPowerWarning					DisplayString,
					ommp81PlusXfpHighSupplyVoltageAlarm					DisplayString,
					ommp81PlusXfpLowSupplyVoltageAlarm					DisplayString,
					ommp81PlusXfpHighSupplyVoltageWarning					DisplayString,
					ommp81PlusXfpLowSupplyVoltageWarning					DisplayString,
					ommp81PlusXfpPresenceAbsenceNotification				DisplayString,
					ommp81PlusSfpInputPowerFailureAlarm					DisplayString,
					ommp81PlusSfpOutputPowerFailureAlarm					DisplayString,
					ommp81PlusSfpHighTemperatureAlarm					DisplayString,
					ommp81PlusSfpLowTemperatureAlarm					DisplayString,
					ommp81PlusSfpHighTemperatureWarning					DisplayString,
					ommp81PlusSfpLowTemperatureWarning					DisplayString,
					ommp81PlusSfpHighBiasCurrentAlarm					DisplayString,
					ommp81PlusSfpLowBiasCurrentAlarm					DisplayString,
					ommp81PlusSfpHighBiasCurrentWarning					DisplayString,
					ommp81PlusSfpLowBiasCurrentWarning					DisplayString,
					ommp81PlusSfpInputHighPowerAlarm					DisplayString,
					ommp81PlusSfpInputLowPowerAlarm						DisplayString,
					ommp81PlusSfpInputHighPowerWarning					DisplayString,
					ommp81PlusSfpInputLowPowerWarning					DisplayString,
					ommp81PlusSfpOutputHighPowerAlarm					DisplayString,
					ommp81PlusSfpOutputLowPowerAlarm					DisplayString,
					ommp81PlusSfpOutputHighPowerWarning					DisplayString,
					ommp81PlusSfpOutputLowPowerWarning					DisplayString,
					ommp81PlusSfpHighSupplyVoltageAlarm					DisplayString,
					ommp81PlusSfpLowSupplyVoltageAlarm					DisplayString,
					ommp81PlusSfpHighSupplyVoltageWarning					DisplayString,
					ommp81PlusSfpLowSupplyVoltageWarning					DisplayString,
					ommp81PlusSfpPresenceAbsenceNotification				DisplayString,
					ommp81PlusSfpTransmitFaultPresenceAlarm					DisplayString,
					ommp81PlusOtuLossOfSignalAlarm						DisplayString,
					ommp81PlusOtuLossOfFrameAlarm						DisplayString,
					ommp81PlusOtuOutOfFrameAlarm						DisplayString,
					ommp81PlusOtuLossOfMultiFrameAlarm					DisplayString,
					ommp81PlusOtuOutOfMultiFrameAlarm					DisplayString,
					ommp81PlusOtuSignalFailAlarm						DisplayString,
					ommp81PlusOtuSignalDegradeAlarm						DisplayString,
					ommp81PlusOtuAlarmIndicationSignalAlarm					DisplayString,
					ommp81PlusOtuIncomingAlignmentErrorAlarm				DisplayString,
					ommp81PlusOtuTraceIdentifierMismatchAlarm				DisplayString,
					ommp81PlusOtuBackwardIncomingAlignmentErrorAlarm			DisplayString,
					ommp81PlusOtuBackwardDefectIndicationAlarm				DisplayString,
					ommp81PlusOduSignalFailAlarm						DisplayString,
					ommp81PlusOduSignalDegradeAlarm						DisplayString,
					ommp81PlusOduAlarmIndicationSignalAlarm					DisplayString,
					ommp81PlusOduTcm1IncomingAlignmentErrorAlarm				DisplayString,
					ommp81PlusOduTcm2IncomingAlignmentErrorAlarm				DisplayString,
					ommp81PlusOduTcm3IncomingAlignmentErrorAlarm				DisplayString,
					ommp81PlusOduTcm4IncomingAlignmentErrorAlarm				DisplayString,
					ommp81PlusOduTcm5IncomingAlignmentErrorAlarm				DisplayString,
					ommp81PlusOduTcm6IncomingAlignmentErrorAlarm				DisplayString,
					ommp81PlusOduTraceIdentifierMismatchAlarm				DisplayString,
					ommp81PlusOduLockedDefectAlarm						DisplayString,
					ommp81PlusOduOpenConnectionIndicationAlarm				DisplayString,
					ommp81PlusOduBackwardDefectIndicationAlarm				DisplayString,
					ommp81PlusOduTcm1BackwardIncomingAlignmentErrorAlarm			DisplayString,
					ommp81PlusOduTcm2BackwardIncomingAlignmentErrorAlarm			DisplayString,
					ommp81PlusOduTcm3BackwardIncomingAlignmentErrorAlarm			DisplayString,
					ommp81PlusOduTcm4BackwardIncomingAlignmentErrorAlarm			DisplayString,
					ommp81PlusOduTcm5BackwardIncomingAlignmentErrorAlarm			DisplayString,
					ommp81PlusOduTcm6BackwardIncomingAlignmentErrorAlarm			DisplayString,
					ommp81PlusOduLossOfFrameLossOfMultiframeAlarm				DisplayString,
					ommp81PlusOpuPayloadMismatchAlarm					DisplayString,
					ommp81PlusOchLossOfPayloadAlarm						DisplayString,
					ommp81PlusSdhLossOfSignalAlarm						DisplayString,
					ommp81PlusSdhOutOfFrameAlarm						DisplayString,
					ommp81PlusSdhLossOfFrameAlarm						DisplayString,
					ommp81PlusSdhRsAlarmIndicationSignalAlarm				DisplayString,
					ommp81PlusSdhRsTraceIdentifierMismatchAlarm				DisplayString,
					ommp81PlusSdhAuAlarmIndicationSignalAlarm				DisplayString,
					ommp81PlusSdhAuLossOfPointerAlarm					DisplayString,
					ommp81PlusSdhMsAlarmIndicationSignalAlarm				DisplayString,
					ommp81PlusSdhMsRemoteErrorIndicationAlarm				DisplayString,
					ommp81PlusSdhMsRemoteDefectIndicationAlarm				DisplayString,
					ommp81PlusSdhMsRemoteFailureIndicationAlarm				DisplayString,
					ommp81PlusSdhMsB2ExcessiveErrorAlarm					DisplayString,
					ommp81PlusSdhMsB2SignalDegradeAlarm					DisplayString,
					ommp81PlusSdhLossOfSequenceSynchronisationAlarm				DisplayString,
					ommp81PlusSdhLowerOrderPathPayloadLabelMismatchAlarm			DisplayString,
					ommp81PlusSdhLowerOrderPathUnequippedAlarm				DisplayString,
					ommp81PlusEthernetLossOfSignalAlarm					DisplayString,
					ommp81PlusEthernetLossOfSignalSyncAlarm					DisplayString,
					ommp81PlusEthernetLinkFailureAlarm					DisplayString,
					ommp81PlusEthernetAutoNegotiationAlarm					DisplayString,
					ommp81PlusEthernetFrameCheckSequenceAlarm				DisplayString,
					ommp81PlusEthernetCarrierStatusAlarm					DisplayString,
					ommp81PlusEthernetHighBerAlarm						DisplayString,
					ommp81PlusEthernetLocalFaultAlarm					DisplayString,
					ommp81PlusEthernetRemoteFaultAlarm					DisplayString,
					ommp81PlusFcTransmitDisparityInversionDefectAlarm			DisplayString,
					ommp81PlusFcTransmitDigitalLossOfLinkDefectAlarm			DisplayString,
					ommp81PlusFcTrasnmitLossOfSynchronizationDefectAlarm			DisplayString,
					ommp81PlusFcReceiveDigitalLossOfLinkDefectAlarm				DisplayString,
					ommp81PlusFcReceiveLossOfSynchronizationDefectAlarm			DisplayString,
					ommp81PlusFcReceiveTransitionDetectDefectAlarm				DisplayString,
					ommp81PlusFcReceiveAnalogLossOfSignalDefectAlarm			DisplayString,
					ommp81PlusFcReceiveLineCodeViolationDefectAlarm				DisplayString,
					ommp81PlusGfpCsfSignalFailAlarm						DisplayString,
					ommp81PlusGfpCsfLinkFailAlarm						DisplayString,
					ommp81PlusGfpCoreHeaderErrorAlarm					DisplayString,
					ommp81PlusGfpExtentionHeaderErrorAlarm					DisplayString,
					ommp81PlusAlarmQueryTableRowStatus					RowStatus
		}

--*****************************************************************************
--				OPTICAL	ALARMS
--***************************************************************************** 

	ommp81PlusXfpInputPowerFailureAlarm OBJECT-TYPE
              SYNTAX  DisplayString
              MAX-ACCESS  read-only
              STATUS  current
              DESCRIPTION
			"If optical input power at requested interface is less than
			-20dbm, this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 1 }

	ommp81PlusXfpOutputPowerFailureAlarm OBJECT-TYPE
              SYNTAX  DisplayString
              MAX-ACCESS  read-only
              STATUS  current
              DESCRIPTION
			"If optical output power at requested interface is less than
			-10dbm, this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 2 }

	ommp81PlusXfpHighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 3 }

	ommp81PlusXfpLowTemperatureAlarm OBJECT-TYPE
              SYNTAX  DisplayString
              MAX-ACCESS  read-only
              STATUS  current
              DESCRIPTION
			"If optical temperature at requested interface is lower 
			than the Low Temperature Alarm Threshold, alarm will be 
			generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 4 }

	ommp81PlusXfpHighTemperatureWarning OBJECT-TYPE
              SYNTAX  DisplayString
              MAX-ACCESS  read-only
              STATUS  current
              DESCRIPTION
			"If optical temperature at requested interface is greater
			than the High Temperature Warning Threshold, this alarm 
			will be generated.
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 5 }

	ommp81PlusXfpLowTemperatureWarning OBJECT-TYPE
              SYNTAX  DisplayString
              MAX-ACCESS  read-only
              STATUS  current
              DESCRIPTION
			"If optical temperature at requested interface is lesser
			than the Low Temperature Warning Threshold, this alarm 
			will be generated.
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 6 }

	ommp81PlusXfpHighBiasCurrentAlarm OBJECT-TYPE
              SYNTAX  DisplayString
              MAX-ACCESS  read-only
              STATUS  current
              DESCRIPTION
			"If optical transmit bias current at requested interface
			is greater than the High Bias Current Alarm Threshold, 
			this alarm will be generated.
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 7 }

	ommp81PlusXfpLowBiasCurrentAlarm OBJECT-TYPE
              SYNTAX  DisplayString
              MAX-ACCESS  read-only
              STATUS  current
              DESCRIPTION
			"If optical transmit bias current at requested interface
			is lesser than the Low Bias Current Alarm Threshold, 
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 8 }

	ommp81PlusXfpHighBiasCurrentWarning OBJECT-TYPE
              SYNTAX  DisplayString
              MAX-ACCESS  read-only
              STATUS  current
              DESCRIPTION
			"If optical transmit bias current at requested interface
			is greater than the High Bias Current Warning Threshold,
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 9 }

	ommp81PlusXfpLowBiasCurrentWarning OBJECT-TYPE
              SYNTAX  DisplayString
              MAX-ACCESS  read-only
              STATUS  current
              DESCRIPTION
			"If optical transmit bias current at requested interface
			is lesser than the Low Bias Current Warning Threshold, 
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 10 }

	ommp81PlusXfpInputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 11 }

	ommp81PlusXfpInputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 12 }

	ommp81PlusXfpInputHighPowerWarning OBJECT-TYPE
              SYNTAX  DisplayString
              MAX-ACCESS  read-only
              STATUS  current
              DESCRIPTION
			"If optical Input power at requested interface is 
			greater than the High Input Power Warning Threshold, 
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 13 }

	ommp81PlusXfpInputLowPowerWarning OBJECT-TYPE
              SYNTAX  DisplayString
              MAX-ACCESS  read-only
              STATUS  current
              DESCRIPTION
			"If optical Input power at requested interface is lesser
			than the Low Input Power Warning Threshold, this alarm 
			will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 14 }

	ommp81PlusXfpOutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 15 }

	ommp81PlusXfpOutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 16 }

	ommp81PlusXfpOutputHighPowerWarning OBJECT-TYPE
              SYNTAX  DisplayString
              MAX-ACCESS  read-only
              STATUS  current
              DESCRIPTION
			"If optical Output power at requested interface is 
			greater than the High Output Power Warning Threshold, 
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 17 }

	ommp81PlusXfpOutputLowPowerWarning OBJECT-TYPE
              SYNTAX  DisplayString
              MAX-ACCESS  read-only
              STATUS  current
              DESCRIPTION
			"If optical Output power at requested interface is 
			lesser than the Low Output Power Warning Threshold, 
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 18 }

	ommp81PlusXfpHighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 19 }

	ommp81PlusXfpLowSupplyVoltageAlarm OBJECT-TYPE
              SYNTAX  DisplayString
              MAX-ACCESS  read-only
              STATUS  current
              DESCRIPTION
			"If optical Supply Voltage at requested interface is 
			lesser than the Low Supply Voltage Alarm Threshold, 
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 20 }

	ommp81PlusXfpHighSupplyVoltageWarning OBJECT-TYPE
              SYNTAX  DisplayString
              MAX-ACCESS  read-only
              STATUS  current
              DESCRIPTION
			"If optical Supply Voltage at requested interface is 
			higher than the High Supply Voltage Warning Threshold,
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 21 }

	ommp81PlusXfpLowSupplyVoltageWarning OBJECT-TYPE
              SYNTAX  DisplayString
              MAX-ACCESS  read-only
              STATUS  current
              DESCRIPTION
			"If optical Supply Voltage at requested interface is 
			lesser than the Low Supply Voltage Warning Threshold, 
			this alarm will be generated
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 22 }

	ommp81PlusXfpPresenceAbsenceNotification OBJECT-TYPE
              SYNTAX  DisplayString
              MAX-ACCESS  read-only
              STATUS  current
              DESCRIPTION
			"Whenever the XFP is jacked in or jacked out, this 
			notification is generated.
			-----------------------------
			ommp81PlusInterfaceNumber:
			9 - LINE-1
			-----------------------------
			Values :
			If Alarm is Present(module absent) - Date and Time Stamp
				    eg:2017-5-18,9:47:20.0,+5:30
			If Alarm is Absent(module present) - 0
			-----------------------------"
		::= { ommp81PlusAlarmQueryEntry 23 }

	ommp81PlusSfpInputPowerFailureAlarm OBJECT-TYPE
              SYNTAX  DisplayString
              MAX-ACCESS  read-only
              STATUS  current
              DESCRIPTION
			"If optical input power at requested interface is less than
			-20dbm, this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 41 }

	ommp81PlusSfpOutputPowerFailureAlarm OBJECT-TYPE
              SYNTAX  DisplayString
              MAX-ACCESS  read-only
              STATUS  current
              DESCRIPTION
			"If optical output power at requested interface is less than
			-10dbm, this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 42 }

	ommp81PlusSfpHighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 43 }

	ommp81PlusSfpLowTemperatureAlarm OBJECT-TYPE
              SYNTAX  DisplayString
              MAX-ACCESS  read-only
              STATUS  current
              DESCRIPTION
			"If optical temperature at requested interface is lesser 
			than the Low Temperature Alarm Threshold, alarm will be 
			generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 44 }

	ommp81PlusSfpHighTemperatureWarning OBJECT-TYPE
              SYNTAX  DisplayString
              MAX-ACCESS  read-only
              STATUS  current
              DESCRIPTION
			"If optical temperature at requested interface is greater
			than the High Temperature Warning Threshold, this alarm 
			will be generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 45 }

	ommp81PlusSfpLowTemperatureWarning OBJECT-TYPE
              SYNTAX  DisplayString
              MAX-ACCESS  read-only
              STATUS  current
              DESCRIPTION
			"If optical temperature at requested interface is lesser
			than the Low Temperature Warning Threshold, this alarm 
			will be generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 46 }

	ommp81PlusSfpHighBiasCurrentAlarm OBJECT-TYPE
              SYNTAX  DisplayString
              MAX-ACCESS  read-only
              STATUS  current
              DESCRIPTION
			"If optical transmit bias current at requested interface
			is greater than the High Bias Current Alarm Threshold, 
			this alarm will be generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 47 }

	ommp81PlusSfpLowBiasCurrentAlarm OBJECT-TYPE
              SYNTAX  DisplayString
              MAX-ACCESS  read-only
              STATUS  current
              DESCRIPTION
			"If optical transmit bias current at requested interface
			is lesser than the Low Bias Current Alarm Threshold, 
			this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 48 }

	ommp81PlusSfpHighBiasCurrentWarning OBJECT-TYPE
              SYNTAX  DisplayString
              MAX-ACCESS  read-only
              STATUS  current
              DESCRIPTION
			"If optical transmit bias current at requested interface
			is greater than the High Bias Current Warning Threshold,
			this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 49 }

	ommp81PlusSfpLowBiasCurrentWarning OBJECT-TYPE
              SYNTAX  DisplayString
              MAX-ACCESS  read-only
              STATUS  current
              DESCRIPTION
			"If optical transmit bias current at requested interface
			is lesser than the Low Bias Current Warning Threshold, 
			this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 50 }

	ommp81PlusSfpInputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 51 }

	ommp81PlusSfpInputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 52 }

	ommp81PlusSfpInputHighPowerWarning OBJECT-TYPE
              SYNTAX  DisplayString
              MAX-ACCESS  read-only
              STATUS  current
              DESCRIPTION
			"If optical Input power at requested interface is 
			greater than the High Input Power Warning Threshold, 
			this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 53 }

	ommp81PlusSfpInputLowPowerWarning OBJECT-TYPE
              SYNTAX  DisplayString
              MAX-ACCESS  read-only
              STATUS  current
              DESCRIPTION
			"If optical Input power at requested interface is lesser
			than the Low Input Power Warning Threshold, this alarm 
			will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 54 }

	ommp81PlusSfpOutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 55 }

	ommp81PlusSfpOutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 56 }

	ommp81PlusSfpOutputHighPowerWarning OBJECT-TYPE
              SYNTAX  DisplayString
              MAX-ACCESS  read-only
              STATUS  current
              DESCRIPTION
			"If optical Output power at requested interface is 
			greater than the High Output Power Warning Threshold, 
			this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 57 }

	ommp81PlusSfpOutputLowPowerWarning OBJECT-TYPE
              SYNTAX  DisplayString
              MAX-ACCESS  read-only
              STATUS  current
              DESCRIPTION
			"If optical Output power at requested interface is 
			lesser than the Low Output Power Warning Threshold, this
			alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 58 }

	ommp81PlusSfpHighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 59 }

	ommp81PlusSfpLowSupplyVoltageAlarm OBJECT-TYPE
              SYNTAX  DisplayString
              MAX-ACCESS  read-only
              STATUS  current
              DESCRIPTION
			"If optical Supply Voltage at requested interface is 
			lesser than the Low Supply Voltage Alarm Threshold, this
			alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 60 }

	ommp81PlusSfpHighSupplyVoltageWarning OBJECT-TYPE
              SYNTAX  DisplayString
              MAX-ACCESS  read-only
              STATUS  current
              DESCRIPTION
			"If optical Supply Voltage at requested interface is 
			greater than the High Supply Voltage Warning Threshold, 
			this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 61 }

	ommp81PlusSfpLowSupplyVoltageWarning OBJECT-TYPE
              SYNTAX  DisplayString
              MAX-ACCESS  read-only
              STATUS  current
              DESCRIPTION
			"If optical Supply Voltage at requested interface is 
			lesser than the Low Supply Voltage Warning Threshold, 
			this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 62 }

	ommp81PlusSfpPresenceAbsenceNotification OBJECT-TYPE
              SYNTAX  DisplayString
              MAX-ACCESS  read-only
              STATUS  current
              DESCRIPTION
			"Whenever the SFP is jacked in or jacked out, this 
			notification is generated.
			-----------------------------
			ommp81PlusInterfaceNumber:
			1 to 8 - CLIENT-1 to CLIENT-8
			-----------------------------
			Values :
			If Alarm is Present(module absent) - Date and Time Stamp
				    eg:2017-5-18,9:47:20.0,+5:30
			If Alarm is Absent(module present) - 0
			-----------------------------"
		::= { ommp81PlusAlarmQueryEntry 63 }

	ommp81PlusSfpTransmitFaultPresenceAlarm OBJECT-TYPE
              SYNTAX  DisplayString
              MAX-ACCESS  read-only
              STATUS  current
              DESCRIPTION
			"Whenever the SFP laser is unable to generate
			any data this alarm will be generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 64 }

	ommp81PlusOtuLossOfSignalAlarm OBJECT-TYPE
              SYNTAX  DisplayString
              MAX-ACCESS  read-only
              STATUS  current
              DESCRIPTION
			"For port configured with OTU2/OTU1 traffic,
			if there is no signal received then OTU-LOS Alarm
			is generated.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 81 }

	ommp81PlusOtuLossOfFrameAlarm OBJECT-TYPE
              SYNTAX  DisplayString
              MAX-ACCESS  read-only
              STATUS  current
              DESCRIPTION
			"For port configured with OTU2/OTU1 traffic, if
			OTU2/OTU1 frame received are in out-of-frame (OOF)
			state for 3 ms, then OTU-LOF Alarm is generated
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 82 }

	ommp81PlusOtuOutOfFrameAlarm OBJECT-TYPE
              SYNTAX  DisplayString
              MAX-ACCESS  read-only
              STATUS  current
              DESCRIPTION
			"For port configured with OTU2/OTU1 traffic, if 5
			consecutive OTU2/OTU1 frames are received with
			invalid framing patterns then OOF Alarm is
			generated
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 83 }

	ommp81PlusOtuLossOfMultiFrameAlarm OBJECT-TYPE
              SYNTAX  DisplayString
              MAX-ACCESS  read-only
              STATUS  current
              DESCRIPTION
			"For port configured with OTU2/OTU1 traffic, if 
			OTU2/OTU1 frame received are in Out-of-multiframe
			(OOM) state for 3 ms then LOM Alarm is generated.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 84 }

	ommp81PlusOtuOutOfMultiFrameAlarm OBJECT-TYPE
              SYNTAX  DisplayString
              MAX-ACCESS  read-only
              STATUS  current
              DESCRIPTION
			"For port configured with OTU2/OTU1 traffic, if the
			received MFAS does not match with the expected multi
			frame number for five consecutive frames then
			OOM Alarm is generated.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 85 }

	ommp81PlusOtuSignalFailAlarm OBJECT-TYPE
              SYNTAX  DisplayString
              MAX-ACCESS  read-only
              STATUS  current
              DESCRIPTION
			"For port configured with OTU2/OTU1 traffic, 
			OTU SF alarm is generated when BIP errors evaluated by 
			SM field of OTU2/OTU1 frame exceeds the 
			'ommp81PlusOtuSignalFailThreshold' threshold
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 86 }

	ommp81PlusOtuSignalDegradeAlarm OBJECT-TYPE
              SYNTAX  DisplayString
              MAX-ACCESS  read-only
              STATUS  current
              DESCRIPTION
			"For port configured with OTU2/OTU1 traffic, 
			OTU SD alarm is generated when BIP errors evaluated by 
			SM field of OTU2/OTU1 frame exceeds the 
			'ommp81PlusOtuSignalDegradeThreshold' threshold.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 87 }

	ommp81PlusOtuAlarmIndicationSignalAlarm OBJECT-TYPE
              SYNTAX  DisplayString
              MAX-ACCESS  read-only
              STATUS  current
              DESCRIPTION
			"For port configured with OTU2/OTU1 traffic,
			OTU-AIS is generated and transmitted in forward 
			direction, when LOS has been detected at far-end port.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 88 }

	ommp81PlusOtuIncomingAlignmentErrorAlarm OBJECT-TYPE
              SYNTAX  DisplayString
              MAX-ACCESS  read-only
              STATUS  current
              DESCRIPTION
			"For port configured with OTU2/OTU1 traffic, IAE alarms
			shall be declared if the IAE bit in the SM overhead
			field (byte 3, bit 6) is 1 for 5 consecutive frames. 
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 89 }

	ommp81PlusOtuTraceIdentifierMismatchAlarm OBJECT-TYPE
              SYNTAX  DisplayString
              MAX-ACCESS  read-only
              STATUS  current
              DESCRIPTION
			"For port configured with OTU2/OTU1 traffic, when there
			is a mismatch between the incoming and the expected
			Trail Trace Identifier(TTI) at the SM section,
			OTU-TIM alarm is generated.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 90 }

	ommp81PlusOtuBackwardIncomingAlignmentErrorAlarm OBJECT-TYPE
              SYNTAX  DisplayString
              MAX-ACCESS  read-only
              STATUS  current
              DESCRIPTION
			"For port configured with OTU2/OTU1 traffic, 
			the presence of this alarm conveys that an incoming
			alignment error(IAE) condition is detected
			by the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 91 }

	ommp81PlusOtuBackwardDefectIndicationAlarm OBJECT-TYPE
              SYNTAX  DisplayString
              MAX-ACCESS  read-only
              STATUS  current
              DESCRIPTION
			"For port configured with OTU2/OTU1 traffic,
			the presence of this alarm conveys that a
			a defect like LOS, LOF, LOM has been detected in the
			by the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 92 }

	ommp81PlusOduSignalFailAlarm OBJECT-TYPE
              SYNTAX  DisplayString
              MAX-ACCESS  read-only
              STATUS  current
              DESCRIPTION
			"For port configured with OTU2/OTU1 traffic, ODU-SF
			alarm is generated when BIP errors evaluated by 
			PM field of OTU2 frame exceeds the 
			'ommp81PlusOduSignalFailThreshold' threshold.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 111 }

	ommp81PlusOduSignalDegradeAlarm OBJECT-TYPE
              SYNTAX  DisplayString
              MAX-ACCESS  read-only
              STATUS  current
              DESCRIPTION
			"For port configured with OTU2/OTU1 traffic,ODU-SD
			alarm is generated when BIP errors evaluated by 
			PM field of OTU2 frame exceeds the 	
			'ommp81PlusOduSignalDegradeThreshold' threshold.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 112 }

	ommp81PlusOduAlarmIndicationSignalAlarm OBJECT-TYPE
              SYNTAX  DisplayString
              MAX-ACCESS  read-only
              STATUS  current
              DESCRIPTION
			"For port configured with OTU2/OTU1 traffic, when the incoming
			OTU2 frame has all 1s in the entire ODUk signal,
			excluding the frame alignment overhead (FA OH),
			OTUk overhead (OTUk OH) and ODUk FTFL, this alarm is
			generated
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 113 }

	ommp81PlusOduTcm1IncomingAlignmentErrorAlarm OBJECT-TYPE
              SYNTAX  DisplayString
              MAX-ACCESS  read-only
              STATUS  current
              DESCRIPTION
			"For port configured with OTU2/OTU1 traffic, TCM1 IAE
			shall be declared if the accepted STAT information is
			0b010
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 114 }

	ommp81PlusOduTcm2IncomingAlignmentErrorAlarm OBJECT-TYPE
              SYNTAX  DisplayString
              MAX-ACCESS  read-only
              STATUS  current
              DESCRIPTION
			"For port configured with OTU2/OTU1 traffic, TCM2 IAE
			shall be declared if the accepted STAT information is
			0b010
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 115 }

	ommp81PlusOduTcm3IncomingAlignmentErrorAlarm OBJECT-TYPE
              SYNTAX  DisplayString
              MAX-ACCESS  read-only
              STATUS  current
              DESCRIPTION
			"For port configured with OTU2/OTU1 traffic, TCM3 IAE
			shall be declared if the accepted STAT information is
			0b010
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 116 }

	ommp81PlusOduTcm4IncomingAlignmentErrorAlarm OBJECT-TYPE
              SYNTAX  DisplayString
              MAX-ACCESS  read-only
              STATUS  current
              DESCRIPTION
			"For port configured with OTU2/OTU1 traffic, TCM4 IAE
			shall be declared if the accepted STAT information is
			0b010
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 117 }

	ommp81PlusOduTcm5IncomingAlignmentErrorAlarm OBJECT-TYPE
              SYNTAX  DisplayString
              MAX-ACCESS  read-only
              STATUS  current
              DESCRIPTION
			"For port configured with OTU2/OTU1 traffic, TCM5 IAE
			shall be declared if the accepted STAT information is
			0b010
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 118 }

	ommp81PlusOduTcm6IncomingAlignmentErrorAlarm OBJECT-TYPE
              SYNTAX  DisplayString
              MAX-ACCESS  read-only
              STATUS  current
              DESCRIPTION
			"For port configured with OTU2/OTU1 traffic, TCM6 IAE
			shall be declared if the accepted STAT information is
			0b010
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 119 }

	ommp81PlusOduTraceIdentifierMismatchAlarm OBJECT-TYPE
              SYNTAX  DisplayString
              MAX-ACCESS  read-only
              STATUS  current
              DESCRIPTION
			"For port configured with OTU2/OTU1 traffic, when there
			is a mismatch between the incoming and the expected
			Trail Trace Identifier(TTI) at the PM section,
			ODU-TIM alarm is generated.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 120 }

	ommp81PlusOduLockedDefectAlarm OBJECT-TYPE
              SYNTAX  DisplayString
              MAX-ACCESS  read-only
              STATUS  current
              DESCRIPTION
			"For port configured with OTU2/OTU1 traffic, 
			the locked maintenance signal is generated on operator
			request in order to lock the signal from user access. It
			consists of a repeating 0b0101 0101 pattern in the
			entire ODUk signal, which excludes the Frame Alignment
			overhead and the OTUk overhead.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 121 }

	ommp81PlusOduOpenConnectionIndicationAlarm OBJECT-TYPE
              SYNTAX  DisplayString
              MAX-ACCESS  read-only
              STATUS  current
              DESCRIPTION
			"For port configured with OTU2/OTU1 traffic, 
			an open connection indication is sent downstream when
			no signal is detected from upstream. It consists of a
			repeating 0b0110 0110 pattern in the entire ODUk signal,
			which excludes the Frame Alignment overhead and the
			OTUk overhead.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 122 }

	ommp81PlusOduBackwardDefectIndicationAlarm OBJECT-TYPE
              SYNTAX  DisplayString
              MAX-ACCESS  read-only
              STATUS  current
              DESCRIPTION
			"For port configured with OTU2/OTU1 traffic, 
			the presence of this alarm conveys that either of
			OTU-LOS or OTU-LOF or OTU-LOM or OTU-AIS or ODU-AIS
			or ODU-OCI or ODU-LCK condition is detected
			by the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 123 }

	ommp81PlusOduTcm1BackwardIncomingAlignmentErrorAlarm OBJECT-TYPE
              SYNTAX  DisplayString
              MAX-ACCESS  read-only
              STATUS  current
              DESCRIPTION
			"For port configured with OTU2/OTU1 traffic, 
			the presence of this alarm conveys that
			TCM1 incoming alignment error (IAE) condition is 
			detected in the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 124 }

	ommp81PlusOduTcm2BackwardIncomingAlignmentErrorAlarm OBJECT-TYPE
              SYNTAX  DisplayString
              MAX-ACCESS  read-only
              STATUS  current
              DESCRIPTION
			"For port configured with OTU2/OTU1 traffic, 
			the presence of this alarm conveys that
			TCM2 incoming alignment error (IAE) condition is 
			detected in the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 125 }

	ommp81PlusOduTcm3BackwardIncomingAlignmentErrorAlarm OBJECT-TYPE
              SYNTAX  DisplayString
              MAX-ACCESS  read-only
              STATUS  current
              DESCRIPTION
			"For port configured with OTU2/OTU1 traffic, 
			the presence of this alarm conveys that
			TCM3 incoming alignment error (IAE) condition is 
			detected in the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 126 }


	ommp81PlusOduTcm4BackwardIncomingAlignmentErrorAlarm OBJECT-TYPE
              SYNTAX  DisplayString
              MAX-ACCESS  read-only
              STATUS  current
              DESCRIPTION
			"For port configured with OTU2/OTU1 traffic, 
			the presence of this alarm conveys that
			TCM4 incoming alignment error (IAE) condition is 
			detected in the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 127 }

	ommp81PlusOduTcm5BackwardIncomingAlignmentErrorAlarm OBJECT-TYPE
              SYNTAX  DisplayString
              MAX-ACCESS  read-only
              STATUS  current
              DESCRIPTION
			"For port configured with OTU2/OTU1 traffic, 
			the presence of this alarm conveys that
			TCM5 incoming alignment error (IAE) condition is 
			detected in the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 128 }

	ommp81PlusOduTcm6BackwardIncomingAlignmentErrorAlarm OBJECT-TYPE
              SYNTAX  DisplayString
              MAX-ACCESS  read-only
              STATUS  current
              DESCRIPTION
			"For port configured with OTU2/OTU1 traffic, 
			the presence of this alarm conveys that
			TCM6 incoming alignment error (IAE) condition is 
			detected in the far-end card.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 129 }

	ommp81PlusOduLossOfFrameLossOfMultiframeAlarm OBJECT-TYPE
              SYNTAX  DisplayString
              MAX-ACCESS  read-only
              STATUS  current
              DESCRIPTION
			"While demultiplexing the incoming OPU2 frame into the
			ODU1, if the start of a ODU1 frame is not found	then 
			this alarm is generated. Since the alarm is generated at
			the demultiplexing level, the alarm cannot be
			represented with respect to a client/line port, as one
			ODU1 slice might have multiple client data. This
			property is w.r.t slice
			-----------------------------
			ommp81PlusInterfaceNumber:
			ODU1 slices demapped from OTU2 signal received at LINE-1
			5 - ODU1 Slice 5
			6 - ODU1 Slice 6
			7 - ODU1 Slice 7
			8 - ODU1 Slice 8
			-----------------------------
			Values :
			If Alarm is Present - Date and Time Stamp
				    eg:2017-5-18,9:47:20.0,+5:30
			If Alarm is Absent  - 0
			-----------------------------"
		::= { ommp81PlusAlarmQueryEntry 130 }

	ommp81PlusOpuPayloadMismatchAlarm OBJECT-TYPE
              SYNTAX  DisplayString
              MAX-ACCESS  read-only
              STATUS  current
              DESCRIPTION
			"For port configured with OTU2/OTU1 traffic, 
			OPU-PLM Alarm is declared if the accepted payload type
			is not equal to the expected payload type.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 135 }

	ommp81PlusOchLossOfPayloadAlarm OBJECT-TYPE
              SYNTAX  DisplayString
              MAX-ACCESS  read-only
              STATUS  current
              DESCRIPTION
			"If input power level at the XFP is less than 
			-21dbm this this alarm will be generated.
			-----------------------------
			ommp81PlusInterfaceNumber:
			9 - LINE-1
			-----------------------------
			Values :
			If Alarm is Present - Date and Time Stamp
				    eg:2017-5-18,9:47:20.0,+5:30
			If Alarm is Absent  - 0
			-----------------------------"
		::= { ommp81PlusAlarmQueryEntry 136 }

	ommp81PlusSdhLossOfSignalAlarm OBJECT-TYPE
              SYNTAX  DisplayString
              MAX-ACCESS  read-only
              STATUS  current
              DESCRIPTION
			"For port configured with STM1/4/16 traffic, if there
			is no signal received then SDH-LOS Alarm is 
			generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 141 }

	ommp81PlusSdhOutOfFrameAlarm OBJECT-TYPE
              SYNTAX  DisplayString
              MAX-ACCESS  read-only
              STATUS  current
              DESCRIPTION
			"For port configured with STM1/4/16 traffic, when
			several consecutive SDH frames have A1, A2 bytes errored
			for a period more than 625us, this alarm will be
			generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 142 }

	ommp81PlusSdhLossOfFrameAlarm OBJECT-TYPE
              SYNTAX  DisplayString
              MAX-ACCESS  read-only
              STATUS  current
              DESCRIPTION
			"For port configured with STM1/4/16 traffic, 
			If SDH frame received are out-of-frame (OOF) state for 
			3 ms then LOF alarm is generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 143 }

	ommp81PlusSdhRsAlarmIndicationSignalAlarm OBJECT-TYPE
              SYNTAX  DisplayString
              MAX-ACCESS  read-only
              STATUS  current
              DESCRIPTION
			"For port configured with STM1/4/16 traffic, RS-AIS
			alarm is indicated when there is no signal 
			received by the far-end port.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 144 }

	ommp81PlusSdhRsTraceIdentifierMismatchAlarm OBJECT-TYPE
              SYNTAX  DisplayString
              MAX-ACCESS  read-only
              STATUS  current
              DESCRIPTION
			"For port configured with STM1/4/16 traffic, this alarms
			is generated when there is a mismatch of the accepted
			and expected trace identifier in J0 byte.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 145 }

	ommp81PlusSdhAuAlarmIndicationSignalAlarm OBJECT-TYPE
              SYNTAX  DisplayString
              MAX-ACCESS  read-only
              STATUS  current
              DESCRIPTION
			"For port configured with STM1/4/16 traffic, AU-AIS
			is generated if all ones are detected in the H1 and H2
			bytes of the AU pointer.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 146 }

	ommp81PlusSdhAuLossOfPointerAlarm OBJECT-TYPE
              SYNTAX  DisplayString
              MAX-ACCESS  read-only
              STATUS  current
              DESCRIPTION
			"For port configured with STM1/4/16 traffic, 
			LOP state occurs when N consecutive invalid pointers
			are received or N consecutive New Data Flags (NDF)
			are received where N = 8, 9, or 10. LOP state is 
			cleared when three equal valid pointers or three
			consecutive AIS indications are received.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 147 }

	ommp81PlusSdhMsAlarmIndicationSignalAlarm OBJECT-TYPE
              SYNTAX  DisplayString
              MAX-ACCESS  read-only
              STATUS  current
              DESCRIPTION
			"For port configured with STM1/4/16 traffic, 
			MS-AIS is an alarm indication signal (AIS) is a signal 
			sent downstream as an indication that an upstream
			defect has been detected.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 148 }

	ommp81PlusSdhMsRemoteErrorIndicationAlarm OBJECT-TYPE
              SYNTAX  DisplayString
              MAX-ACCESS  read-only
              STATUS  current
              DESCRIPTION
			"For port configured with STM1/4/16 traffic, 
			this alarm is an indication returned to a transmitting
			node (source) that an errored block has been detected at
			the receiving node (sink).
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 149 }

	ommp81PlusSdhMsRemoteDefectIndicationAlarm OBJECT-TYPE
              SYNTAX  DisplayString
              MAX-ACCESS  read-only
              STATUS  current
              DESCRIPTION
			"For port configured with STM1/4/16 traffic, 
			MS-RDI is a signal returned to the transmitting equipment 
			upon detecting a LOS, LOF, or MS-AIS defect
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 150 }

	ommp81PlusSdhMsRemoteFailureIndicationAlarm OBJECT-TYPE
              SYNTAX  DisplayString
              MAX-ACCESS  read-only
              STATUS  current
              DESCRIPTION
			"For port configured with STM1/4/16 traffic,
			a failure is a defect that persists beyond the maximum
			time allocated to the transmission system protection
			mechanisms. When this situation occurs, an RFI is sent
			to the far end and will initiate a path protection
			switch if this function has been provisioned.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 151 }

	ommp81PlusSdhMsB2ExcessiveErrorAlarm OBJECT-TYPE
              SYNTAX  DisplayString
              MAX-ACCESS  read-only
              STATUS  current
              DESCRIPTION
			"For port configured with STM1/4/16 traffic, 
			B2 SF alarm is generated when Parity errors evaluated 
			by byte B2 of SDH frame exceeds the 
			'ommp81PlusSdhMsB2ExcessiveErrorThreshold' threshold.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 152 }

	ommp81PlusSdhMsB2SignalDegradeAlarm OBJECT-TYPE
              SYNTAX  DisplayString
              MAX-ACCESS  read-only
              STATUS  current
              DESCRIPTION
			"For port configured with STM1/4/16 traffic,
			B2 SD alarm is generated when Parity errors evaluated 
			by byte B2 of SDH frame exceeds the 
			'ommp81PlusSdhMsB2SignalDegradeThreshold' threshold.
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 153 }

	ommp81PlusSdhLossOfSequenceSynchronisationAlarm OBJECT-TYPE
              SYNTAX  DisplayString
              MAX-ACCESS  read-only
              STATUS  current
              DESCRIPTION
			"For port configured with STM1/4/16 traffic, 
			Sequence synchronisation shall be considered to be lost
			and re-synchronisation shall be started if:
			The bit error ratio is >= 0.20 during an integration
			interval of 1 second; or
			It can be unambiguously identified that the test
			sequence and the reference sequence are out of phase.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 154 }

	ommp81PlusSdhLowerOrderPathPayloadLabelMismatchAlarm OBJECT-TYPE
              SYNTAX  DisplayString
              MAX-ACCESS  read-only
              STATUS  current
              DESCRIPTION
			"Reserved for further study
			-----------------------------
			ommp81PlusInterfaceNumber:
			1 to 8 - CLIENT-1 to CLIENT-8
			9 - LINE-1
			-----------------------------
			Values :
			If Alarm is Present - Date and Time Stamp
				    eg:2017-5-18,9:47:20.0,+5:30
			If Alarm is Absent  - 0
			-----------------------------"
		::= { ommp81PlusAlarmQueryEntry 155 }

	ommp81PlusSdhLowerOrderPathUnequippedAlarm OBJECT-TYPE
              SYNTAX  DisplayString
              MAX-ACCESS  read-only
              STATUS  current
              DESCRIPTION
			"For port configured with STM1/4/16 traffic,
			these signals indicate to downstream transport
			processing functions (refer to ITU-T Rec. G.803) that
			the virtual container is unoccupied,
			not connected to a path termination source function.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 156 }

	ommp81PlusEthernetLossOfSignalAlarm OBJECT-TYPE
              SYNTAX  DisplayString
              MAX-ACCESS  read-only
              STATUS  current
              DESCRIPTION
			"For port configured with 
			GE-GFP-F/FE-GFP-F/GE-GFP-T/FE-GFP-T traffic,
			if there is no signal received then LOS Alarm is 
			generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 171 }

	ommp81PlusEthernetLossOfSignalSyncAlarm OBJECT-TYPE
              SYNTAX  DisplayString
              MAX-ACCESS  read-only
              STATUS  current
              DESCRIPTION
			"For port configured with 
			GE-GFP-F/FE-GFP-F/GE-GFP-T/FE-GFP-T traffic,
			when the receive interface does not achieve PCS
		        sync it is called Loss of Sync.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 172 }

	ommp81PlusEthernetLinkFailureAlarm OBJECT-TYPE
              SYNTAX  DisplayString
              MAX-ACCESS  read-only
              STATUS  current
              DESCRIPTION
			"For port configured with 
			GE-GFP-F/FE-GFP-F/GE-GFP-T/FE-GFP-T traffic,
			in the event of ingress client signal failure, 
			the link failure alarm is generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 173 }

	ommp81PlusEthernetAutoNegotiationAlarm OBJECT-TYPE
              SYNTAX  DisplayString
              MAX-ACCESS  read-only
              STATUS  current
              DESCRIPTION
			"For port configured with 
			GE-GFP-F/GE-GFP-T traffic,
			if auto-negotiation is failed to establish between 
			link-partners, this alarm will get generated
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 174 }

	ommp81PlusEthernetFrameCheckSequenceAlarm OBJECT-TYPE
              SYNTAX  DisplayString
              MAX-ACCESS  read-only
              STATUS  current
              DESCRIPTION
			"For port configured with 
			GE-GFP-F/FE-GFP-F/GE-GFP-T/FE-GFP-T traffic,
			in the incoming ethernet frame, if the FCS value in the
			FCS byte and the FCS value calculated for the payload
			of the frame doesnt match, then number of FCS errors
			is incremented. If in one second, 50 such FCS errors
			are got, then FCS this alarm will be generated. 
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 175 }

	ommp81PlusEthernetCarrierStatusAlarm OBJECT-TYPE
              SYNTAX  DisplayString
              MAX-ACCESS  read-only
              STATUS  current
              DESCRIPTION
			"For port configured with 
			GE-GFP-F/FE-GFP-F/GE-GFP-T/FE-GFP-T traffic,
			whenever there is an absence of the carrier signal
			i.e. carrier sense loss occurs this alarm is generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 176 }

	ommp81PlusEthernetHighBerAlarm OBJECT-TYPE
              SYNTAX  DisplayString
              MAX-ACCESS  read-only
              STATUS  current
              DESCRIPTION
			"For port configured with 
			GE-GFP-F/FE-GFP-F/GE-GFP-T/FE-GFP-T traffic,
			this alarm is generated when signal BER is
			greater than 1e−4. 
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 177 }

	ommp81PlusEthernetLocalFaultAlarm OBJECT-TYPE
              SYNTAX  DisplayString
              MAX-ACCESS  read-only
              STATUS  current
              DESCRIPTION
			"For port configured with 
			GE-GFP-F/FE-GFP-F/GE-GFP-T/FE-GFP-T traffic,
			if fault is detected on the receive data path then Local
			Fault Alarm is generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 178 }

	ommp81PlusEthernetRemoteFaultAlarm OBJECT-TYPE
              SYNTAX  DisplayString
              MAX-ACCESS  read-only
              STATUS  current
              DESCRIPTION
			"For port configured with 
			GE-GFP-F/FE-GFP-F/GE-GFP-T/FE-GFP-T traffic,
			if fault is detected on the transmit data path then 
			Remote Fault Alarm is generated.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 179 }

	ommp81PlusFcTransmitDisparityInversionDefectAlarm OBJECT-TYPE
              SYNTAX  DisplayString
              MAX-ACCESS  read-only
              STATUS  current
              DESCRIPTION
			"For port configured with FC-100/200 traffic,
			get the FC Transmit Disparity Inversion Defect
			alarm status.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 191 }

	ommp81PlusFcTransmitDigitalLossOfLinkDefectAlarm OBJECT-TYPE
              SYNTAX  DisplayString
              MAX-ACCESS  read-only
              STATUS  current
              DESCRIPTION
			"For port configured with FC-100/200 traffic,
			get FC Transmit Digital Loss Of Link Defect alarm status.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 192 }

	ommp81PlusFcTrasnmitLossOfSynchronizationDefectAlarm OBJECT-TYPE
              SYNTAX  DisplayString
              MAX-ACCESS  read-only
              STATUS  current
              DESCRIPTION
			"For port configured with FC-100/200 traffic,
			get FC Transmit Loss Of Synchronization Defect
			alarm status.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 193 }

	ommp81PlusFcReceiveDigitalLossOfLinkDefectAlarm OBJECT-TYPE
              SYNTAX  DisplayString
              MAX-ACCESS  read-only
              STATUS  current
              DESCRIPTION
			"For port configured with FC-100/200 traffic,
			get FC Receive Digital Loss Of Link Defect alarm status.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 194 }

	ommp81PlusFcReceiveLossOfSynchronizationDefectAlarm OBJECT-TYPE
              SYNTAX  DisplayString
              MAX-ACCESS  read-only
              STATUS  current
              DESCRIPTION
			"For port configured with FC-100/200 traffic,
			get FC Receive Loss Of Synchronization Defect alarm
			status.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 195 }

	ommp81PlusFcReceiveTransitionDetectDefectAlarm OBJECT-TYPE
              SYNTAX  DisplayString
              MAX-ACCESS  read-only
              STATUS  current
              DESCRIPTION
			"For port configured with FC-100/200 traffic,
			get FC Receive Transition Detect Defect alarm status.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 196 }

	ommp81PlusFcReceiveAnalogLossOfSignalDefectAlarm OBJECT-TYPE
              SYNTAX  DisplayString
              MAX-ACCESS  read-only
              STATUS  current
              DESCRIPTION
			"For port configured with FC-100/200 traffic,
			get FC Receive Analog Loss Of Signal Defect status.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 197 }

	ommp81PlusFcReceiveLineCodeViolationDefectAlarm OBJECT-TYPE
              SYNTAX  DisplayString
              MAX-ACCESS  read-only
              STATUS  current
              DESCRIPTION
			"For port configured with FC-100/200 traffic,
			get FC Receive Line Code Violation Defect alarm status.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 198 }

	ommp81PlusGfpCsfSignalFailAlarm OBJECT-TYPE
              SYNTAX  DisplayString
              MAX-ACCESS  read-only
              STATUS  current
              DESCRIPTION
			"If signal loss at the far-end occurs, then
			this alarm is detected at the near-end card.
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 211 }

	ommp81PlusGfpCsfLinkFailAlarm OBJECT-TYPE
              SYNTAX  DisplayString
              MAX-ACCESS  read-only
              STATUS  current
              DESCRIPTION
			"If there is a link failure occured at the far-end
			card, then this alarm is detected at the near-end card 
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 212 }

	ommp81PlusGfpCoreHeaderErrorAlarm OBJECT-TYPE
              SYNTAX  DisplayString
              MAX-ACCESS  read-only
              STATUS  current
              DESCRIPTION
			"This alarm is generated if the core header error
			count is found to be greater than 50 for a particular
			instance. i.e. for a particular second
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 213 }

	ommp81PlusGfpExtentionHeaderErrorAlarm OBJECT-TYPE
              SYNTAX  DisplayString
              MAX-ACCESS  read-only
              STATUS  current
              DESCRIPTION
			"This alarm is generated if the extention header error
			count is found to be greater than 50 for a particular
			instance. i.e. for a particular second
			-----------------------------
			ommp81PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp81PlusAlarmQueryEntry 214 }

	ommp81PlusAlarmQueryTableRowStatus OBJECT-TYPE
              SYNTAX      RowStatus
              MAX-ACCESS  read-write
              STATUS      current
              DESCRIPTION
			"*****************************
			This is MIB realted property,
			NOT to be considered as a card property
			*****************************"
              ::= { ommp81PlusAlarmQueryEntry 215 }	                                

--*****************************************************************************
--				    ALARM Notification Table
--*****************************************************************************
	ommp81PlusXfpInputPowerFailureAlarmTrap NOTIFICATION-TYPE
		OBJECTS { ommp81PlusXfpInputPowerFailureAlarm  }
		STATUS  current
		DESCRIPTION
                        "OMMP81-PLUS XFP Input Power Failure Alarm Trap"
        ::= { ommp81PlusAlarmNotification 1 }

	ommp81PlusXfpOutputPowerFailureAlarmTrap NOTIFICATION-TYPE
		OBJECTS { ommp81PlusXfpOutputPowerFailureAlarm  }
		STATUS  current
		DESCRIPTION
                        "OMMP81-PLUS XFP Output Power Failure Alarm Trap" 
        ::= { ommp81PlusAlarmNotification 2 }

	ommp81PlusXfpHighTemperatureAlarmTrap NOTIFICATION-TYPE
		OBJECTS { ommp81PlusXfpHighTemperatureAlarm  }
		STATUS  current
		DESCRIPTION
                        "OMMP81-PLUS XFP High Temperature Alarm Trap" 
        ::= { ommp81PlusAlarmNotification 3 }

	ommp81PlusXfpLowTemperatureAlarmTrap NOTIFICATION-TYPE
		OBJECTS { ommp81PlusXfpLowTemperatureAlarm  }
		STATUS  current
		DESCRIPTION
                        "OMMP81-PLUS XFP Low Temperature Alarm Trap" 
        ::= { ommp81PlusAlarmNotification 4 }

	ommp81PlusXfpHighTemperatureWarningTrap NOTIFICATION-TYPE
		OBJECTS { ommp81PlusXfpHighTemperatureWarning  }
		STATUS  current
		DESCRIPTION
                        "OMMP81-PLUS XFP High Temperature Warning Trap" 
        ::= { ommp81PlusAlarmNotification 5 }

	ommp81PlusXfpLowTemperatureWarningTrap NOTIFICATION-TYPE
		OBJECTS { ommp81PlusXfpLowTemperatureWarning  }
		STATUS  current
		DESCRIPTION
                        "OMMP81-PLUS XFP Low Temperature Warning Trap" 
        ::= { ommp81PlusAlarmNotification 6 }

	ommp81PlusXfpHighBiasCurrentAlarmTrap NOTIFICATION-TYPE
		OBJECTS { ommp81PlusXfpHighBiasCurrentAlarm  }
		STATUS  current
		DESCRIPTION
                        "OMMP81-PLUS XFP High Bias Current Alarm Trap" 
        ::= { ommp81PlusAlarmNotification 7 }

	ommp81PlusXfpLowBiasCurrentAlarmTrap NOTIFICATION-TYPE
		OBJECTS { ommp81PlusXfpLowBiasCurrentAlarm  }
		STATUS  current
		DESCRIPTION
                        "OMMP81-PLUS XFP Low Bias Current Alarm Trap" 
        ::= { ommp81PlusAlarmNotification 8 }

	ommp81PlusXfpHighBiasCurrentWarningTrap NOTIFICATION-TYPE
		OBJECTS { ommp81PlusXfpHighBiasCurrentWarning  }
		STATUS  current
		DESCRIPTION
                        "OMMP81-PLUS XFP High Bias Current Warning Trap" 
        ::= { ommp81PlusAlarmNotification 9 }

	ommp81PlusXfpLowBiasCurrentWarningTrap NOTIFICATION-TYPE
		OBJECTS { ommp81PlusXfpLowBiasCurrentWarning  }
		STATUS  current
		DESCRIPTION
                        "OMMP81-PLUS XFP Low Bias Current Warning Trap" 
        ::= { ommp81PlusAlarmNotification 10 }

	ommp81PlusXfpInputHighPowerAlarmTrap NOTIFICATION-TYPE
		OBJECTS { ommp81PlusXfpInputHighPowerAlarm  }
		STATUS  current
		DESCRIPTION
                        "OMMP81-PLUS XFP Input High Power Alarm Trap" 
        ::= { ommp81PlusAlarmNotification 11 }

	ommp81PlusXfpInputLowPowerAlarmTrap NOTIFICATION-TYPE
		OBJECTS { ommp81PlusXfpInputLowPowerAlarm  }
		STATUS  current
		DESCRIPTION
                        "OMMP81-PLUS XFP Input Low Power Alarm Trap" 
        ::= { ommp81PlusAlarmNotification 12 }

	ommp81PlusXfpInputHighPowerWarningTrap NOTIFICATION-TYPE
		OBJECTS { ommp81PlusXfpInputHighPowerWarning  }
		STATUS  current
		DESCRIPTION
                        "OMMP81-PLUS XFP Input High Power Warning Trap" 
        ::= { ommp81PlusAlarmNotification 13 }

	ommp81PlusXfpInputLowPowerWarningTrap NOTIFICATION-TYPE
		OBJECTS { ommp81PlusXfpInputLowPowerWarning  }
		STATUS  current
		DESCRIPTION
                        "OMMP81-PLUS XFP Input Low Power Warning Trap" 
        ::= { ommp81PlusAlarmNotification 14 }

	ommp81PlusXfpOutputHighPowerAlarmTrap NOTIFICATION-TYPE
		OBJECTS { ommp81PlusXfpOutputHighPowerAlarm  }
		STATUS  current
		DESCRIPTION
                        "OMMP81-PLUS XFP Output High Power Alarm Trap" 
        ::= { ommp81PlusAlarmNotification 15 }

	ommp81PlusXfpOutputLowPowerAlarmTrap NOTIFICATION-TYPE
		OBJECTS { ommp81PlusXfpOutputLowPowerAlarm  }
		STATUS  current
		DESCRIPTION
                        "OMMP81-PLUS XFP Output Low Power Alarm Trap" 
        ::= { ommp81PlusAlarmNotification 16 }

	ommp81PlusXfpOutputHighPowerWarningTrap NOTIFICATION-TYPE
		OBJECTS { ommp81PlusXfpOutputHighPowerWarning  }
		STATUS  current
		DESCRIPTION
                        "OMMP81-PLUS XFP Output High Power Warning Trap" 
        ::= { ommp81PlusAlarmNotification 17 }

	ommp81PlusXfpOutputLowPowerWarningTrap NOTIFICATION-TYPE
		OBJECTS { ommp81PlusXfpOutputLowPowerWarning  }
		STATUS  current
		DESCRIPTION
                        "OMMP81-PLUS XFP Output Low Power Warning Trap" 
        ::= { ommp81PlusAlarmNotification 18 }

	ommp81PlusXfpHighSupplyVoltageAlarmTrap NOTIFICATION-TYPE
		OBJECTS { ommp81PlusXfpHighSupplyVoltageAlarm  }
		STATUS  current
		DESCRIPTION
                        "OMMP81-PLUS XFP High Supply Voltage Alarm Trap" 
        ::= { ommp81PlusAlarmNotification 19 }

	ommp81PlusXfpLowSupplyVoltageAlarmTrap NOTIFICATION-TYPE
		OBJECTS { ommp81PlusXfpLowSupplyVoltageAlarm  }
		STATUS  current
		DESCRIPTION
                        "OMMP81-PLUS XFP Low Supply Voltage Alarm Trap" 
        ::= { ommp81PlusAlarmNotification 20 }

	ommp81PlusXfpHighSupplyVoltageWarningTrap NOTIFICATION-TYPE
		OBJECTS { ommp81PlusXfpHighSupplyVoltageWarning  }
		STATUS  current
		DESCRIPTION
                        "OMMP81-PLUS XFP High Supply Voltage Warning Trap" 
        ::= { ommp81PlusAlarmNotification 21 }

	ommp81PlusXfpLowSupplyVoltageWarningTrap NOTIFICATION-TYPE
		OBJECTS { ommp81PlusXfpLowSupplyVoltageWarning  }
		STATUS  current
		DESCRIPTION
                        "OMMP81-PLUS XFP Low Supply Voltage Warning Trap" 
        ::= { ommp81PlusAlarmNotification 22 }

	ommp81PlusXfpPresenceAbsenceNotificationTrap NOTIFICATION-TYPE
		OBJECTS { ommp81PlusXfpPresenceAbsenceNotification  }
		STATUS  current
		DESCRIPTION
                        "OMMP81-PLUS XFP Presence Absence Notification Trap" 
        ::= { ommp81PlusAlarmNotification 23 }

	ommp81PlusSfpInputPowerFailureAlarmTrap NOTIFICATION-TYPE
		OBJECTS { ommp81PlusSfpInputPowerFailureAlarm  }
		STATUS  current
		DESCRIPTION
                        "OMMP81-PLUS SFP Input Power Failure Alarm Trap" 
        ::= { ommp81PlusAlarmNotification 41 }

	ommp81PlusSfpOutputPowerFailureAlarmTrap NOTIFICATION-TYPE
		OBJECTS { ommp81PlusSfpOutputPowerFailureAlarm  }
		STATUS  current
		DESCRIPTION
                        "OMMP81-PLUS SFP Output Power Failure Alarm Trap" 
        ::= { ommp81PlusAlarmNotification 42 }

	ommp81PlusSfpHighTemperatureAlarmTrap NOTIFICATION-TYPE
		OBJECTS { ommp81PlusSfpHighTemperatureAlarm  }
		STATUS  current
		DESCRIPTION
                        "OMMP81-PLUS SFP High Temperature Alarm Trap" 
        ::= { ommp81PlusAlarmNotification 43 }

	ommp81PlusSfpLowTemperatureAlarmTrap NOTIFICATION-TYPE
		OBJECTS { ommp81PlusSfpLowTemperatureAlarm  }
		STATUS  current
		DESCRIPTION
                        "OMMP81-PLUS SFP Low Temperature Alarm Trap" 
        ::= { ommp81PlusAlarmNotification 44 }

	ommp81PlusSfpHighTemperatureWarningTrap NOTIFICATION-TYPE
		OBJECTS { ommp81PlusSfpHighTemperatureWarning  }
		STATUS  current
		DESCRIPTION
                        "OMMP81-PLUS SFP High Temperature Warning Trap" 
        ::= { ommp81PlusAlarmNotification 45 }

	ommp81PlusSfpLowTemperatureWarningTrap NOTIFICATION-TYPE
		OBJECTS { ommp81PlusSfpLowTemperatureWarning  }
		STATUS  current
		DESCRIPTION
                        "OMMP81-PLUS SFP Low Temperature Warning Trap" 
        ::= { ommp81PlusAlarmNotification 46 }

	ommp81PlusSfpHighBiasCurrentAlarmTrap NOTIFICATION-TYPE
		OBJECTS { ommp81PlusSfpHighBiasCurrentAlarm  }
		STATUS  current
		DESCRIPTION
                        "OMMP81-PLUS SFP High Bias Current Alarm Trap" 
        ::= { ommp81PlusAlarmNotification 47 }

	ommp81PlusSfpLowBiasCurrentAlarmTrap NOTIFICATION-TYPE
		OBJECTS { ommp81PlusSfpLowBiasCurrentAlarm  }
		STATUS  current
		DESCRIPTION
                        "OMMP81-PLUS SFP Low Bias Current Alarm Trap" 
        ::= { ommp81PlusAlarmNotification 48 }

	ommp81PlusSfpHighBiasCurrentWarningTrap NOTIFICATION-TYPE
		OBJECTS { ommp81PlusSfpHighBiasCurrentWarning  }
		STATUS  current
		DESCRIPTION
                        "OMMP81-PLUS SFP High Bias Current Warning Trap" 
        ::= { ommp81PlusAlarmNotification 49 }

	ommp81PlusSfpLowBiasCurrentWarningTrap NOTIFICATION-TYPE
		OBJECTS { ommp81PlusSfpLowBiasCurrentWarning  }
		STATUS  current
		DESCRIPTION
                        "OMMP81-PLUS SFP Low Bias Current Warning Trap" 
        ::= { ommp81PlusAlarmNotification 50 }

	ommp81PlusSfpInputHighPowerAlarmTrap NOTIFICATION-TYPE
		OBJECTS { ommp81PlusSfpInputHighPowerAlarm  }
		STATUS  current
		DESCRIPTION
                        "OMMP81-PLUS SFP Input High Power Alarm Trap" 
        ::= { ommp81PlusAlarmNotification 51 }

	ommp81PlusSfpInputLowPowerAlarmTrap NOTIFICATION-TYPE
		OBJECTS { ommp81PlusSfpInputLowPowerAlarm  }
		STATUS  current
		DESCRIPTION
                        "OMMP81-PLUS SFP Input Low Power Alarm Trap" 
        ::= { ommp81PlusAlarmNotification 52 }

	ommp81PlusSfpInputHighPowerWarningTrap NOTIFICATION-TYPE
		OBJECTS { ommp81PlusSfpInputHighPowerWarning  }
		STATUS  current
		DESCRIPTION
                        "OMMP81-PLUS SFP Input High Power Warning Trap" 
        ::= { ommp81PlusAlarmNotification 53 }

	ommp81PlusSfpInputLowPowerWarningTrap NOTIFICATION-TYPE
		OBJECTS { ommp81PlusSfpInputLowPowerWarning  }
		STATUS  current
		DESCRIPTION
                        "OMMP81-PLUS SFP Input Low Power Warning Trap" 
        ::= { ommp81PlusAlarmNotification 54 }

	ommp81PlusSfpOutputHighPowerAlarmTrap NOTIFICATION-TYPE
		OBJECTS { ommp81PlusSfpOutputHighPowerAlarm  }
		STATUS  current
		DESCRIPTION
                        "OMMP81-PLUS SFP Output High Power Alarm Trap" 
        ::= { ommp81PlusAlarmNotification 55 }

	ommp81PlusSfpOutputLowPowerAlarmTrap NOTIFICATION-TYPE
		OBJECTS { ommp81PlusSfpOutputLowPowerAlarm  }
		STATUS  current
		DESCRIPTION
                        "OMMP81-PLUS SFP Output Low Power Alarm Trap" 
        ::= { ommp81PlusAlarmNotification 56 }

	ommp81PlusSfpOutputHighPowerWarningTrap NOTIFICATION-TYPE
		OBJECTS { ommp81PlusSfpOutputHighPowerWarning  }
		STATUS  current
		DESCRIPTION
                        "OMMP81-PLUS SFP Output High Power Warning Trap" 
        ::= { ommp81PlusAlarmNotification 57 }

	ommp81PlusSfpOutputLowPowerWarningTrap NOTIFICATION-TYPE
		OBJECTS { ommp81PlusSfpOutputLowPowerWarning  }
		STATUS  current
		DESCRIPTION
                        "OMMP81-PLUS SFP Output Low Power Warning Trap" 
        ::= { ommp81PlusAlarmNotification 58 }

	ommp81PlusSfpHighSupplyVoltageAlarmTrap NOTIFICATION-TYPE
		OBJECTS { ommp81PlusSfpHighSupplyVoltageAlarm  }
		STATUS  current
		DESCRIPTION
                        "OMMP81-PLUS SFP High Supply Voltage Alarm Trap" 
        ::= { ommp81PlusAlarmNotification 59 }

	ommp81PlusSfpLowSupplyVoltageAlarmTrap NOTIFICATION-TYPE
		OBJECTS { ommp81PlusSfpLowSupplyVoltageAlarm  }
		STATUS  current
		DESCRIPTION
                        "OMMP81-PLUS SFP Low Supply Voltage Alarm Trap" 
        ::= { ommp81PlusAlarmNotification 60 }

	ommp81PlusSfpHighSupplyVoltageWarningTrap NOTIFICATION-TYPE
		OBJECTS { ommp81PlusSfpHighSupplyVoltageWarning  }
		STATUS  current
		DESCRIPTION
                        "OMMP81-PLUS SFP High Supply Voltage Warning Trap" 
        ::= { ommp81PlusAlarmNotification 61 }

	ommp81PlusSfpLowSupplyVoltageWarningTrap NOTIFICATION-TYPE
		OBJECTS { ommp81PlusSfpLowSupplyVoltageWarning  }
		STATUS  current
		DESCRIPTION
                        "OMMP81-PLUS SFP Low Supply Voltage Warning Trap" 
        ::= { ommp81PlusAlarmNotification 62 }

	ommp81PlusSfpPresenceAbsenceNotificationTrap NOTIFICATION-TYPE
		OBJECTS { ommp81PlusSfpPresenceAbsenceNotification  }
		STATUS  current
		DESCRIPTION
                        "OMMP81-PLUS SFP Presence Absence Notification Trap" 
        ::= { ommp81PlusAlarmNotification 63 }

	ommp81PlusSfpTransmitFaultPresenceAlarmTrap NOTIFICATION-TYPE
		OBJECTS { ommp81PlusSfpTransmitFaultPresenceAlarm  }
		STATUS  current
		DESCRIPTION
                        "OMMP81-PLUS SFP Transmit Fault Presence Alarm Trap" 
        ::= { ommp81PlusAlarmNotification 64 }

	ommp81PlusOtuLossOfSignalAlarmTrap NOTIFICATION-TYPE
		OBJECTS { ommp81PlusOtuLossOfSignalAlarm  }
		STATUS  current
		DESCRIPTION
                        "OMMP81-PLUS OTU Loss Of Signal Alarm Trap" 
        ::= { ommp81PlusAlarmNotification 81 }

	ommp81PlusOtuLossOfFrameAlarmTrap NOTIFICATION-TYPE
		OBJECTS { ommp81PlusOtuLossOfFrameAlarm  }
		STATUS  current
		DESCRIPTION
                        "OMMP81-PLUS OTU Loss Of Frame Alarm Trap" 
        ::= { ommp81PlusAlarmNotification 82 }

	ommp81PlusOtuOutOfFrameAlarmTrap NOTIFICATION-TYPE
		OBJECTS { ommp81PlusOtuOutOfFrameAlarm  }
		STATUS  current
		DESCRIPTION
                        "OMMP81-PLUS OTU Out Of Frame Alarm Trap" 
        ::= { ommp81PlusAlarmNotification 83 }

	ommp81PlusOtuLossOfMultiFrameAlarmTrap NOTIFICATION-TYPE
		OBJECTS { ommp81PlusOtuLossOfMultiFrameAlarm  }
		STATUS  current
		DESCRIPTION
                        "OMMP81-PLUS OTU Loss Of Multi Frame Alarm Trap" 
        ::= { ommp81PlusAlarmNotification 84 }

	ommp81PlusOtuOutOfMultiFrameAlarmTrap NOTIFICATION-TYPE
		OBJECTS { ommp81PlusOtuOutOfMultiFrameAlarm  }
		STATUS  current
		DESCRIPTION
                        "OMMP81-PLUS OTU Out Of Multi Frame Alarm Trap" 
        ::= { ommp81PlusAlarmNotification 85 }

	ommp81PlusOtuSignalFailAlarmTrap NOTIFICATION-TYPE
		OBJECTS { ommp81PlusOtuSignalFailAlarm  }
		STATUS  current
		DESCRIPTION
                        "OMMP81-PLUS OTU Signal Fail Alarm Trap" 
        ::= { ommp81PlusAlarmNotification 86 }

	ommp81PlusOtuSignalDegradeAlarmTrap NOTIFICATION-TYPE
		OBJECTS { ommp81PlusOtuSignalDegradeAlarm  }
		STATUS  current
		DESCRIPTION
                        "OMMP81-PLUS OTU Signal Degrade Alarm Trap" 
        ::= { ommp81PlusAlarmNotification 87 }

	ommp81PlusOtuAlarmIndicationSignalAlarmTrap NOTIFICATION-TYPE
		OBJECTS { ommp81PlusOtuAlarmIndicationSignalAlarm  }
		STATUS  current
		DESCRIPTION
                        "OMMP81-PLUS OTU Alarm Indication Signal Alarm Trap" 
        ::= { ommp81PlusAlarmNotification 88 }

	ommp81PlusOtuIncomingAlignmentErrorAlarmTrap NOTIFICATION-TYPE
		OBJECTS { ommp81PlusOtuIncomingAlignmentErrorAlarm  }
		STATUS  current
		DESCRIPTION
                        "OMMP81-PLUS OTU Incoming Alignment Error Alarm Trap" 
        ::= { ommp81PlusAlarmNotification 89 }

	ommp81PlusOtuTraceIdentifierMismatchAlarmTrap NOTIFICATION-TYPE
		OBJECTS { ommp81PlusOtuTraceIdentifierMismatchAlarm  }
		STATUS  current
		DESCRIPTION
                        "OMMP81-PLUS OTU Trace Identifier Mismatch Alarm Trap" 
        ::= { ommp81PlusAlarmNotification 90 }

	ommp81PlusOtuBackwardIncomingAlignmentErrorAlarmTrap NOTIFICATION-TYPE
		OBJECTS { ommp81PlusOtuBackwardIncomingAlignmentErrorAlarm  }
		STATUS  current
		DESCRIPTION
                        "OMMP81-PLUS OTU Backward Incoming Alignment Error Alarm Trap" 
        ::= { ommp81PlusAlarmNotification 91 }

	ommp81PlusOtuBackwardDefectIndicationAlarmTrap NOTIFICATION-TYPE
		OBJECTS { ommp81PlusOtuBackwardDefectIndicationAlarm  }
		STATUS  current
		DESCRIPTION
                        "OMMP81-PLUS OTU Backward Defect Indication Alarm Trap" 
        ::= { ommp81PlusAlarmNotification 92 }

	ommp81PlusOduSignalFailAlarmTrap NOTIFICATION-TYPE
		OBJECTS { ommp81PlusOduSignalFailAlarm  }
		STATUS  current
		DESCRIPTION
                        "OMMP81-PLUS ODU Signal Fail Alarm Trap" 
        ::= { ommp81PlusAlarmNotification 111 }

	ommp81PlusOduSignalDegradeAlarmTrap NOTIFICATION-TYPE
		OBJECTS { ommp81PlusOduSignalDegradeAlarm  }
		STATUS  current
		DESCRIPTION
                        "OMMP81-PLUS ODU Signal Degrade Alarm Trap" 
        ::= { ommp81PlusAlarmNotification 112 }

	ommp81PlusOduAlarmIndicationSignalAlarmTrap NOTIFICATION-TYPE
		OBJECTS { ommp81PlusOduAlarmIndicationSignalAlarm  }
		STATUS  current
		DESCRIPTION
                        "OMMP81-PLUS ODU Alarm Indication Signal Alarm Trap" 
        ::= { ommp81PlusAlarmNotification 113 }

	ommp81PlusOduTcm1IncomingAlignmentErrorAlarmTrap NOTIFICATION-TYPE
		OBJECTS { ommp81PlusOduTcm1IncomingAlignmentErrorAlarm  }
		STATUS  current
		DESCRIPTION
                        "OMMP81-PLUS ODU TCM1 Incoming Alignment Error Alarm Trap" 
        ::= { ommp81PlusAlarmNotification 114 }

	ommp81PlusOduTcm2IncomingAlignmentErrorAlarmTrap NOTIFICATION-TYPE
		OBJECTS { ommp81PlusOduTcm2IncomingAlignmentErrorAlarm  }
		STATUS  current
		DESCRIPTION
                        "OMMP81-PLUS ODU TCM2 Incoming Alignment Error Alarm Trap" 
        ::= { ommp81PlusAlarmNotification 115 }

	ommp81PlusOduTcm3IncomingAlignmentErrorAlarmTrap NOTIFICATION-TYPE
		OBJECTS { ommp81PlusOduTcm3IncomingAlignmentErrorAlarm  }
		STATUS  current
		DESCRIPTION
                        "OMMP81-PLUS ODU TCM3 Incoming Alignment Error Alarm Trap" 
        ::= { ommp81PlusAlarmNotification 116 }

	ommp81PlusOduTcm4IncomingAlignmentErrorAlarmTrap NOTIFICATION-TYPE
		OBJECTS { ommp81PlusOduTcm4IncomingAlignmentErrorAlarm  }
		STATUS  current
		DESCRIPTION
                        "OMMP81-PLUS ODU TCM4 Incoming Alignment Error Alarm Trap" 
        ::= { ommp81PlusAlarmNotification 117 }

	ommp81PlusOduTcm5IncomingAlignmentErrorAlarmTrap NOTIFICATION-TYPE
		OBJECTS { ommp81PlusOduTcm5IncomingAlignmentErrorAlarm  }
		STATUS  current
		DESCRIPTION
                        "OMMP81-PLUS ODU TCM5 Incoming Alignment Error Alarm Trap" 
        ::= { ommp81PlusAlarmNotification 118 }

	ommp81PlusOduTcm6IncomingAlignmentErrorAlarmTrap NOTIFICATION-TYPE
		OBJECTS { ommp81PlusOduTcm6IncomingAlignmentErrorAlarm  }
		STATUS  current
		DESCRIPTION
                        "OMMP81-PLUS ODU TCM6 Incoming Alignment Error Alarm Trap" 
        ::= { ommp81PlusAlarmNotification 119 }

	ommp81PlusOduTraceIdentifierMismatchAlarmTrap NOTIFICATION-TYPE
		OBJECTS { ommp81PlusOduTraceIdentifierMismatchAlarm  }
		STATUS  current
		DESCRIPTION
                        "OMMP81-PLUS ODU Trace Identifier Mismatch Alarm Trap" 
        ::= { ommp81PlusAlarmNotification 120 }

	ommp81PlusOduLockedDefectAlarmTrap NOTIFICATION-TYPE
		OBJECTS { ommp81PlusOduLockedDefectAlarm  }
		STATUS  current
		DESCRIPTION
                        "OMMP81-PLUS ODU Locked Defect Alarm Trap" 
        ::= { ommp81PlusAlarmNotification 121 }

	ommp81PlusOduOpenConnectionIndicationAlarmTrap NOTIFICATION-TYPE
		OBJECTS { ommp81PlusOduOpenConnectionIndicationAlarm  }
		STATUS  current
		DESCRIPTION
                        "OMMP81-PLUS ODU Open Connection Indication Alarm Trap" 
        ::= { ommp81PlusAlarmNotification 122 }

	ommp81PlusOduBackwardDefectIndicationAlarmTrap NOTIFICATION-TYPE
		OBJECTS { ommp81PlusOduBackwardDefectIndicationAlarm  }
		STATUS  current
		DESCRIPTION
                        "OMMP81-PLUS ODU Backward Defect Indication Alarm Trap" 
        ::= { ommp81PlusAlarmNotification 123 }

	ommp81PlusOduTcm1BackwardIncomingAlignmentErrorAlarmTrap NOTIFICATION-TYPE
		OBJECTS { ommp81PlusOduTcm1BackwardIncomingAlignmentErrorAlarm  }
		STATUS  current
		DESCRIPTION
                        "OMMP81-PLUS ODU TCM1 Backward Incoming Alignment Error Alarm Trap" 
        ::= { ommp81PlusAlarmNotification 124 }

	ommp81PlusOduTcm2BackwardIncomingAlignmentErrorAlarmTrap NOTIFICATION-TYPE
		OBJECTS { ommp81PlusOduTcm2BackwardIncomingAlignmentErrorAlarm  }
		STATUS  current
		DESCRIPTION
                        "OMMP81-PLUS ODU TCM2 Backward Incoming Alignment Error Alarm Trap" 
        ::= { ommp81PlusAlarmNotification 125 }

	ommp81PlusOduTcm3BackwardIncomingAlignmentErrorAlarmTrap NOTIFICATION-TYPE
		OBJECTS { ommp81PlusOduTcm3BackwardIncomingAlignmentErrorAlarm  }
		STATUS  current
		DESCRIPTION
                        "OMMP81-PLUS ODU TCM3 Backward Incoming Alignment Error Alarm Trap" 
        ::= { ommp81PlusAlarmNotification 126 }

	ommp81PlusOduTcm4BackwardIncomingAlignmentErrorAlarmTrap NOTIFICATION-TYPE
		OBJECTS { ommp81PlusOduTcm4BackwardIncomingAlignmentErrorAlarm  }
		STATUS  current
		DESCRIPTION
                        "OMMP81-PLUS ODU TCM4 Backward Incoming Alignment Error Alarm Trap" 
        ::= { ommp81PlusAlarmNotification 127 }

	ommp81PlusOduTcm5BackwardIncomingAlignmentErrorAlarmTrap NOTIFICATION-TYPE
		OBJECTS { ommp81PlusOduTcm5BackwardIncomingAlignmentErrorAlarm  }
		STATUS  current
		DESCRIPTION
                        "OMMP81-PLUS ODU TCM5 Backward Incoming Alignment Error Alarm Trap" 
        ::= { ommp81PlusAlarmNotification 128 }

	ommp81PlusOduTcm6BackwardIncomingAlignmentErrorAlarmTrap NOTIFICATION-TYPE
		OBJECTS { ommp81PlusOduTcm6BackwardIncomingAlignmentErrorAlarm  }
		STATUS  current
		DESCRIPTION
                        "OMMP81-PLUS ODU TCM6 Backward Incoming Alignment Error Alarm Trap" 
        ::= { ommp81PlusAlarmNotification 129 }

	ommp81PlusOduLossOfFrameLossOfMultiframeAlarmTrap NOTIFICATION-TYPE
		OBJECTS { ommp81PlusOduLossOfFrameLossOfMultiframeAlarm  }
		STATUS  current
		DESCRIPTION
                        "OMMP81-PLUS ODU Loss Of Frame Loss Of Multiframe Alarm Trap" 
        ::= { ommp81PlusAlarmNotification 130 }

	ommp81PlusOpuPayloadMismatchAlarmTrap NOTIFICATION-TYPE
		OBJECTS { ommp81PlusOpuPayloadMismatchAlarm  }
		STATUS  current
		DESCRIPTION
                        "OMMP81-PLUS OPU Payload Mismatch Alarm Trap" 
        ::= { ommp81PlusAlarmNotification 135 }

	ommp81PlusOchLossOfPayloadAlarmTrap NOTIFICATION-TYPE
		OBJECTS { ommp81PlusOchLossOfPayloadAlarm  }
		STATUS  current
		DESCRIPTION
                        "OMMP81-PLUS OCH Loss Of Payload Alarm Trap" 
        ::= { ommp81PlusAlarmNotification 136 }

	ommp81PlusSdhLossOfSignalAlarmTrap NOTIFICATION-TYPE
		OBJECTS { ommp81PlusSdhLossOfSignalAlarm  }
		STATUS  current
		DESCRIPTION
                        "OMMP81-PLUS SDH Loss Of Signal Alarm Trap" 
        ::= { ommp81PlusAlarmNotification 141 }

	ommp81PlusSdhOutOfFrameAlarmTrap NOTIFICATION-TYPE
		OBJECTS { ommp81PlusSdhOutOfFrameAlarm  }
		STATUS  current
		DESCRIPTION
                        "OMMP81-PLUS SDH Out Of Frame Alarm Trap" 
        ::= { ommp81PlusAlarmNotification 142 }

	ommp81PlusSdhLossOfFrameAlarmTrap NOTIFICATION-TYPE
		OBJECTS { ommp81PlusSdhLossOfFrameAlarm  }
		STATUS  current
		DESCRIPTION
                        "OMMP81-PLUS SDH Loss Of Frame Alarm Trap" 
        ::= { ommp81PlusAlarmNotification 143 }

	ommp81PlusSdhRsAlarmIndicationSignalAlarmTrap NOTIFICATION-TYPE
		OBJECTS { ommp81PlusSdhRsAlarmIndicationSignalAlarm  }
		STATUS  current
		DESCRIPTION
                        "OMMP81-PLUS SDH RS Alarm Indication Signal Alarm Trap" 
        ::= { ommp81PlusAlarmNotification 144 }

	ommp81PlusSdhRsTraceIdentifierMismatchAlarmTrap NOTIFICATION-TYPE
		OBJECTS { ommp81PlusSdhRsTraceIdentifierMismatchAlarm  }
		STATUS  current
		DESCRIPTION
                        "OMMP81-PLUS SDH RS Trace Identifier Mismatch Alarm Trap" 
        ::= { ommp81PlusAlarmNotification 145 }

	ommp81PlusSdhAuAlarmIndicationSignalAlarmTrap NOTIFICATION-TYPE
		OBJECTS { ommp81PlusSdhAuAlarmIndicationSignalAlarm  }
		STATUS  current
		DESCRIPTION
                        "OMMP81-PLUS SDH AU Alarm Indication Signal Alarm Trap" 
        ::= { ommp81PlusAlarmNotification 146 }

	ommp81PlusSdhAuLossOfPointerAlarmTrap NOTIFICATION-TYPE
		OBJECTS { ommp81PlusSdhAuLossOfPointerAlarm  }
		STATUS  current
		DESCRIPTION
                        "OMMP81-PLUS SDH AU Loss Of Pointer Alarm Trap" 
        ::= { ommp81PlusAlarmNotification 147 }

	ommp81PlusSdhMsAlarmIndicationSignalAlarmTrap NOTIFICATION-TYPE
		OBJECTS { ommp81PlusSdhMsAlarmIndicationSignalAlarm  }
		STATUS  current
		DESCRIPTION
                        "OMMP81-PLUS SDH MS Alarm Indication Signal Alarm Trap" 
        ::= { ommp81PlusAlarmNotification 148 }

	ommp81PlusSdhMsRemoteErrorIndicationAlarmTrap NOTIFICATION-TYPE
		OBJECTS { ommp81PlusSdhMsRemoteErrorIndicationAlarm  }
		STATUS  current
		DESCRIPTION
                        "OMMP81-PLUS SDH MS Remote Error Indication Alarm Trap" 
        ::= { ommp81PlusAlarmNotification 149 }

	ommp81PlusSdhMsRemoteDefectIndicationAlarmTrap NOTIFICATION-TYPE
		OBJECTS { ommp81PlusSdhMsRemoteDefectIndicationAlarm  }
		STATUS  current
		DESCRIPTION
                        "OMMP81-PLUS SDH MS Remote Defect Indication Alarm Trap" 
        ::= { ommp81PlusAlarmNotification 150 }

	ommp81PlusSdhMsRemoteFailureIndicationAlarmTrap NOTIFICATION-TYPE
		OBJECTS { ommp81PlusSdhMsRemoteFailureIndicationAlarm  }
		STATUS  current
		DESCRIPTION
                        "OMMP81-PLUS SDH MS Remote Failure Indication Alarm Trap" 
        ::= { ommp81PlusAlarmNotification 151 }

	ommp81PlusSdhMsB2ExcessiveErrorAlarmTrap NOTIFICATION-TYPE
		OBJECTS { ommp81PlusSdhMsB2ExcessiveErrorAlarm  }
		STATUS  current
		DESCRIPTION
                        "OMMP81-PLUS SDH MS B2 Signal Fail Alarm Trap" 
        ::= { ommp81PlusAlarmNotification 152 }

	ommp81PlusSdhMsB2SignalDegradeAlarmTrap NOTIFICATION-TYPE
		OBJECTS { ommp81PlusSdhMsB2SignalDegradeAlarm  }
		STATUS  current
		DESCRIPTION
                        "OMMP81-PLUS SDH MS B2 Signal Degrade Alarm Trap" 
        ::= { ommp81PlusAlarmNotification 153 }

	ommp81PlusSdhLossOfSequenceSynchronisationAlarmTrap NOTIFICATION-TYPE
		OBJECTS { ommp81PlusSdhLossOfSequenceSynchronisationAlarm  }
		STATUS  current
		DESCRIPTION
                        "OMMP81-PLUS SDH Loss Of Sequence Synchronisation Alarm Trap" 
        ::= { ommp81PlusAlarmNotification 154 }

	ommp81PlusSdhLowerOrderPathPayloadLabelMismatchAlarmTrap NOTIFICATION-TYPE
		OBJECTS { ommp81PlusSdhLowerOrderPathPayloadLabelMismatchAlarm  }
		STATUS  current
		DESCRIPTION
                        "OMMP81-PLUS SDH Lower Order Path Payload Label Mismatch Alarm Trap" 
        ::= { ommp81PlusAlarmNotification 155 }

	ommp81PlusSdhLowerOrderPathUnequippedAlarmTrap NOTIFICATION-TYPE
		OBJECTS { ommp81PlusSdhLowerOrderPathUnequippedAlarm  }
		STATUS  current
		DESCRIPTION
                        "OMMP81-PLUS SDH Lower Order Path Unequipped Alarm Trap" 
        ::= { ommp81PlusAlarmNotification 156 }

	ommp81PlusEthernetLossOfSignalAlarmTrap NOTIFICATION-TYPE
		OBJECTS { ommp81PlusEthernetLossOfSignalAlarm  }
		STATUS  current
		DESCRIPTION
                        "OMMP81-PLUS Ethernet Loss Of Signal Alarm Trap" 
        ::= { ommp81PlusAlarmNotification 171 }

	ommp81PlusEthernetLossOfSignalSyncAlarmTrap NOTIFICATION-TYPE
		OBJECTS { ommp81PlusEthernetLossOfSignalSyncAlarm  }
		STATUS  current
		DESCRIPTION
                        "OMMP81-PLUS Ethernet Loss Of Signal Sync Alarm Trap" 
        ::= { ommp81PlusAlarmNotification 172 }

	ommp81PlusEthernetLinkFailureAlarmTrap NOTIFICATION-TYPE
		OBJECTS { ommp81PlusEthernetLinkFailureAlarm  }
		STATUS  current
		DESCRIPTION
                        "OMMP81-PLUS Ethernet Link Failure Alarm Trap" 
        ::= { ommp81PlusAlarmNotification 173 }

	ommp81PlusEthernetAutoNegotiationAlarmTrap NOTIFICATION-TYPE
		OBJECTS { ommp81PlusEthernetAutoNegotiationAlarm  }
		STATUS  current
		DESCRIPTION
                        "OMMP81-PLUS Ethernet AUto Negotiation Alarm Trap" 
        ::= { ommp81PlusAlarmNotification 174 }

	ommp81PlusEthernetFrameCheckSequenceAlarmTrap NOTIFICATION-TYPE
		OBJECTS { ommp81PlusEthernetFrameCheckSequenceAlarm  }
		STATUS  current
		DESCRIPTION
                        "OMMP81-PLUS Ethernet Frame Check Sequence Alarm Trap" 
        ::= { ommp81PlusAlarmNotification 175 }

	ommp81PlusEthernetCarrierStatusAlarmTrap NOTIFICATION-TYPE
		OBJECTS { ommp81PlusEthernetCarrierStatusAlarm  }
		STATUS  current
		DESCRIPTION
                        "OMMP81-PLUS Ethernet Carrier Status Alarm Trap" 
        ::= { ommp81PlusAlarmNotification 176 }

	ommp81PlusEthernetHighBerAlarmTrap NOTIFICATION-TYPE
		OBJECTS { ommp81PlusEthernetHighBerAlarm  }
		STATUS  current
		DESCRIPTION
                        "OMMP81-PLUS Ethernet High Ber Alarm Trap" 
        ::= { ommp81PlusAlarmNotification 177 }

	ommp81PlusEthernetLocalFaultAlarmTrap NOTIFICATION-TYPE
		OBJECTS { ommp81PlusEthernetLocalFaultAlarm  }
		STATUS  current
		DESCRIPTION
                        "OMMP81-PLUS Ethernet Local Fault Alarm Trap" 
        ::= { ommp81PlusAlarmNotification 178 }

	ommp81PlusEthernetRemoteFaultAlarmTrap NOTIFICATION-TYPE
		OBJECTS { ommp81PlusEthernetRemoteFaultAlarm  }
		STATUS  current
		DESCRIPTION
                        "OMMP81-PLUS Ethernet Remote Fault Alarm Trap" 
        ::= { ommp81PlusAlarmNotification 179 }

	ommp81PlusFcTransmitDisparityInversionDefectAlarmTrap NOTIFICATION-TYPE
		OBJECTS { ommp81PlusFcTransmitDisparityInversionDefectAlarm  }
		STATUS  current
		DESCRIPTION
                        "OMMP81-PLUS FC Transmit Display Invert Alarm Trap" 
        ::= { ommp81PlusAlarmNotification 191 }

	ommp81PlusFcTransmitDigitalLossOfLinkDefectAlarmTrap NOTIFICATION-TYPE
		OBJECTS { ommp81PlusFcTransmitDigitalLossOfLinkDefectAlarm  }
		STATUS  current
		DESCRIPTION
                        "OMMP81-PLUS FC Transmit Dlolb Alarm Trap" 
        ::= { ommp81PlusAlarmNotification 192 }

	ommp81PlusFcTrasnmitLossOfSynchronizationDefectAlarmTrap NOTIFICATION-TYPE
		OBJECTS { ommp81PlusFcTrasnmitLossOfSynchronizationDefectAlarm  }
		STATUS  current
		DESCRIPTION
                        "OMMP81-PLUS FC Transmit Sync Alarm Trap" 
        ::= { ommp81PlusAlarmNotification 193 }

	ommp81PlusFcReceiveDigitalLossOfLinkDefectAlarmTrap NOTIFICATION-TYPE
		OBJECTS { ommp81PlusFcReceiveDigitalLossOfLinkDefectAlarm  }
		STATUS  current
		DESCRIPTION
                        "OMMP81-PLUS FC Receive Dlolb Alarm Trap" 
        ::= { ommp81PlusAlarmNotification 194 }

	ommp81PlusFcReceiveLossOfSynchronizationDefectAlarmTrap NOTIFICATION-TYPE
		OBJECTS { ommp81PlusFcReceiveLossOfSynchronizationDefectAlarm  }
		STATUS  current
		DESCRIPTION
                        "OMMP81-PLUS FC Receive Sync Alarm Trap" 
        ::= { ommp81PlusAlarmNotification 195 }

	ommp81PlusFcReceiveTransitionDetectDefectAlarmTrap NOTIFICATION-TYPE
		OBJECTS { ommp81PlusFcReceiveTransitionDetectDefectAlarm  }
		STATUS  current
		DESCRIPTION
                        "OMMP81-PLUS FC Receive Xdet Alarm Trap" 
        ::= { ommp81PlusAlarmNotification 196 }

	ommp81PlusFcReceiveAnalogLossOfSignalDefectAlarmTrap NOTIFICATION-TYPE
		OBJECTS { ommp81PlusFcReceiveAnalogLossOfSignalDefectAlarm  }
		STATUS  current
		DESCRIPTION
                        "OMMP81-PLUS FC Receive Asd Alarm Trap" 
        ::= { ommp81PlusAlarmNotification 197 }

	ommp81PlusFcReceiveLineCodeViolationDefectAlarmTrap NOTIFICATION-TYPE
		OBJECTS { ommp81PlusFcReceiveLineCodeViolationDefectAlarm  }
		STATUS  current
		DESCRIPTION
                        "OMMP81-PLUS FC Receive Lcv Alarm Trap" 
        ::= { ommp81PlusAlarmNotification 198 }

	ommp81PlusGfpCsfSignalFailAlarmTrap NOTIFICATION-TYPE
		OBJECTS { ommp81PlusGfpCsfSignalFailAlarm  }
		STATUS  current
		DESCRIPTION
                        "OMMP81-PLUS GFP Csf Signal Failure Alarm Trap" 
        ::= { ommp81PlusAlarmNotification 211 }

	ommp81PlusGfpCsfLinkFailAlarmTrap NOTIFICATION-TYPE
		OBJECTS { ommp81PlusGfpCsfLinkFailAlarm  }
		STATUS  current
		DESCRIPTION
                        "OMMP81-PLUS GFP Csf Link Failure Alarm Trap" 
        ::= { ommp81PlusAlarmNotification 212 }

	ommp81PlusGfpCoreHeaderErrorAlarmTrap NOTIFICATION-TYPE
		OBJECTS { ommp81PlusGfpCoreHeaderErrorAlarm  }
		STATUS  current
		DESCRIPTION
                        "OMMP81-PLUS GFP Core Header Error Alarm Trap" 
        ::= { ommp81PlusAlarmNotification 213 }

	ommp81PlusGfpExtentionHeaderErrorAlarmTrap NOTIFICATION-TYPE
		OBJECTS { ommp81PlusGfpExtentionHeaderErrorAlarm  }
		STATUS  current
		DESCRIPTION
                        "OMMP81-PLUS GFP Extention Header Error Alarm Trap" 
        ::= { ommp81PlusAlarmNotification 214 }

--*****************************************************************************
--				    PERFORMANCE
--*****************************************************************************        

	ommp81PlusPerformanceTable OBJECT-TYPE
	      SYNTAX  SEQUENCE OF Ommp81PlusPerformanceEntry
              MAX-ACCESS  not-accessible
              STATUS  current
              DESCRIPTION
                      "Gives Optical and Signal performance status of the OMMP81-PLUS card"
		::= { ommp81PlusPerformance 1 }	

	ommp81PlusPerformanceEntry   OBJECT-TYPE
              SYNTAX  Ommp81PlusPerformanceEntry 
              MAX-ACCESS  not-accessible
              STATUS  current
              DESCRIPTION 
              	""
		INDEX   { node, rack , subRack , slot , ommp81PlusInterfaceNumber}
		::= { ommp81PlusPerformanceTable 1 }
	
	Ommp81PlusPerformanceEntry ::= 
		SEQUENCE {
				ommp81PlusXfpInputPower							DisplayString,
				ommp81PlusXfpOutputPower						DisplayString,
				ommp81PlusXfpBiasCurrent						DisplayString,
				ommp81PlusXfpSupplyVoltage						DisplayString,
				ommp81PlusXfpTemperature						DisplayString,
				ommp81PlusSfpInputPower							DisplayString,
				ommp81PlusSfpOutputPower						DisplayString,
				ommp81PlusSfpBiasCurrent						DisplayString,
				ommp81PlusSfpSupplyVoltage						DisplayString,
				ommp81PlusSfpTemperature						DisplayString,
				ommp81PlusOtnFecUncorrectedWords					DisplayString,
				ommp81PlusOtnFecCorrectedBits						DisplayString,
				ommp81PlusOtnFecZerosCorrectedBits					DisplayString,
				ommp81PlusOtnFecOnesCorrectedBits					DisplayString,
				ommp81PlusOtuBitInterleavedParityErrors					DisplayString,
				ommp81PlusOtuIncomingAlignmentErrorSeconds				DisplayString,
				ommp81PlusOtuBackwardErrorIndicationErrorCount				DisplayString,
				ommp81PlusOtuBackwardIncomingAlignmentErrorSeconds			DisplayString,
				ommp81PlusOtuErrorFreeSeconds						DisplayString,
				ommp81PlusOtuErrorSeconds						DisplayString,
				ommp81PlusOtuBackgroundBlockErrors					DisplayString,
				ommp81PlusOtuSevereErrorSeconds						DisplayString,
				ommp81PlusOtuUnavailableSeconds						DisplayString,
				ommp81PlusOtuBackgroundBlockErrorRatio					DisplayString,
				ommp81PlusOtuSevereErrorSecondsErrorRatio				DisplayString,
				ommp81PlusOtuFarEndErrorFreeSeconds					DisplayString,
				ommp81PlusOtuFarEndErrorSeconds						DisplayString,
				ommp81PlusOtuFarEndBackgroundBlockErrors				DisplayString,
				ommp81PlusOtuFarEndSevereErrorSeconds					DisplayString,
				ommp81PlusOtuFarEndUnavailableSeconds					DisplayString,
				ommp81PlusOtuFarEndBackgroundBlockErrorRatio				DisplayString,
				ommp81PlusOtuFarEndSevereErrorSecondsErrorRatio				DisplayString,
				ommp81PlusOtuErrorRatio							DisplayString,
				ommp81PlusOtuBitErrorRate						DisplayString,
				ommp81PlusOtuFramesReceived						DisplayString,
				ommp81PlusOduBitInterleavedParityErrors					DisplayString,
				ommp81PlusOduTcm1BitInterleavedParityErrors				DisplayString,
				ommp81PlusOduTcm2BitInterleavedParityErrors				DisplayString,
				ommp81PlusOduTcm3BitInterleavedParityErrors				DisplayString,
				ommp81PlusOduTcm4BitInterleavedParityErrors				DisplayString,
				ommp81PlusOduTcm5BitInterleavedParityErrors				DisplayString,
				ommp81PlusOduTcm6BitInterleavedParityErrors				DisplayString,
				ommp81PlusOduTcm1IncomingAlignmentErrorSeconds				DisplayString,
				ommp81PlusOduBackwardErrorIndicationErrorCount				DisplayString,
				ommp81PlusOduTcm1BackwardErrorIndicationErrorCount			DisplayString,
				ommp81PlusOduTcm2BackwardErrorIndicationErrorCount			DisplayString,
				ommp81PlusOduTcm3BackwardErrorIndicationErrorCount			DisplayString,
				ommp81PlusOduTcm4BackwardErrorIndicationErrorCount			DisplayString,
				ommp81PlusOduTcm5BackwardErrorIndicationErrorCount			DisplayString,
				ommp81PlusOduTcm6BackwardErrorIndicationErrorCount			DisplayString,
				ommp81PlusOduTcm1BackwardIncomingAlignmentErrorSeconds			DisplayString,
				ommp81PlusOduDelayMeasurement						DisplayString,
				ommp81PlusOduErrorFreeSeconds						DisplayString,
				ommp81PlusOduErrorSeconds						DisplayString,
				ommp81PlusOduBackgroundBlockErrors					DisplayString,
				ommp81PlusOduSevereErrorSeconds						DisplayString,
				ommp81PlusOduUnavailableSeconds						DisplayString,
				ommp81PlusOduBackgroundBlockErrorRatio					DisplayString,
				ommp81PlusOduSevereErrorSecondsErrorRatio				DisplayString,
				ommp81PlusOduFarEndErrorFreeSeconds					DisplayString,
				ommp81PlusOduFarEndErrorSeconds						DisplayString,
				ommp81PlusOduFarEndBackgroundBlockErrors				DisplayString,
				ommp81PlusOduFarEndSevereErrorSeconds					DisplayString,
				ommp81PlusOduFarEndUnavailableSeconds					DisplayString,
				ommp81PlusOduFarEndBackgroundBlockErrorRatio				DisplayString,
				ommp81PlusOduFarEndSevereErrorSecondsErrorRatio				DisplayString,
				ommp81PlusSdhRsB1BitInterleavedParityErrors				DisplayString,
				ommp81PlusSdhMsB2BitInterleavedParityErrors				DisplayString,
				ommp81PlusSdhMsB3BitInterleavedParityErrors				DisplayString,
				ommp81PlusSdhMsRemoteErrorIndicationErrorCount				DisplayString,
				ommp81PlusSdhMsRemoteDefectIndicationErrorCount				DisplayString,
				ommp81PlusSdhErrorFreeSeconds						DisplayString,
				ommp81PlusSdhErrorSeconds						DisplayString,
				ommp81PlusSdhBackgroundBlockErrors					DisplayString,
				ommp81PlusSdhSevereErrorSeconds						DisplayString,
				ommp81PlusSdhUnavailableSeconds						DisplayString,
				ommp81PlusSdhErrorSecondsErrorRatio					DisplayString,
				ommp81PlusSdhBackgroundBlockErrorRatio					DisplayString,
				ommp81PlusSdhSevereErrorSecondsErrorRatio				DisplayString,
				ommp81PlusEthernetMacTerminatedFramesTransmitted			DisplayString,
				ommp81PlusEthernetMacTerminatedFramesReceived				DisplayString,
				ommp81PlusEthernetMacTerminatedPauseFramesTransmitted			DisplayString,
				ommp81PlusEthernetMacTerminatedPauseFramesReceived			DisplayString,
				ommp81PlusEthernetMacTerminatedUnicastFramesTransmitted			DisplayString,
				ommp81PlusEthernetMacTerminatedUnicastFramesReceived			DisplayString,
				ommp81PlusEthernetMacTerminatedMulticastFramesTransmitted		DisplayString,
				ommp81PlusEthernetMacTerminatedMulticastFramesReceived			DisplayString,
				ommp81PlusEthernetMacTerminatedBroadcastFramesTransmitted		DisplayString,
				ommp81PlusEthernetMacTerminatedBroadcastFramesReceived			DisplayString,
				ommp81PlusEthernetMacTerminatedUnderSizeFramesTransmitted		DisplayString,
				ommp81PlusEthernetMacTerminatedUnderSizeFramesReceived			DisplayString,
				ommp81PlusEthernetMacTerminatedOverSizeFramesTransmitted		DisplayString,
				ommp81PlusEthernetMacTerminatedOverSizeFramesReceived			DisplayString,
				ommp81PlusEthernetMacTerminatedVlanTaggedFramesTransmitted		DisplayString,
				ommp81PlusEthernetMacTerminatedVlanTaggedFramesReceived			DisplayString,
				ommp81PlusEthernetMacTerminatedFrameSymbolErrorsReceived		DisplayString,
				ommp81PlusEthernetMacTerminatedFragmentFramesReceived			DisplayString,
				ommp81PlusEthernetMacTerminatedFrameCheckSequenceErrorsReceived		DisplayString,
				ommp81PlusEthernetMacTerminatedFramesReceivedWithNoDefect		DisplayString,
				ommp81PlusEthernetMacTerminatedBytesTransmitted				DisplayString,
				ommp81PlusEthernetMacTerminatedBytesReceived				DisplayString,	
				ommp81PlusEthernetMacTerminatedControlFramesTransmitted			DisplayString,
				ommp81PlusEthernetMacTerminatedControlFramesReceived			DisplayString,
				ommp81PlusEthernetTransparentTransmitLcvCount				DisplayString,	
				ommp81PlusEthernetTransparentTransmitPropagationErrorDeletionCount	DisplayString,
				ommp81PlusEthernetTransparentTransmitIdleDeletionCount			DisplayString,
				ommp81PlusEthernetTransparentTransmitConfDeletionCount			DisplayString,
				ommp81PlusEthernetTransparentTransmitPropagationInsertionCount		DisplayString,
				ommp81PlusEthernetTransparentTransmitIdleInsertionCount			DisplayString,
				ommp81PlusEthernetTransparentTransmitConfInsertionCount			DisplayString,
				ommp81PlusEthernetTransparentReceiveLcvCount				DisplayString,
				ommp81PlusEthernetTransparentReceivePropagationErrorDeletionCount	DisplayString,
				ommp81PlusEthernetTransparentReceiveIdleDeletionCount			DisplayString,
				ommp81PlusEthernetTransparentReceiveConfDeletionCount			DisplayString,
				ommp81PlusEthernetTransparentReceivePacketDeletionCount			DisplayString,
				ommp81PlusGfpCoreHeaderErrorCount					DisplayString,
				ommp81PlusGfpExtentionHeaderErrorCount					DisplayString,
				ommp81PlusGfpFrameCountWithSingleBitError				DisplayString,
				ommp81PlusGfpTypeHeaderErrorCount					DisplayString,
				ommp81PlusGfpReceiveDropFrameCount					DisplayString,
				ommp81PlusGfpReceiveExtensionHeaderIdentifierFilterDropCount		DisplayString,
				ommp81PlusFcTransmitWordCount						DisplayString,
				ommp81PlusFcReceiveWordCount						DisplayString,
				ommp81PlusFcTransmitTotalPackets					DisplayString,
				ommp81PlusFcReceiveTotalPackets						DisplayString,
				ommp81PlusFcTransmitBadCrc						DisplayString,
				ommp81PlusFcReceiveBadCrc						DisplayString,
				ommp81PlusFcTransmitLcvCount						DisplayString,
				ommp81PlusFcReceiveLcvCount						DisplayString,
				ommp81PlusFcTransmitFillWordInsertionCount				DisplayString,
				ommp81PlusFcTransmitPrimitiveSequenceInsertionCount			DisplayString,
				ommp81PlusFcTransmitFillWordDeletionCount				DisplayString,
				ommp81PlusFcTransmitPrimitiveSequenceDeletionCount			DisplayString,
				ommp81PlusPerformanceTableRowStatus					RowStatus
			}	           

	ommp81PlusXfpInputPower OBJECT-TYPE
		SYNTAX  DisplayString
		MAX-ACCESS  read-only
		STATUS  current
		DESCRIPTION
			"Gives the current Input power(dbm) received at the port
			-----------------------------
			ommp81PlusInterfaceNumber:
			9 - LINE-1
			-----------------------------
			Values:
			eg: -9.0
			-----------------------------"
	::= { ommp81PlusPerformanceEntry 1 }

	ommp81PlusXfpOutputPower OBJECT-TYPE
		SYNTAX  DisplayString
		MAX-ACCESS  read-only
		STATUS  current
		DESCRIPTION
			"Gives the current Output power(dbm) transmitted at the port
			-----------------------------
			ommp81PlusInterfaceNumber:
			9 - LINE-1
			-----------------------------
			Values:
			eg: -0.6
			-----------------------------"
	::= { ommp81PlusPerformanceEntry 2 }

	ommp81PlusXfpBiasCurrent OBJECT-TYPE
		SYNTAX  DisplayString
		MAX-ACCESS  read-only
		STATUS  current
		DESCRIPTION
			"Gives the bias current(mA) thats transmitted at the port
			-----------------------------
			ommp81PlusInterfaceNumber:
			9 - LINE-1
			-----------------------------
			Values:
			eg: 55
			-----------------------------"
	::= { ommp81PlusPerformanceEntry 3 }

	ommp81PlusXfpSupplyVoltage OBJECT-TYPE
		SYNTAX  DisplayString
		MAX-ACCESS  read-only
		STATUS  current
		DESCRIPTION
			"Gives the Supply Voltage of the port
			-----------------------------
			ommp81PlusInterfaceNumber:
			9 - LINE-1
			-----------------------------
			Values:
			eg: 3.3
			-----------------------------"
	::= { ommp81PlusPerformanceEntry 4 }

	ommp81PlusXfpTemperature OBJECT-TYPE
		SYNTAX  DisplayString
		MAX-ACCESS  read-only
		STATUS  current
		DESCRIPTION
			"Gives the temperature(degree celcius) of the transmitter
			at  the port
			-----------------------------
			ommp81PlusInterfaceNumber:
			9 - LINE-1
			-----------------------------
			Values:
			eg: 33.35
			-----------------------------"
	::= { ommp81PlusPerformanceEntry 5 }

	ommp81PlusSfpInputPower OBJECT-TYPE
		SYNTAX  DisplayString
		MAX-ACCESS  read-only
		STATUS  current
		DESCRIPTION
			"Gives the current Input power(dbm) received at the port
			-----------------------------
			ommp81PlusInterfaceNumber:
			1 to 8 - CLIENT-1 to CLIENT-8
			-----------------------------
			Values:
			eg: -9.0
			-----------------------------"
	::= { ommp81PlusPerformanceEntry 21 }

	ommp81PlusSfpOutputPower OBJECT-TYPE
		SYNTAX  DisplayString
		MAX-ACCESS  read-only
		STATUS  current
		DESCRIPTION
			"Gives the current Output power(dbm) transmitted at the port
			-----------------------------
			ommp81PlusInterfaceNumber:
			1 to 8 - CLIENT-1 to CLIENT-8
			-----------------------------
			Values:
			eg: -6.0
			-----------------------------"
	::= { ommp81PlusPerformanceEntry 22 }

	ommp81PlusSfpBiasCurrent OBJECT-TYPE
		SYNTAX  DisplayString
		MAX-ACCESS  read-only
		STATUS  current
		DESCRIPTION
			"Gives the bias current(mA) thats transmitted at the port
			-----------------------------
			ommp81PlusInterfaceNumber:
			1 to 8 - CLIENT-1 to CLIENT-8
			-----------------------------
			Values:
			eg: 55
			-----------------------------"
	::= { ommp81PlusPerformanceEntry 23 }

	ommp81PlusSfpSupplyVoltage OBJECT-TYPE
		SYNTAX  DisplayString
		MAX-ACCESS  read-only
		STATUS  current
		DESCRIPTION
			"Gives the Supply Voltage of the port
			-----------------------------
			ommp81PlusInterfaceNumber:
			1 to 8 - CLIENT-1 to CLIENT-8
			-----------------------------
			Values:
			eg: 3.3
			-----------------------------"
	::= { ommp81PlusPerformanceEntry 24 }

	ommp81PlusSfpTemperature OBJECT-TYPE
		SYNTAX  DisplayString
		MAX-ACCESS  read-only
		STATUS  current
		DESCRIPTION
			"Gives the temperature(degree celcius) of the transmitter
			at the port
			-----------------------------
			ommp81PlusInterfaceNumber:
			1 to 8 - CLIENT-1 to CLIENT-8
			-----------------------------
			Values:
			eg: 33.35
			-----------------------------"
	::= { ommp81PlusPerformanceEntry 25 }

	ommp81PlusOtnFecUncorrectedWords OBJECT-TYPE
		SYNTAX  DisplayString
		MAX-ACCESS  read-only
		STATUS  current
		DESCRIPTION
			"For port configured with OTU2/OTU1 traffic,
			OTU Uncorrected Word Error Counter counts the number of
			FEC errored code words that could not be corrected.
			-----------------------------
			ommp81PlusInterfaceNumber:
			1 to 8 - CLIENT-1 to CLIENT-8
			9 - LINE-1
			-----------------------------
			Values:
			eg: 1234
			-----------------------------"
	::= { ommp81PlusPerformanceEntry 41 }

	ommp81PlusOtnFecCorrectedBits OBJECT-TYPE
		SYNTAX  DisplayString
		MAX-ACCESS  read-only
		STATUS  current
		DESCRIPTION
			"For port configured with OTU2/OTU1 traffic,
			OTU Corrected Bit Error Counter counts the number of
			FEC error bits that could be corrected(sum of ones
			corrected and zeros corrected bits).
			-----------------------------
			ommp81PlusInterfaceNumber:
			1 to 8 - CLIENT-1 to CLIENT-8
			9 - LINE-1
			-----------------------------
			Values:
			eg: 1234
			-----------------------------"
	::= { ommp81PlusPerformanceEntry 42 }

	ommp81PlusOtnFecZerosCorrectedBits OBJECT-TYPE
		SYNTAX  DisplayString
		MAX-ACCESS  read-only
		STATUS  current
		DESCRIPTION
			"For port configured with OTU2/OTU1 traffic,
			OTU Zero Corrected Bits Error Counter counts the number
			of FEC error bits that could be corrected from
			one to zero value(Expected 0 but received as 1).
			-----------------------------
			ommp81PlusInterfaceNumber:
			1 to 8 - CLIENT-1 to CLIENT-8
			9 - LINE-1
			-----------------------------
			Values:
			eg: 1234
			-----------------------------"
	::= { ommp81PlusPerformanceEntry 43 }

	ommp81PlusOtnFecOnesCorrectedBits OBJECT-TYPE
		SYNTAX  DisplayString
		MAX-ACCESS  read-only
		STATUS  current
		DESCRIPTION
			"For port configured with OTU2/OTU1 traffic,
			OTU Ones Corrected Byte Error Counter counts the number
			of FEC error bytes that could be corrected from
			zero to one value(Expected 1 but received as 0).
			-----------------------------
			ommp81PlusInterfaceNumber:
			1 to 8 - CLIENT-1 to CLIENT-8
			9 - LINE-1
			-----------------------------
			Values:
			eg: 1234
			-----------------------------"
	::= { ommp81PlusPerformanceEntry 44 }

	ommp81PlusOtuBitInterleavedParityErrors OBJECT-TYPE
		SYNTAX  DisplayString
		MAX-ACCESS  read-only
		STATUS  current
		DESCRIPTION
			"For port configured with OTU2/OTU1 traffic,
			OTU-BIP Counter counts the Parity errors evaluated by
			SM field of an OTU2 frame.
			-----------------------------
			ommp81PlusInterfaceNumber:
			1 to 8 - CLIENT-1 to CLIENT-8
			9 - LINE-1
			-----------------------------
			Values:
			eg: 1234
			-----------------------------"
	::= { ommp81PlusPerformanceEntry 45 }

	ommp81PlusOtuIncomingAlignmentErrorSeconds OBJECT-TYPE
		SYNTAX  DisplayString
		MAX-ACCESS  read-only
		STATUS  current
		DESCRIPTION
			"For port configured with OTU2/OTU1 traffic,
			OTU Incoming Alignment Error Second increases,
			when OTU IAE Alarm is detected in that particular second
			of the incoming OTU signal
			-----------------------------
			ommp81PlusInterfaceNumber:
			1 to 8 - CLIENT-1 to CLIENT-8
			9 - LINE-1
			-----------------------------
			Values:
			eg: 1234
			-----------------------------"
	::= { ommp81PlusPerformanceEntry 46 }

	ommp81PlusOtuBackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code.
			-----------------------------
			ommp81PlusInterfaceNumber:
			1 to 8 - CLIENT-1 to CLIENT-8
			9 - LINE-1
			-----------------------------
			Values:
			eg: 1234
			-----------------------------"
	::= { ommp81PlusPerformanceEntry 47 }

	ommp81PlusOtuBackwardIncomingAlignmentErrorSeconds OBJECT-TYPE
		SYNTAX  DisplayString
		MAX-ACCESS  read-only
		STATUS  current
		DESCRIPTION
			"For port configured with OTU2/OTU1 traffic,
			OTU-BIAE Counter increases when SM-BIAE Alarm is 
			detected in that particular second
			of the incoming OTU signal
			-----------------------------
			ommp81PlusInterfaceNumber:
			1 to 8 - CLIENT-1 to CLIENT-8
			9 - LINE-1
			-----------------------------
			Values:
			eg: 1234
			-----------------------------"
	::= { ommp81PlusPerformanceEntry 48 }

	ommp81PlusOtuErrorFreeSeconds OBJECT-TYPE
		SYNTAX  DisplayString
		MAX-ACCESS  read-only
		STATUS  current
		DESCRIPTION
			"For port configured with OTU2/OTU1 traffic,
			OTU Error Free Seconds increases when no BIP errors
			or defects are detected
			-----------------------------
			ommp81PlusInterfaceNumber:
			1 to 8 - CLIENT-1 to CLIENT-8
			9 - LINE-1
			-----------------------------
			Values:
			eg: 1234
			-----------------------------"
	::= { ommp81PlusPerformanceEntry 49 }

	ommp81PlusOtuErrorSeconds OBJECT-TYPE
		SYNTAX  DisplayString
		MAX-ACCESS  read-only
		STATUS  current
		DESCRIPTION
			"For port configured with OTU2/OTU1 traffic,
			OTU Error Seconds increases when any defects like 
			OTU-AIS, SM-TIM etc are detected at the
			section monitoring level
			-----------------------------
			ommp81PlusInterfaceNumber:
			1 to 8 - CLIENT-1 to CLIENT-8
			9 - LINE-1
			-----------------------------
			Values:
			eg: 1234
			-----------------------------"
	::= { ommp81PlusPerformanceEntry 50 }

	ommp81PlusOtuBackgroundBlockErrors OBJECT-TYPE
		SYNTAX  DisplayString
		MAX-ACCESS  read-only
		STATUS  current
		DESCRIPTION
			"For port configured with OTU2/OTU1 traffic,
			OTU Background Block Errors increases on defects 
			detected and when BIP errors are less than 15% errored
			blocks received 
			-----------------------------
			ommp81PlusInterfaceNumber:
			1 to 8 - CLIENT-1 to CLIENT-8
			9 - LINE-1
			-----------------------------
			Values:
			eg: 1234
			-----------------------------"
	::= { ommp81PlusPerformanceEntry 51 }

	ommp81PlusOtuSevereErrorSeconds OBJECT-TYPE
		SYNTAX  DisplayString
		MAX-ACCESS  read-only
		STATUS  current
		DESCRIPTION
			"For port configured with OTU2/OTU1 traffic,
			OTU Severe Error Seconds increases on defects
			detected and when BIP errors are greater than or
			equal to 15% errored blocks received 
			-----------------------------
			ommp81PlusInterfaceNumber:
			1 to 8 - CLIENT-1 to CLIENT-8
			9 - LINE-1
			-----------------------------
			Values:
			eg: 1234
			-----------------------------"
	::= { ommp81PlusPerformanceEntry 52 }

	ommp81PlusOtuUnavailableSeconds OBJECT-TYPE
		SYNTAX  DisplayString
		MAX-ACCESS  read-only
		STATUS  current
		DESCRIPTION
			"For port configured with OTU2/OTU1 traffic,
			OTU Unavailable Seconds increases,
			when 10 consecutive OTU Severe Error seconds
			are detected
			-----------------------------
			ommp81PlusInterfaceNumber:
			1 to 8 - CLIENT-1 to CLIENT-8
			9 - LINE-1
			-----------------------------
			Values:
			eg: 1234
			-----------------------------"
	::= { ommp81PlusPerformanceEntry 53 }

	ommp81PlusOtuBackgroundBlockErrorRatio OBJECT-TYPE
		SYNTAX  DisplayString
		MAX-ACCESS  read-only
		STATUS  current
		DESCRIPTION
			"For port configured with OTU2/OTU1 traffic,
			gives OTU Background Block Error Seconds Error Ratio.
			The ratio of BBE in available time to total seconds
			in available time during a fixed measurement interval.
			-----------------------------
			ommp81PlusInterfaceNumber:
			1 to 8 - CLIENT-1 to CLIENT-8
			9 - LINE-1
			-----------------------------
			Values:
			eg: 1e-3
			-----------------------------"
	::= { ommp81PlusPerformanceEntry 55 }

	ommp81PlusOtuSevereErrorSecondsErrorRatio OBJECT-TYPE
		SYNTAX  DisplayString
		MAX-ACCESS  read-only
		STATUS  current
		DESCRIPTION
			"For port configured with OTU2/OTU1 traffic,
			gives OTU Severe Error Seconds Error Ratio.
			The ratio of SES in available time to total seconds
			in available time during a fixed measurement interval.
			-----------------------------
			ommp81PlusInterfaceNumber:
			1 to 8 - CLIENT-1 to CLIENT-8
			9 - LINE-1
			-----------------------------
			Values:
			eg: 1e-3
			-----------------------------"
	::= { ommp81PlusPerformanceEntry 56 }

	ommp81PlusOtuFarEndErrorFreeSeconds OBJECT-TYPE
		SYNTAX  DisplayString
		MAX-ACCESS  read-only
		STATUS  current
		DESCRIPTION
			"For port configured with OTU2/OTU1 traffic,
			OTU Far end Error Free Seconds, increases when no
			backward errors or defects like BDI or BEI
			are detected in the incoming OTU signal.
			-----------------------------
			ommp81PlusInterfaceNumber:
			1 to 8 - CLIENT-1 to CLIENT-8
			9 - LINE-1
			-----------------------------
			Values:
			eg: 1234
			-----------------------------"
	::= { ommp81PlusPerformanceEntry 57 }

	ommp81PlusOtuFarEndErrorSeconds OBJECT-TYPE
		SYNTAX  DisplayString
		MAX-ACCESS  read-only
		STATUS  current
		DESCRIPTION
			"For port configured with OTU2/OTU1 traffic,
			OTU Far End Error Seconds increases on
			detection of defects like BDI in incoming
			OTU signal.
			-----------------------------
			ommp81PlusInterfaceNumber:
			1 to 8 - CLIENT-1 to CLIENT-8
			9 - LINE-1
			-----------------------------
			Values:
			eg: 1234
			-----------------------------"
	::= { ommp81PlusPerformanceEntry 58 }

	ommp81PlusOtuFarEndBackgroundBlockErrors OBJECT-TYPE
		SYNTAX  DisplayString
		MAX-ACCESS  read-only
		STATUS  current
		DESCRIPTION
			"For port configured with OTU2/OTU1 traffic,
			OTU Far End Background Block Errors increases when BEI
			errors are less than 15% Errored Blocks in incoming
			OTU signal.
			-----------------------------
			ommp81PlusInterfaceNumber:
			1 to 8 - CLIENT-1 to CLIENT-8
			9 - LINE-1
			-----------------------------
			Values:
			eg: 1234
			-----------------------------"
	::= { ommp81PlusPerformanceEntry 59 }

	ommp81PlusOtuFarEndSevereErrorSeconds OBJECT-TYPE
		SYNTAX  DisplayString
		MAX-ACCESS  read-only
		STATUS  current
		DESCRIPTION
			"For port configured with OTU2/OTU1 traffic,
			OTU Far End Severe Error Seconds increases on defects
			like BDI are detected and when BEI errors are greater
			than or equal to 15% Errored Blocks in incoming OTU 
			signal.
			-----------------------------
			ommp81PlusInterfaceNumber:
			1 to 8 - CLIENT-1 to CLIENT-8
			9 - LINE-1
			-----------------------------
			Values:
			eg: 1234
			-----------------------------"
	::= { ommp81PlusPerformanceEntry 60 }

	ommp81PlusOtuFarEndUnavailableSeconds OBJECT-TYPE
		SYNTAX  DisplayString
		MAX-ACCESS  read-only
		STATUS  current
		DESCRIPTION
			"For port configured with OTU2/OTU1 traffic,
			OTU Far End Unavailable Seconds increases, 
			after 9 consecutive OTU Far End Severe Error
			seconds are detected
			-----------------------------
			ommp81PlusInterfaceNumber:
			1 to 8 - CLIENT-1 to CLIENT-8
			9 - LINE-1
			-----------------------------
			Values:
			eg: 1234
			-----------------------------"
	::= { ommp81PlusPerformanceEntry 61 }

	ommp81PlusOtuFarEndBackgroundBlockErrorRatio OBJECT-TYPE
		SYNTAX  DisplayString
		MAX-ACCESS  read-only
		STATUS  current
		DESCRIPTION
			"For port configured with OTU2/OTU1 traffic,
			gives Otu Far End Background Block Error Ratio.
			The ratio of Far End BBE in available time to tota
			seconds in available time during a fixed measurement
			interval.
			-----------------------------
			ommp81PlusInterfaceNumber:
			1 to 8 - CLIENT-1 to CLIENT-8
			9 - LINE-1
			-----------------------------
			Values:
			eg: 1e-3
			-----------------------------"
	::= { ommp81PlusPerformanceEntry 63 }

	ommp81PlusOtuFarEndSevereErrorSecondsErrorRatio OBJECT-TYPE
		SYNTAX  DisplayString
		MAX-ACCESS  read-only
		STATUS  current
		DESCRIPTION
			"For port configured with OTU2/OTU1 traffic,
			gives Otu Far End Severe Error Seconds Error Ratio.
			The ratio of Far End SES in available time to total seconds
			in available time during a fixed measurement interval.
			-----------------------------
			ommp81PlusInterfaceNumber:
			1 to 8 - CLIENT-1 to CLIENT-8
			9 - LINE-1
			-----------------------------
			Values:
			eg: 1e-3
			-----------------------------"
	::= { ommp81PlusPerformanceEntry 64 }

	ommp81PlusOtuErrorRatio   OBJECT-TYPE
              SYNTAX  DisplayString
              MAX-ACCESS  read-only
              STATUS  current
              DESCRIPTION
			"For port configured with OTU2/OTU1 traffic,
			gives the OTU Error Ratio for requested port. The ratio  
			of number of error bits to the number of bits received in
			a particular second
			-----------------------------
			ommp81PlusInterfaceNumber:
			1 to 8 - CLIENT-1 to CLIENT-8
			9 - LINE-1
			-----------------------------	
			Value:
			eg: 4.0
			-----------------------------"
	::= { ommp81PlusPerformanceEntry 65 } 

	ommp81PlusOtuBitErrorRate  OBJECT-TYPE
              SYNTAX  DisplayString
              MAX-ACCESS  read-only
              STATUS  current
              DESCRIPTION
			"For port configured with OTU2/OTU1 traffic, gives the 
			Bit Error Rate. Bit error rate is the Error ratio 
			multiplied by the OTU2 standard signal 
			data-rate( 10.709225316 Gbps )
			-----------------------------
			ommp81PlusInterfaceNumber:
			1 to 8 - CLIENT-1 to CLIENT-8
			9 - LINE-1
			-----------------------------	
			Value:
			eg: 4.0
			-----------------------------"
	::= { ommp81PlusPerformanceEntry 66 }

	ommp81PlusOtuFramesReceived  OBJECT-TYPE
              SYNTAX  DisplayString
              MAX-ACCESS  read-only
              STATUS  current
              DESCRIPTION
			"For port configured with OTU2/OTU1 traffic, gives the 
			gives the number of OTU frames transmitted.
			-----------------------------
			ommp81PlusInterfaceNumber:
			1 to 8 - CLIENT-1 to CLIENT-8
			9 - LINE-1
			-----------------------------	
			Value:
			eg: 4.0
			-----------------------------"
	::= { ommp81PlusPerformanceEntry 67 }

	ommp81PlusOduBitInterleavedParityErrors OBJECT-TYPE
		SYNTAX  DisplayString
		MAX-ACCESS  read-only
		STATUS  current
		DESCRIPTION
			"For port configured with OTU2/OTU1 traffic,
			ODU-BIP Counter counts the Parity errors evaluated by
			PM field of an OTU2 frame
			-----------------------------
			ommp81PlusInterfaceNumber:
			1 to 8 - CLIENT-1 to CLIENT-8
			9 - LINE-1
			-----------------------------
			Values:
			eg: 1234
			-----------------------------"
	::= { ommp81PlusPerformanceEntry 81 }

	ommp81PlusOduTcm1BitInterleavedParityErrors OBJECT-TYPE
		SYNTAX  DisplayString
		MAX-ACCESS  read-only
		STATUS  current
		DESCRIPTION
			"For port configured with OTU2/OTU1 traffic,
			TCM1-BIP Counter counts the Parity errors evaluated by
			TCM1 field in ODU frame
			-----------------------------
			ommp81PlusInterfaceNumber:
			1 to 8 - CLIENT-1 to CLIENT-8
			9 - LINE-1
			-----------------------------
			Values:
			eg: 1234
			-----------------------------"
	::= { ommp81PlusPerformanceEntry 82 }

	ommp81PlusOduTcm2BitInterleavedParityErrors OBJECT-TYPE
		SYNTAX  DisplayString
		MAX-ACCESS  read-only
		STATUS  current
		DESCRIPTION
			"For port configured with OTU2/OTU1 traffic,
			TCM2-BIP Counter counts the Parity errors evaluated by
			TCM2 field in ODU frame
			-----------------------------
			ommp81PlusInterfaceNumber:
			1 to 8 - CLIENT-1 to CLIENT-8
			9 - LINE-1
			-----------------------------
			Values:
			eg: 1234
			-----------------------------"
	::= { ommp81PlusPerformanceEntry 83 }

	ommp81PlusOduTcm3BitInterleavedParityErrors OBJECT-TYPE
		SYNTAX  DisplayString
		MAX-ACCESS  read-only
		STATUS  current
		DESCRIPTION
			"For port configured with OTU2/OTU1 traffic,
			TCM3-BIP Counter counts the Parity errors evaluated by
			TCM3 field in ODU frame
			-----------------------------
			ommp81PlusInterfaceNumber:
			1 to 8 - CLIENT-1 to CLIENT-8
			9 - LINE-1
			-----------------------------
			Values:
			eg: 1234
			-----------------------------"
	::= { ommp81PlusPerformanceEntry 84 }

	ommp81PlusOduTcm4BitInterleavedParityErrors OBJECT-TYPE
		SYNTAX  DisplayString
		MAX-ACCESS  read-only
		STATUS  current
		DESCRIPTION
			"For port configured with OTU2/OTU1 traffic,
			TCM4-BIP Counter counts the Parity errors evaluated by
			TCM4 field in ODU frame
			-----------------------------
			ommp81PlusInterfaceNumber:
			1 to 8 - CLIENT-1 to CLIENT-8
			9 - LINE-1
			-----------------------------
			Values:
			eg: 1234
			-----------------------------"
	::= { ommp81PlusPerformanceEntry 85 }

	ommp81PlusOduTcm5BitInterleavedParityErrors OBJECT-TYPE
		SYNTAX  DisplayString
		MAX-ACCESS  read-only
		STATUS  current
		DESCRIPTION
			"For port configured with OTU2/OTU1 traffic,
			TCM5-BIP Counter counts the Parity errors evaluated by
			TCM5 field in ODU frame
			-----------------------------
			ommp81PlusInterfaceNumber:
			1 to 8 - CLIENT-1 to CLIENT-8
			9 - LINE-1
			-----------------------------
			Values:
			eg: 1234
			-----------------------------"
	::= { ommp81PlusPerformanceEntry 86 }

	ommp81PlusOduTcm6BitInterleavedParityErrors OBJECT-TYPE
		SYNTAX  DisplayString
		MAX-ACCESS  read-only
		STATUS  current
		DESCRIPTION
			"For port configured with OTU2/OTU1 traffic,
			TCM6-BIP Counter counts the Parity errors evaluated by
			TCM6 field in ODU frame
			-----------------------------
			ommp81PlusInterfaceNumber:
			1 to 8 - CLIENT-1 to CLIENT-8
			9 - LINE-1
			-----------------------------
			Values:
			eg: 1234
			-----------------------------"
	::= { ommp81PlusPerformanceEntry 87 }

	ommp81PlusOduTcm1IncomingAlignmentErrorSeconds OBJECT-TYPE
		SYNTAX  DisplayString
		MAX-ACCESS  read-only
		STATUS  current
		DESCRIPTION
			"For port configured with OTU2/OTU1 traffic,
			ODU Incoming Alignment Error Count increases,
			when ODU-TCM1-IAE is detected in that particular second
			of the incoming OTU signal
			-----------------------------
			ommp81PlusInterfaceNumber:
			1 to 8 - CLIENT-1 to CLIENT-8
			9 - LINE-1
			-----------------------------
			Values:
			eg: 1234
			-----------------------------"
	::= { ommp81PlusPerformanceEntry 88 }

	ommp81PlusOduBackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code.
			-----------------------------
			ommp81PlusInterfaceNumber:
			1 to 8 - CLIENT-1 to CLIENT-8
			9 - LINE-1
			-----------------------------
			Values:
			eg: 1234
			-----------------------------"
	::= { ommp81PlusPerformanceEntry 89 }

	ommp81PlusOduTcm1BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM1 level.
			-----------------------------
			ommp81PlusInterfaceNumber:
			1 to 8 - CLIENT-1 to CLIENT-8
			9 - LINE-1
			-----------------------------
			Values:
			eg: 1234
			-----------------------------"
	::= { ommp81PlusPerformanceEntry 90 }

	ommp81PlusOduTcm2BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM2 level.
			-----------------------------
			ommp81PlusInterfaceNumber:
			1 to 8 - CLIENT-1 to CLIENT-8
			9 - LINE-1
			-----------------------------
			Values:
			eg: 1234
			-----------------------------"
	::= { ommp81PlusPerformanceEntry 91 }

	ommp81PlusOduTcm3BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM3 level.
			-----------------------------
			ommp81PlusInterfaceNumber:
			1 to 8 - CLIENT-1 to CLIENT-8
			9 - LINE-1
			-----------------------------
			Values:
			eg: 1234
			-----------------------------"
	::= { ommp81PlusPerformanceEntry 92 }

	ommp81PlusOduTcm4BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM4 level.
			-----------------------------
			ommp81PlusInterfaceNumber:
			1 to 8 - CLIENT-1 to CLIENT-8
			9 - LINE-1
			-----------------------------
			Values:
			eg: 1234
			-----------------------------"
	::= { ommp81PlusPerformanceEntry 93 }

	ommp81PlusOduTcm5BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM5 level.
			-----------------------------
			ommp81PlusInterfaceNumber:
			1 to 8 - CLIENT-1 to CLIENT-8
			9 - LINE-1
			-----------------------------
			Values:
			eg: 1234
			-----------------------------"
	::= { ommp81PlusPerformanceEntry 94 }

	ommp81PlusOduTcm6BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM6 level.
			-----------------------------
			ommp81PlusInterfaceNumber:
			1 to 8 - CLIENT-1 to CLIENT-8
			9 - LINE-1
			-----------------------------
			Values:
			eg: 1234
			-----------------------------"
	::= { ommp81PlusPerformanceEntry 95 }

	ommp81PlusOduTcm1BackwardIncomingAlignmentErrorSeconds OBJECT-TYPE
		SYNTAX  DisplayString
		MAX-ACCESS  read-only
		STATUS  current
		DESCRIPTION
			"For port configured with OTU2/OTU1 traffic,
			ODU Backward Incoming Alignment Error Count increases,
			when ODU-TCM1-BIAE is detected in that particular second
			of the incoming OTU signal
			-----------------------------
			ommp81PlusInterfaceNumber:
			1 to 8 - CLIENT-1 to CLIENT-8
			9 - LINE-1
			-----------------------------
			Values:
			eg: 1234
			-----------------------------"
	::= { ommp81PlusPerformanceEntry 96 }

	ommp81PlusOduDelayMeasurement OBJECT-TYPE
		SYNTAX  DisplayString
		MAX-ACCESS  read-only
		STATUS  current
		DESCRIPTION
			"For port configured with OTU2/OTU1 traffic,
			gives delay measurement of ODU frame
			-----------------------------
			ommp81PlusInterfaceNumber:
			1 to 8 - CLIENT-1 to CLIENT-8
			9 - LINE-1
			-----------------------------
			Values:
			eg: Reserved for further study
			-----------------------------"
	::= { ommp81PlusPerformanceEntry 97 }

	ommp81PlusOduErrorFreeSeconds OBJECT-TYPE
		SYNTAX  DisplayString
		MAX-ACCESS  read-only
		STATUS  current
		DESCRIPTION
			"For port configured with OTU2/OTU1 traffic,
			ODU Error Free Seconds increases,
			when no BIP errors or defects are detected at the
			path monitoring level
			-----------------------------
			ommp81PlusInterfaceNumber:
			1 to 8 - CLIENT-1 to CLIENT-8
			9 - LINE-1
			-----------------------------
			Values:
			eg: 1234
			-----------------------------"
	::= { ommp81PlusPerformanceEntry 98 }

	ommp81PlusOduErrorSeconds OBJECT-TYPE
		SYNTAX  DisplayString
		MAX-ACCESS  read-only
		STATUS  current
		DESCRIPTION
			"For port configured with OTU2/OTU1 traffic,
			ODU Error Seconds increases on defects detected at the
			path monitoring level
			-----------------------------
			ommp81PlusInterfaceNumber:
			1 to 8 - CLIENT-1 to CLIENT-8
			9 - LINE-1
			-----------------------------
			Values:
			eg: 1234
			-----------------------------"
	::= { ommp81PlusPerformanceEntry 99 }

	ommp81PlusOduBackgroundBlockErrors OBJECT-TYPE
		SYNTAX  DisplayString
		MAX-ACCESS  read-only
		STATUS  current
		DESCRIPTION
			"For port configured with OTU2/OTU1 traffic,
			ODU Background Block Errors increases on defects 
			detected and when BIP errors are less than 15% 
			Errored Blocks in incoming OTU signal.
			-----------------------------
			ommp81PlusInterfaceNumber:
			1 to 8 - CLIENT-1 to CLIENT-8
			9 - LINE-1
			-----------------------------
			Values:
			eg: 1234
			-----------------------------"
	::= { ommp81PlusPerformanceEntry 100 }

	ommp81PlusOduSevereErrorSeconds OBJECT-TYPE
		SYNTAX  DisplayString
		MAX-ACCESS  read-only
		STATUS  current
		DESCRIPTION
			"For port configured with OTU2/OTU1 traffic,
			ODU Severe Error Seconds increases on defects detected
			and when BIP errors are more than 15% Errored Blocks
			in incoming OTU signal.
			-----------------------------
			ommp81PlusInterfaceNumber:
			1 to 8 - CLIENT-1 to CLIENT-8
			9 - LINE-1
			-----------------------------
			Values:
			eg: 1234
			-----------------------------"
	::= { ommp81PlusPerformanceEntry 101 }

	ommp81PlusOduUnavailableSeconds OBJECT-TYPE
		SYNTAX  DisplayString
		MAX-ACCESS  read-only
		STATUS  current
		DESCRIPTION
			"For port configured with OTU2/OTU1 traffic,
			ODU Unavailable Seconds increases, when 10 consecutive
			Severe ODU Error seconds are detected
			-----------------------------
			ommp81PlusInterfaceNumber:
			1 to 8 - CLIENT-1 to CLIENT-8
			9 - LINE-1
			-----------------------------
			Values:
			eg: 1234
			-----------------------------"
	::= { ommp81PlusPerformanceEntry 102 }

	ommp81PlusOduBackgroundBlockErrorRatio OBJECT-TYPE
		SYNTAX  DisplayString
		MAX-ACCESS  read-only
		STATUS  current
		DESCRIPTION
			"For port configured with OTU2/OTU1 traffic,
			gives ODU Background Block Error Ratio i.e.
			the ratio of BBE in available time to total seconds
			in available time during a fixed measurement interval.
			-----------------------------
			ommp81PlusInterfaceNumber:
			1 to 8 - CLIENT-1 to CLIENT-8
			9 - LINE-1
			-----------------------------
			Values:
			eg: 1e-3
			-----------------------------"
	::= { ommp81PlusPerformanceEntry 104 }

	ommp81PlusOduSevereErrorSecondsErrorRatio OBJECT-TYPE
		SYNTAX  DisplayString
		MAX-ACCESS  read-only
		STATUS  current
		DESCRIPTION
			"For port configured with OTU2/OTU1 traffic,
			gives ODU Severe Error Seconds Error Ratio i.e.
			the ratio of SES in available time to total seconds
			in available time during a fixed measurement interval.
			-----------------------------
			ommp81PlusInterfaceNumber:
			1 to 8 - CLIENT-1 to CLIENT-8
			9 - LINE-1
			-----------------------------
			Values:
			eg: 1e-3
			-----------------------------"
	::= { ommp81PlusPerformanceEntry 105 }

	ommp81PlusOduFarEndErrorFreeSeconds OBJECT-TYPE
		SYNTAX  DisplayString
		MAX-ACCESS  read-only
		STATUS  current
		DESCRIPTION
			"For port configured with OTU2/OTU1 traffic,
			ODU Far end Error Free Seconds, increases when no
			far end errors or defects are detected
			-----------------------------
			ommp81PlusInterfaceNumber:
			1 to 8 - CLIENT-1 to CLIENT-8
			9 - LINE-1
			-----------------------------
			Values:
			eg: 1234
			-----------------------------"
	::= { ommp81PlusPerformanceEntry 106 }

	ommp81PlusOduFarEndErrorSeconds OBJECT-TYPE
		SYNTAX  DisplayString
		MAX-ACCESS  read-only
		STATUS  current
		DESCRIPTION
			"For port configured with OTU2/OTU1 traffic,
			ODU Far End Error Seconds increases on detection of
			defects like BDI and BEI at path monitoring level
			-----------------------------
			ommp81PlusInterfaceNumber:
			1 to 8 - CLIENT-1 to CLIENT-8
			9 - LINE-1
			-----------------------------
			Values:
			eg: 1234
			-----------------------------"
	::= { ommp81PlusPerformanceEntry 107 }

	ommp81PlusOduFarEndBackgroundBlockErrors OBJECT-TYPE
		SYNTAX  DisplayString
		MAX-ACCESS  read-only
		STATUS  current
		DESCRIPTION
			"For port configured with OTU2/OTU1 traffic,
			ODU Far End Background Block Errors increases when
			BEI errors are less than 15% Errored Blocks in
			incoming OTU signal.
			-----------------------------
			ommp81PlusInterfaceNumber:
			1 to 8 - CLIENT-1 to CLIENT-8
			9 - LINE-1
			-----------------------------
			Values:
			eg: 1234
			-----------------------------"
	::= { ommp81PlusPerformanceEntry 108 }

	ommp81PlusOduFarEndSevereErrorSeconds OBJECT-TYPE
		SYNTAX  DisplayString
		MAX-ACCESS  read-only
		STATUS  current
		DESCRIPTION
			"For port configured with OTU2/OTU1 traffic,
			ODU Far End Severe Error Seconds increases on defects
			like BDI are detected and when BEI errors are more than
			15% Errored Blocks in incoming OTU signal.
			-----------------------------
			ommp81PlusInterfaceNumber:
			1 to 8 - CLIENT-1 to CLIENT-8
			9 - LINE-1
			-----------------------------
			Values:
			eg: 1234
			-----------------------------"
	::= { ommp81PlusPerformanceEntry 109 }

	ommp81PlusOduFarEndUnavailableSeconds OBJECT-TYPE
		SYNTAX  DisplayString
		MAX-ACCESS  read-only
		STATUS  current
		DESCRIPTION
			"For port configured with OTU2/OTU1 traffic,
			ODU Far End Unavailable Seconds increases, when 10
			consecutive OTU Far End Error seconds are detected
			-----------------------------
			ommp81PlusInterfaceNumber:
			1 to 8 - CLIENT-1 to CLIENT-8
			9 - LINE-1
			-----------------------------
			Values:
			eg: 1234
			-----------------------------"
	::= { ommp81PlusPerformanceEntry 110 }

	ommp81PlusOduFarEndBackgroundBlockErrorRatio OBJECT-TYPE
		SYNTAX  DisplayString
		MAX-ACCESS  read-only
		STATUS  current
		DESCRIPTION
			"For port configured with OTU2/OTU1 traffic,
			gives ODU Far End Background Block Error Ratio i.e.
			the ratio of Far End BBE in available time to total
			seconds	in available time during a fixed measurement
			interval.
			-----------------------------
			ommp81PlusInterfaceNumber:
			1 to 8 - CLIENT-1 to CLIENT-8
			9 - LINE-1
			-----------------------------
			Values:
			eg: 1e-3
			-----------------------------"
	::= { ommp81PlusPerformanceEntry 112 }

	ommp81PlusOduFarEndSevereErrorSecondsErrorRatio OBJECT-TYPE
		SYNTAX  DisplayString
		MAX-ACCESS  read-only
		STATUS  current
		DESCRIPTION
			"For port configured with OTU2/OTU1 traffic,
			gives ODU Far End Severe Error Seconds Error Ratio i.e.
			The ratio of Far End SES in available time to total
			seconds in available time during a fixed measurement
			interval.
			-----------------------------
			ommp81PlusInterfaceNumber:
			1 to 8 - CLIENT-1 to CLIENT-8
			9 - LINE-1
			-----------------------------
			Values:
			eg: 1e-3
			-----------------------------"
	::= { ommp81PlusPerformanceEntry 113 }

	ommp81PlusSdhRsB1BitInterleavedParityErrors OBJECT-TYPE
		SYNTAX  DisplayString
		MAX-ACCESS  read-only
		STATUS  current
		DESCRIPTION
			"For port configured with STM1/4/16 traffic,
			SDH B1 BIP counter counts the Parity errors evaluated
			from byte B1 of the STM frame
			-----------------------------
			ommp81PlusInterfaceNumber:
			1 to 8 - CLIENT-1 to CLIENT-8
			-----------------------------
			Values:
			eg: 1234
			-----------------------------"
	::= { ommp81PlusPerformanceEntry 121 }

	ommp81PlusSdhMsB2BitInterleavedParityErrors OBJECT-TYPE
		SYNTAX  DisplayString
		MAX-ACCESS  read-only
		STATUS  current
		DESCRIPTION
			"For port configured with STM1/4/16 traffic,
			SDH B2 BIP counter counts the Parity errors evaluated 
			from byte B2 of the STM frame
			-----------------------------
			ommp81PlusInterfaceNumber:
			1 to 8 - CLIENT-1 to CLIENT-8
			-----------------------------
			Values:
			eg: 1234
			-----------------------------"
	::= { ommp81PlusPerformanceEntry 122 }

	ommp81PlusSdhMsB3BitInterleavedParityErrors OBJECT-TYPE
		SYNTAX  DisplayString
		MAX-ACCESS  read-only
		STATUS  current
		DESCRIPTION
			"For port configured with STM1/4/16 traffic,
			SDH B3 BIP counter counts the Parity errors evaluated 
			from byte B3 of the STM frame
			-----------------------------
			ommp81PlusInterfaceNumber:
			1 to 8 - CLIENT-1 to CLIENT-8
			-----------------------------
			Values:
			eg: 1234
			-----------------------------"
	::= { ommp81PlusPerformanceEntry 123 }

	ommp81PlusSdhMsRemoteErrorIndicationErrorCount OBJECT-TYPE
		SYNTAX  DisplayString
		MAX-ACCESS  read-only
		STATUS  current
		DESCRIPTION
			"For port configured with STM1/4/16 traffic,
			SDH MS-REI error count increases when
			MS-REI is detected for that particular second
			in incoming SDH signal.
			-----------------------------
			ommp81PlusInterfaceNumber:
			1 to 8 - CLIENT-1 to CLIENT-8
			-----------------------------
			Values:
			eg: 1234
			-----------------------------"
	::= { ommp81PlusPerformanceEntry 124 }

	ommp81PlusSdhMsRemoteDefectIndicationErrorCount OBJECT-TYPE
		SYNTAX  DisplayString
		MAX-ACCESS  read-only
		STATUS  current
		DESCRIPTION
			"For port configured with STM1/4/16 traffic,
			SDH MS-RDI error count increases when
			MS-RDI is detected for that particular second
			in incoming SDH signal.
			-----------------------------
			ommp81PlusInterfaceNumber:
			1 to 8 - CLIENT-1 to CLIENT-8
			-----------------------------
			Values:
			eg: 1234
			-----------------------------"
	::= { ommp81PlusPerformanceEntry 125 }

	ommp81PlusSdhErrorFreeSeconds OBJECT-TYPE
		SYNTAX  DisplayString
		MAX-ACCESS  read-only
		STATUS  current
		DESCRIPTION
			"For port configured with STM1/4/16 traffic,
			SDH Error Free Seconds increases when no BIP
			errors or no defects are detected in incoming
			SDH signal.
			-----------------------------
			ommp81PlusInterfaceNumber:
			1 to 8 - CLIENT-1 to CLIENT-8
			-----------------------------
			Values:
			eg: 1234
			-----------------------------"
	::= { ommp81PlusPerformanceEntry 126 }

	ommp81PlusSdhErrorSeconds OBJECT-TYPE
		SYNTAX  DisplayString
		MAX-ACCESS  read-only
		STATUS  current
		DESCRIPTION
			"For port configured with STM1/4/16 traffic,
			SDH Error Seconds increases on detection of BIP errors
			and defects like B1 errors, LOS, LOF in incoming SDH
			signal.
			-----------------------------
			ommp81PlusInterfaceNumber:
			1 to 8 - CLIENT-1 to CLIENT-8
			-----------------------------
			Values:
			eg: 1234
			-----------------------------"
	::= { ommp81PlusPerformanceEntry 127 }

	ommp81PlusSdhBackgroundBlockErrors OBJECT-TYPE
		SYNTAX  DisplayString
		MAX-ACCESS  read-only
		STATUS  current
		DESCRIPTION
			"For port configured with STM1/4/16 traffic,
			SDH Background Block Errors increases on defects 
			detected and when BIP errors are less than 30%
			errored blocks in the incoming SDH signal.
			-----------------------------
			ommp81PlusInterfaceNumber:
			1 to 8 - CLIENT-1 to CLIENT-8
			-----------------------------
			Values:
			eg: 1234
			-----------------------------"
	::= { ommp81PlusPerformanceEntry 128 }

	ommp81PlusSdhSevereErrorSeconds OBJECT-TYPE
		SYNTAX  DisplayString
		MAX-ACCESS  read-only
		STATUS  current
		DESCRIPTION
			"For port configured with STM1/4/16 traffic,
			SDH Severe Error Secodns increases on defects 
			detected and when BIP errors are greater than or equal
			to 30% errored blocks in the incoming SDH signal.
			-----------------------------
			ommp81PlusInterfaceNumber:
			1 to 8 - CLIENT-1 to CLIENT-8
			-----------------------------
			Values:
			eg: 1234
			-----------------------------"
	::= { ommp81PlusPerformanceEntry 129 }

	ommp81PlusSdhUnavailableSeconds OBJECT-TYPE
		SYNTAX  DisplayString
		MAX-ACCESS  read-only
		STATUS  current
		DESCRIPTION
			"For port configured with STM1/4/16 traffic,
			SDH Unavailable Seconds increases, when 10 consecutive
			Severe Error seconds are detected
			-----------------------------
			ommp81PlusInterfaceNumber:
			1 to 8 - CLIENT-1 to CLIENT-8
			-----------------------------
			Values:
			eg: 1234
			-----------------------------"
	::= { ommp81PlusPerformanceEntry 130 }

	ommp81PlusSdhErrorSecondsErrorRatio OBJECT-TYPE
		SYNTAX  DisplayString
		MAX-ACCESS  read-only
		STATUS  current
		DESCRIPTION
			"For port configured with STM1/4/16 traffic,
			gives SDH Error Seconds Error Ratio.
			The ratio of ES in available time to total seconds
			in available time during a fixed measurement interval.
			-----------------------------
			ommp81PlusInterfaceNumber:
			1 to 8 - CLIENT-1 to CLIENT-8
			-----------------------------
			Values:
			eg: 1234
			-----------------------------"
	::= { ommp81PlusPerformanceEntry 131 }

	ommp81PlusSdhBackgroundBlockErrorRatio OBJECT-TYPE
		SYNTAX  DisplayString
		MAX-ACCESS  read-only
		STATUS  current
		DESCRIPTION
			"For port configured with STM1/4/16 traffic,
			gives SDH Background Block Error Ratio.
			The ratio of BBE in available time to total seconds
			in available time during a fixed measurement interval.
			-----------------------------
			ommp81PlusInterfaceNumber:
			1 to 8 - CLIENT-1 to CLIENT-8
			-----------------------------
			Values:
			eg: 1234
			-----------------------------"
	::= { ommp81PlusPerformanceEntry 132 }

	ommp81PlusSdhSevereErrorSecondsErrorRatio OBJECT-TYPE
		SYNTAX  DisplayString
		MAX-ACCESS  read-only
		STATUS  current
		DESCRIPTION
			"For port configured with STM1/4/16 traffic,
			gives SDH Severe Error Seconds Error Ratio.
			The ratio of SES in available time to total seconds
			in available time during a fixed measurement interval.
			-----------------------------
			ommp81PlusInterfaceNumber:
			1 to 8 - CLIENT-1 to CLIENT-8
			-----------------------------
			Values:
			eg: 1234
			-----------------------------"
	::= { ommp81PlusPerformanceEntry 133 }

	ommp81PlusEthernetMacTerminatedFramesTransmitted OBJECT-TYPE
		SYNTAX  DisplayString
		MAX-ACCESS  read-only
		STATUS  current
		DESCRIPTION
			"For port configured with GE-GFP-F/FE-GFP-F traffic,
			gives the number of Ethernet frame transmitted.
			-----------------------------
			ommp81PlusInterfaceNumber:
			1 to 8 - CLIENT-1 to CLIENT-8
			-----------------------------
			Values:
			eg: 1234
			-----------------------------"
	::= { ommp81PlusPerformanceEntry 151 }

	ommp81PlusEthernetMacTerminatedFramesReceived OBJECT-TYPE
		SYNTAX  DisplayString
		MAX-ACCESS  read-only
		STATUS  current
		DESCRIPTION
			"For port configured with GE-GFP-F/FE-GFP-F traffic,
			gives the number of Ethernet frame received.
			-----------------------------
			ommp81PlusInterfaceNumber:
			1 to 8 - CLIENT-1 to CLIENT-8
			-----------------------------
			Values:
			eg: 1234
			-----------------------------"
	::= { ommp81PlusPerformanceEntry 152 }

	ommp81PlusEthernetMacTerminatedPauseFramesTransmitted OBJECT-TYPE
		SYNTAX  DisplayString
		MAX-ACCESS  read-only
		STATUS  current
		DESCRIPTION
			"For port configured with GE-GFP-F/FE-GFP-F traffic,
			gives number of Pause frame transmitted.
			-----------------------------
			ommp81PlusInterfaceNumber:
			1 to 8 - CLIENT-1 to CLIENT-8
			-----------------------------
			Values:
			eg: 1234
			-----------------------------"
	::= { ommp81PlusPerformanceEntry 153 }

	ommp81PlusEthernetMacTerminatedPauseFramesReceived OBJECT-TYPE
		SYNTAX  DisplayString
		MAX-ACCESS  read-only
		STATUS  current
		DESCRIPTION
			"For port configured with GE-GFP-F/FE-GFP-F traffic,
			gives the number of Pause frame received.
			-----------------------------
			ommp81PlusInterfaceNumber:
			1 to 8 - CLIENT-1 to CLIENT-8
			-----------------------------
			Values:
			eg: 1234
			-----------------------------"
	::= { ommp81PlusPerformanceEntry 154 }

	ommp81PlusEthernetMacTerminatedUnicastFramesTransmitted OBJECT-TYPE
		SYNTAX  DisplayString
		MAX-ACCESS  read-only
		STATUS  current
		DESCRIPTION
			"For port configured with GE-GFP-F/FE-GFP-F traffic,
			gives the number of unicast frames transmitted.
			-----------------------------
			ommp81PlusInterfaceNumber:
			1 to 8 - CLIENT-1 to CLIENT-8
			-----------------------------
			Values:
			eg: 1234
			-----------------------------"
	::= { ommp81PlusPerformanceEntry 155 }

	ommp81PlusEthernetMacTerminatedUnicastFramesReceived OBJECT-TYPE
		SYNTAX  DisplayString
		MAX-ACCESS  read-only
		STATUS  current
		DESCRIPTION
			"For port configured with GE-GFP-F/FE-GFP-F traffic,
			gives, the number of unicast frames received.
			-----------------------------
			ommp81PlusInterfaceNumber:
			1 to 8 - CLIENT-1 to CLIENT-8
			-----------------------------
			Values:
			eg: 1234
			-----------------------------"
	::= { ommp81PlusPerformanceEntry 156 }

	ommp81PlusEthernetMacTerminatedMulticastFramesTransmitted OBJECT-TYPE
		SYNTAX  DisplayString
		MAX-ACCESS  read-only
		STATUS  current
		DESCRIPTION
			"For port configured with GE-GFP-F/FE-GFP-F traffic,
			gives, the number of multicast frames transmitted.
			-----------------------------
			ommp81PlusInterfaceNumber:
			1 to 8 - CLIENT-1 to CLIENT-8
			-----------------------------
			Values:
			eg: 1234
			-----------------------------"
	::= { ommp81PlusPerformanceEntry 157 }

	ommp81PlusEthernetMacTerminatedMulticastFramesReceived OBJECT-TYPE
		SYNTAX  DisplayString
		MAX-ACCESS  read-only
		STATUS  current
		DESCRIPTION
			"For port configured with GE-GFP-F/FE-GFP-F traffic,
			gives the number of multicast frames received.
			-----------------------------
			ommp81PlusInterfaceNumber:
			1 to 8 - CLIENT-1 to CLIENT-8
			-----------------------------
			Values:
			eg: 1234
			-----------------------------"
	::= { ommp81PlusPerformanceEntry 158 }

	ommp81PlusEthernetMacTerminatedBroadcastFramesTransmitted OBJECT-TYPE
		SYNTAX  DisplayString
		MAX-ACCESS  read-only
		STATUS  current
		DESCRIPTION
			"For port configured with GE-GFP-F/FE-GFP-F traffic,
			gives the number of broadcast frames transmitted.
			-----------------------------
			ommp81PlusInterfaceNumber:
			1 to 8 - CLIENT-1 to CLIENT-8
			-----------------------------
			Values:
			eg: 1234
			-----------------------------"
	::= { ommp81PlusPerformanceEntry 159 }

	ommp81PlusEthernetMacTerminatedBroadcastFramesReceived OBJECT-TYPE
		SYNTAX  DisplayString
		MAX-ACCESS  read-only
		STATUS  current
		DESCRIPTION
			"For port configured with GE-GFP-F/FE-GFP-F traffic,
			gives the number of broadcast frames received.
			-----------------------------
			ommp81PlusInterfaceNumber:
			1 to 8 - CLIENT-1 to CLIENT-8
			-----------------------------
			Values:
			eg: 1234
			-----------------------------"
	::= { ommp81PlusPerformanceEntry 160 }

	ommp81PlusEthernetMacTerminatedUnderSizeFramesTransmitted OBJECT-TYPE
		SYNTAX  DisplayString
		MAX-ACCESS  read-only
		STATUS  current
		DESCRIPTION
			"For port configured with GE-GFP-F/FE-GFP-F traffic,
			gives the count of transmitted ethernet frames whose
			frame size is less than	64 bytes.
			-----------------------------
			ommp81PlusInterfaceNumber:
			1 to 8 - CLIENT-1 to CLIENT-8
			-----------------------------
			Values:
			eg: 1234
			-----------------------------"
	::= { ommp81PlusPerformanceEntry 161 }

	ommp81PlusEthernetMacTerminatedUnderSizeFramesReceived OBJECT-TYPE
		SYNTAX  DisplayString
		MAX-ACCESS  read-only
		STATUS  current
		DESCRIPTION
			"For port configured with GE-GFP-F/FE-GFP-F traffic,
			gives the count of received ethernet frames whose
			framesize is less than 64 bytes.
			-----------------------------
			ommp81PlusInterfaceNumber:
			1 to 8 - CLIENT-1 to CLIENT-8
			-----------------------------
			Values:
			eg: 1234
			-----------------------------"
	::= { ommp81PlusPerformanceEntry 162 }

	ommp81PlusEthernetMacTerminatedOverSizeFramesTransmitted OBJECT-TYPE
		SYNTAX  DisplayString
		MAX-ACCESS  read-only
		STATUS  current
		DESCRIPTION
			"For port configured with GE-GFP-F/FE-GFP-F traffic,
			gives the count of transmitted ethernet frames 
			whose frame size is greater than 1518 bytes.
			-----------------------------
			ommp81PlusInterfaceNumber:
			1 to 8 - CLIENT-1 to CLIENT-8
			-----------------------------
			Values:
			eg: 1234
			-----------------------------"
	::= { ommp81PlusPerformanceEntry 163 }

	ommp81PlusEthernetMacTerminatedOverSizeFramesReceived OBJECT-TYPE
		SYNTAX  DisplayString
		MAX-ACCESS  read-only
		STATUS  current
		DESCRIPTION
			"For port configured with GE-GFP-F/FE-GFP-F traffic,
			gives the count of received ethernet frames
			whose frame size is greater than 
			1518 bytes.
			-----------------------------
			ommp81PlusInterfaceNumber:
			1 to 8 - CLIENT-1 to CLIENT-8
			-----------------------------
			Values:
			eg: 1234
			-----------------------------"
	::= { ommp81PlusPerformanceEntry 164 }

	ommp81PlusEthernetMacTerminatedVlanTaggedFramesTransmitted OBJECT-TYPE
		SYNTAX  DisplayString
		MAX-ACCESS  read-only
		STATUS  current
		DESCRIPTION
			"For port configured with GE-GFP-F/FE-GFP-F traffic,
			gives the count of transmitted VLAN Tagged frames.
			-----------------------------
			ommp81PlusInterfaceNumber:
			1 to 8 - CLIENT-1 to CLIENT-8
			-----------------------------
			Values:
			eg: 1234
			-----------------------------"
	::= { ommp81PlusPerformanceEntry 165 }

	ommp81PlusEthernetMacTerminatedVlanTaggedFramesReceived OBJECT-TYPE
		SYNTAX  DisplayString
		MAX-ACCESS  read-only
		STATUS  current
		DESCRIPTION
			"For port configured with GE-GFP-F/FE-GFP-F traffic,
			gives the count of received VLAN Tagged frames.
			-----------------------------
			ommp81PlusInterfaceNumber:
			1 to 8 - CLIENT-1 to CLIENT-8
			-----------------------------
			Values:
			eg: 1234
			-----------------------------"
	::= { ommp81PlusPerformanceEntry 166 }

	ommp81PlusEthernetMacTerminatedFrameSymbolErrorsReceived OBJECT-TYPE
		SYNTAX  DisplayString
		MAX-ACCESS  read-only
		STATUS  current
		DESCRIPTION
			"For port configured with GE-GFP-F/FE-GFP-F traffic,
			gives the count of Frame Symbol Error received.
			-----------------------------
			ommp81PlusInterfaceNumber:
			1 to 8 - CLIENT-1 to CLIENT-8
			-----------------------------
			Values:
			eg: 1234
			-----------------------------"
	::= { ommp81PlusPerformanceEntry 167 }

	ommp81PlusEthernetMacTerminatedFragmentFramesReceived OBJECT-TYPE
		SYNTAX  DisplayString
		MAX-ACCESS  read-only
		STATUS  current
		DESCRIPTION
			"For port configured with GE-GFP-F/FE-GFP-F traffic,
			gives the count of Fragment Frames received.
			-----------------------------
			ommp81PlusInterfaceNumber:
			1 to 8 - CLIENT-1 to CLIENT-8
			-----------------------------
			Values:
			eg: 1234
			-----------------------------"
	::= { ommp81PlusPerformanceEntry 168 }

	ommp81PlusEthernetMacTerminatedFrameCheckSequenceErrorsReceived OBJECT-TYPE
		SYNTAX  DisplayString
		MAX-ACCESS  read-only
		STATUS  current
		DESCRIPTION
			"For port configured with GE-GFP-F/FE-GFP-F traffic,
			gives the count of Frame Check Sequence Errors received.
			-----------------------------
			ommp81PlusInterfaceNumber:
			1 to 8 - CLIENT-1 to CLIENT-8
			-----------------------------
			Values:
			eg: 1234
			-----------------------------"
	::= { ommp81PlusPerformanceEntry 169 }

	ommp81PlusEthernetMacTerminatedFramesReceivedWithNoDefect OBJECT-TYPE
		SYNTAX  DisplayString
		MAX-ACCESS  read-only
		STATUS  current
		DESCRIPTION
			"For port configured with GE-GFP-F/FE-GFP-F traffic,
			gives the count of frames that are 
			received with no defects such as undersized frames, FCS
			errors.
			-----------------------------
			ommp81PlusInterfaceNumber:
			1 to 8 - CLIENT-1 to CLIENT-8
			-----------------------------
			Values:
			eg: 1234
			-----------------------------"
	::= { ommp81PlusPerformanceEntry 170 }
	
	ommp81PlusEthernetMacTerminatedBytesTransmitted OBJECT-TYPE
		SYNTAX  DisplayString
		MAX-ACCESS  read-only
		STATUS  current
		DESCRIPTION
			"For port configured with GE-GFP-F/FE-GFP-F traffic,
			gives the count of the Ethernet bytes transmitted.
			-----------------------------
			ommp81PlusInterfaceNumber:
			1 to 8 - CLIENT-1 to CLIENT-8
			-----------------------------
			Values:
			eg: 1234
			-----------------------------"
	::= { ommp81PlusPerformanceEntry 171 }

	ommp81PlusEthernetMacTerminatedBytesReceived OBJECT-TYPE
		SYNTAX  DisplayString
		MAX-ACCESS  read-only
		STATUS  current
		DESCRIPTION
			"For port configured with GE-GFP-F/FE-GFP-F traffic,
			gives the count of Ethernet bytes received.
			-----------------------------
			ommp81PlusInterfaceNumber:
			1 to 8 - CLIENT-1 to CLIENT-8
			-----------------------------
			Values:
			eg: 1234
			-----------------------------"
	::= { ommp81PlusPerformanceEntry 172 }

	ommp81PlusEthernetMacTerminatedControlFramesTransmitted OBJECT-TYPE
		SYNTAX  DisplayString
		MAX-ACCESS  read-only
		STATUS  current
		DESCRIPTION
			"For port configured with GE-GFP-F/FE-GFP-F traffic,
			gives the count of the Ethernet control frames
			transmitted.
			-----------------------------
			ommp81PlusInterfaceNumber:
			1 to 8 - CLIENT-1 to CLIENT-8
			-----------------------------
			Values:
			eg: 1234
			-----------------------------"
	::= { ommp81PlusPerformanceEntry 173 }

	ommp81PlusEthernetMacTerminatedControlFramesReceived OBJECT-TYPE
		SYNTAX  DisplayString
		MAX-ACCESS  read-only
		STATUS  current
		DESCRIPTION
			"For port configured with GE-GFP-F/FE-GFP-F traffic,
			gives the count of the Ethernet control frames
			received.
			-----------------------------
			ommp81PlusInterfaceNumber:
			1 to 8 - CLIENT-1 to CLIENT-8
			-----------------------------
			Values:
			eg: 1234
			-----------------------------"
	::= { ommp81PlusPerformanceEntry 174 }

	ommp81PlusEthernetTransparentTransmitLcvCount OBJECT-TYPE
		SYNTAX  DisplayString
		MAX-ACCESS  read-only
		STATUS  current
		DESCRIPTION
			"For port configured with GE-GFP-T/FE-GFP-T traffic,
			gives the count of Transparent LCV that are transmitted.
			-----------------------------
			ommp81PlusInterfaceNumber:
			1 to 8 - CLIENT-1 to CLIENT-8
			-----------------------------
			Values:
			eg: 1234
			-----------------------------"
	::= { ommp81PlusPerformanceEntry 181 }

	ommp81PlusEthernetTransparentTransmitPropagationErrorDeletionCount OBJECT-TYPE
		SYNTAX  DisplayString
		MAX-ACCESS  read-only
		STATUS  current
		DESCRIPTION
			"For port configured with GE-GFP-T/FE-GFP-T traffic,
			gives the count of Propagation Error Deletion Count
			that are transmitted.
			-----------------------------
			ommp81PlusInterfaceNumber:
			1 to 8 - CLIENT-1 to CLIENT-8
			-----------------------------
			Values:
			eg: 1234
			-----------------------------"
	::= { ommp81PlusPerformanceEntry 182 }

	ommp81PlusEthernetTransparentTransmitIdleDeletionCount OBJECT-TYPE
		SYNTAX  DisplayString
		MAX-ACCESS  read-only
		STATUS  current
		DESCRIPTION
			"For port configured with GE-GFP-T/FE-GFP-T traffic,
			gives the count of Idle Deletion Count that are
			transmitted.
			-----------------------------
			ommp81PlusInterfaceNumber:
			1 to 8 - CLIENT-1 to CLIENT-8
			-----------------------------
			Values:
			eg: 1234
			-----------------------------"
	::= { ommp81PlusPerformanceEntry 183 }

	ommp81PlusEthernetTransparentTransmitConfDeletionCount OBJECT-TYPE
		SYNTAX  DisplayString
		MAX-ACCESS  read-only
		STATUS  current
		DESCRIPTION
			"For port configured with GE-GFP-T/FE-GFP-T traffic,
			gives the count of Conf Deletion Count that are
			transmitted.
			-----------------------------
			ommp81PlusInterfaceNumber:
			1 to 8 - CLIENT-1 to CLIENT-8
			-----------------------------
			Values:
			eg: 1234
			-----------------------------"
	::= { ommp81PlusPerformanceEntry 184 }

	ommp81PlusEthernetTransparentTransmitPropagationInsertionCount OBJECT-TYPE
		SYNTAX  DisplayString
		MAX-ACCESS  read-only
		STATUS  current
		DESCRIPTION
			"For port configured with GE-GFP-T/FE-GFP-T traffic,
			gives the count of Propagation Insertions that are
			transmitted.
			-----------------------------
			ommp81PlusInterfaceNumber:
			1 to 8 - CLIENT-1 to CLIENT-8
			-----------------------------
			Values:
			eg: 1234
			-----------------------------"
	::= { ommp81PlusPerformanceEntry 185 }

	ommp81PlusEthernetTransparentTransmitIdleInsertionCount OBJECT-TYPE
		SYNTAX  DisplayString
		MAX-ACCESS  read-only
		STATUS  current
		DESCRIPTION
			"For port configured with GE-GFP-T/FE-GFP-T traffic,
			gives the count of Idle Insertions that are tranmsitted.
			-----------------------------
			ommp81PlusInterfaceNumber:
			1 to 8 - CLIENT-1 to CLIENT-8
			-----------------------------
			Values:
			eg: 1234
			-----------------------------"
	::= { ommp81PlusPerformanceEntry 186 }

	ommp81PlusEthernetTransparentTransmitConfInsertionCount OBJECT-TYPE
		SYNTAX  DisplayString
		MAX-ACCESS  read-only
		STATUS  current
		DESCRIPTION
			"For port configured with GE-GFP-T/FE-GFP-T traffic,
			gives the count of Conf Insertions that are tranmsitted.
			-----------------------------
			ommp81PlusInterfaceNumber:
			1 to 8 - CLIENT-1 to CLIENT-8
			-----------------------------
			Values:
			eg: 1234
			-----------------------------"
	::= { ommp81PlusPerformanceEntry 187 }

	ommp81PlusEthernetTransparentReceiveLcvCount OBJECT-TYPE
		SYNTAX  DisplayString
		MAX-ACCESS  read-only
		STATUS  current
		DESCRIPTION
			"For port configured with GE-GFP-T/FE-GFP-T traffic,
			gives the count of LCV that are received.
			-----------------------------
			ommp81PlusInterfaceNumber:
			1 to 8 - CLIENT-1 to CLIENT-8
			-----------------------------
			Values:
			eg: 1234
			-----------------------------"
	::= { ommp81PlusPerformanceEntry 188 }

	ommp81PlusEthernetTransparentReceivePropagationErrorDeletionCount OBJECT-TYPE
		SYNTAX  DisplayString
		MAX-ACCESS  read-only
		STATUS  current
		DESCRIPTION
			"For port configured with GE-GFP-T/FE-GFP-T traffic,
			gives the count of Propagation Error Deletions that are
			received.
			-----------------------------
			ommp81PlusInterfaceNumber:
			1 to 8 - CLIENT-1 to CLIENT-8
			-----------------------------
			Values:
			eg: 1234
			-----------------------------"
	::= { ommp81PlusPerformanceEntry 189 }

	ommp81PlusEthernetTransparentReceiveIdleDeletionCount OBJECT-TYPE
		SYNTAX  DisplayString
		MAX-ACCESS  read-only
		STATUS  current
		DESCRIPTION
			"For port configured with GE-GFP-T/FE-GFP-T traffic,
			gives the count of Idle Deletions that are
			received.
			-----------------------------
			ommp81PlusInterfaceNumber:
			1 to 8 - CLIENT-1 to CLIENT-8
			-----------------------------
			Values:
			eg: 1234
			-----------------------------"
	::= { ommp81PlusPerformanceEntry 190 }

	ommp81PlusEthernetTransparentReceiveConfDeletionCount OBJECT-TYPE
		SYNTAX  DisplayString
		MAX-ACCESS  read-only
		STATUS  current
		DESCRIPTION
			"For port configured with GE-GFP-T/FE-GFP-T traffic,
			gives the count of Conf Deletions that are
			received.
			-----------------------------
			ommp81PlusInterfaceNumber:
			1 to 8 - CLIENT-1 to CLIENT-8
			-----------------------------
			Values:
			eg: 1234
			-----------------------------"
	::= { ommp81PlusPerformanceEntry 191 }

	ommp81PlusEthernetTransparentReceivePacketDeletionCount OBJECT-TYPE
		SYNTAX  DisplayString
		MAX-ACCESS  read-only
		STATUS  current
		DESCRIPTION
			"For port configured with GE-GFP-T/FE-GFP-T traffic,
			gives the count of Packet Deletions that are
			received.
			-----------------------------
			ommp81PlusInterfaceNumber:
			1 to 8 - CLIENT-1 to CLIENT-8
			-----------------------------
			Values:
			eg: 1234
			-----------------------------"
	::= { ommp81PlusPerformanceEntry 192 }

	ommp81PlusGfpCoreHeaderErrorCount OBJECT-TYPE
		SYNTAX  DisplayString
		MAX-ACCESS  read-only
		STATUS  current
		DESCRIPTION
			"For port configured with
			GE-GFP-F/FE-GFP-F/GE-GFP-T/FE-GFP-T traffic,
			gives the count of received GFP frames which have error
			in the core header.
			-----------------------------
			ommp81PlusInterfaceNumber:
			1 to 8 - CLIENT-1 to CLIENT-8
			-----------------------------
			Values:
			eg: 1234
			-----------------------------"
	::= { ommp81PlusPerformanceEntry 201 }

	ommp81PlusGfpExtentionHeaderErrorCount OBJECT-TYPE
		SYNTAX  DisplayString
		MAX-ACCESS  read-only
		STATUS  current
		DESCRIPTION
			"For port configured with
			GE-GFP-F/FE-GFP-F/GE-GFP-T/FE-GFP-T traffic,
			gives the count of received GFP frames which have error
			in the extention header.
			-----------------------------
			ommp81PlusInterfaceNumber:
			1 to 8 - CLIENT-1 to CLIENT-8
			-----------------------------
			Values:
			eg: 1234
			-----------------------------"
	::= { ommp81PlusPerformanceEntry 202 }

	ommp81PlusGfpFrameCountWithSingleBitError OBJECT-TYPE
		SYNTAX  DisplayString
		MAX-ACCESS  read-only
		STATUS  current
		DESCRIPTION
			"For port configured with
			GE-GFP-F/FE-GFP-F/GE-GFP-T/FE-GFP-T traffic,
			gives the count of GFP Frames that are received 
			with single bit error.
			-----------------------------
			ommp81PlusInterfaceNumber:
			1 to 8 - CLIENT-1 to CLIENT-8
			-----------------------------
			Values:
			eg: 1234
			-----------------------------"
	::= { ommp81PlusPerformanceEntry 203 }

	ommp81PlusGfpTypeHeaderErrorCount OBJECT-TYPE
		SYNTAX  DisplayString
		MAX-ACCESS  read-only
		STATUS  current
		DESCRIPTION
			"For port configured with
			GE-GFP-F/FE-GFP-F/GE-GFP-T/FE-GFP-T traffic,
			gives the count of received GFP frames which have error
			in the type header.
			-----------------------------
			ommp81PlusInterfaceNumber:
			1 to 8 - CLIENT-1 to CLIENT-8
			-----------------------------
			Values:
			eg: 1234
			-----------------------------"
	::= { ommp81PlusPerformanceEntry 204 }

	ommp81PlusGfpReceiveDropFrameCount OBJECT-TYPE
		SYNTAX  DisplayString
		MAX-ACCESS  read-only
		STATUS  current
		DESCRIPTION
			"For port configured with
			GE-GFP-F/FE-GFP-F/GE-GFP-T/FE-GFP-T traffic,
			gives the Drop Frame count of received GFP frames.
			-----------------------------
			ommp81PlusInterfaceNumber:
			1 to 8 - CLIENT-1 to CLIENT-8
			-----------------------------
			Values:
			eg: 1234
			-----------------------------"
	::= { ommp81PlusPerformanceEntry 205 }

	ommp81PlusGfpReceiveExtensionHeaderIdentifierFilterDropCount OBJECT-TYPE
		SYNTAX  DisplayString
		MAX-ACCESS  read-only
		STATUS  current
		DESCRIPTION
			"For port configured with
			GE-GFP-F/FE-GFP-F/GE-GFP-T/FE-GFP-T traffic,
			gives the Extension Header Identifier Filter
			Drop count of received GFP frames.
			-----------------------------
			ommp81PlusInterfaceNumber:
			1 to 8 - CLIENT-1 to CLIENT-8
			-----------------------------
			Values:
			eg: 1234
			-----------------------------"
	::= { ommp81PlusPerformanceEntry 206 }

	ommp81PlusFcTransmitWordCount OBJECT-TYPE
		SYNTAX  DisplayString
		MAX-ACCESS  read-only
		STATUS  current
		DESCRIPTION
			"For port configured with FC-100/FC-200 traffic,
			gives the count of words that are transmitted.
			-----------------------------
			ommp81PlusInterfaceNumber:
			1 to 8 - CLIENT-1 to CLIENT-8
			-----------------------------
			Values:
			eg: 1234
			-----------------------------"
	::= { ommp81PlusPerformanceEntry 211 }

	ommp81PlusFcReceiveWordCount OBJECT-TYPE
		SYNTAX  DisplayString
		MAX-ACCESS  read-only
		STATUS  current
		DESCRIPTION
			"For port configured with FC-100/FC-200 traffic,
			gives the count of words that are received.
			-----------------------------
			ommp81PlusInterfaceNumber:
			1 to 8 - CLIENT-1 to CLIENT-8
			-----------------------------
			Values:
			eg: 1234
			-----------------------------"
	::= { ommp81PlusPerformanceEntry 212 }

	ommp81PlusFcTransmitTotalPackets OBJECT-TYPE
		SYNTAX  DisplayString
		MAX-ACCESS  read-only
		STATUS  current
		DESCRIPTION
			"For port configured with FC-100/FC-200 traffic,
			gives the count of total packets that are tranmsitted.
			-----------------------------
			ommp81PlusInterfaceNumber:
			1 to 8 - CLIENT-1 to CLIENT-8
			-----------------------------
			Values:
			eg: 1234
			-----------------------------"
	::= { ommp81PlusPerformanceEntry 213 }

	ommp81PlusFcReceiveTotalPackets OBJECT-TYPE
		SYNTAX  DisplayString
		MAX-ACCESS  read-only
		STATUS  current
		DESCRIPTION
			"For port configured with FC-100/FC-200 traffic,
			gives the count of total packets that are received.
			-----------------------------
			ommp81PlusInterfaceNumber:
			1 to 8 - CLIENT-1 to CLIENT-8
			-----------------------------
			Values:
			eg: 1234
			-----------------------------"
	::= { ommp81PlusPerformanceEntry 214 }

	ommp81PlusFcTransmitBadCrc OBJECT-TYPE
		SYNTAX  DisplayString
		MAX-ACCESS  read-only
		STATUS  current
		DESCRIPTION
			"For port configured with FC-100/FC-200 traffic,
			gives the count of bad CRCs that are tranmsitted.
			-----------------------------
			ommp81PlusInterfaceNumber:
			1 to 8 - CLIENT-1 to CLIENT-8
			-----------------------------
			Values:
			eg: 1234
			-----------------------------"
	::= { ommp81PlusPerformanceEntry 215 }

	ommp81PlusFcReceiveBadCrc OBJECT-TYPE
		SYNTAX  DisplayString
		MAX-ACCESS  read-only
		STATUS  current
		DESCRIPTION
			"For port configured with FC-100/FC-200 traffic,
			gives the frame count of that
			had CRC32 mismatch, invalid/abort end-of-frame or
			line code violations.
			-----------------------------
			ommp81PlusInterfaceNumber:
			1 to 8 - CLIENT-1 to CLIENT-8
			-----------------------------
			Values:
			eg: 1234
			-----------------------------"
	::= { ommp81PlusPerformanceEntry 216 }

	ommp81PlusFcTransmitLcvCount OBJECT-TYPE
		SYNTAX  DisplayString
		MAX-ACCESS  read-only
		STATUS  current
		DESCRIPTION
			"For port configured with FC-100/FC-200 traffic,
			reports the number of 8B/10B line-code violations
			(invalid characters or incorrect running
			disparity) that occurred on the data from upstream
			block.
			-----------------------------
			ommp81PlusInterfaceNumber:
			1 to 8 - CLIENT-1 to CLIENT-8
			-----------------------------
			Values:
			eg: 1234
			-----------------------------"
	::= { ommp81PlusPerformanceEntry 217 }

	ommp81PlusFcReceiveLcvCount OBJECT-TYPE
		SYNTAX  DisplayString
		MAX-ACCESS  read-only
		STATUS  current
		DESCRIPTION
			"For port configured with FC-100/FC-200 traffic,
			reports the number of 8B/10B line-code violations
			(invalid characters or incorrect running disparity) that
			occurred on the data from line interface.
			-----------------------------
			ommp81PlusInterfaceNumber:
			1 to 8 - CLIENT-1 to CLIENT-8
			-----------------------------
			Values:
			eg: 1234
			-----------------------------"
	::= { ommp81PlusPerformanceEntry 218 }

	ommp81PlusFcTransmitFillWordInsertionCount OBJECT-TYPE
		SYNTAX  DisplayString
		MAX-ACCESS  read-only
		STATUS  current
		DESCRIPTION
			"For port configured with FC-100/FC-200 traffic,
			gives the count of FW Insertion count. It
			reports number of fill words that were inserted
			for rate adaptation. For fibre channel, each increment
			indicates the number of 4-character IDLE
			(or ARBs - when enabled) ordered set that were inserted.
			-----------------------------
			ommp81PlusInterfaceNumber:
			1 to 8 - CLIENT-1 to CLIENT-8
			-----------------------------
			Values:
			eg: 1234
			-----------------------------"
	::= { ommp81PlusPerformanceEntry 219 }

	ommp81PlusFcTransmitPrimitiveSequenceInsertionCount OBJECT-TYPE
		SYNTAX  DisplayString
		MAX-ACCESS  read-only
		STATUS  current
		DESCRIPTION
			"For port configured with FC-100/FC-200 traffic,
			gives the count of Primitive Sequence Insertions. It
			reports number of primitive sequences or sequence
			functions that were inserted for rate adaptation.
			For fibre channel, each increment indicates the number
			of 4-character Primitive Sequences that
			were inserted.
			-----------------------------
			ommp81PlusInterfaceNumber:
			1 to 8 - CLIENT-1 to CLIENT-8
			-----------------------------
			Values:
			eg: 1234
			-----------------------------"
	::= { ommp81PlusPerformanceEntry 220 }

	ommp81PlusFcTransmitFillWordDeletionCount OBJECT-TYPE
		SYNTAX  DisplayString
		MAX-ACCESS  read-only
		STATUS  current
		DESCRIPTION
			"For port configured with FC-100/FC-200 traffic,
			gives the count of number of fill words that were
			deleted for rate adaptation.
			-----------------------------
			ommp81PlusInterfaceNumber:
			1 to 8 - CLIENT-1 to CLIENT-8
			-----------------------------
			Values:
			eg: 1234
			-----------------------------"
	::= { ommp81PlusPerformanceEntry 221 }

	ommp81PlusFcTransmitPrimitiveSequenceDeletionCount OBJECT-TYPE
		SYNTAX  DisplayString
		MAX-ACCESS  read-only
		STATUS  current
		DESCRIPTION
			"For port configured with FC-100/FC-200 traffic,
			reports number of Primitive Signals or Sequence
			Functions that were deleted for rate adaptation.
			For fibre channel, each increment indicates the
			number of 4-character Primitive Sequences that were
			deleted.
			-----------------------------
			ommp81PlusInterfaceNumber:
			1 to 8 - CLIENT-1 to CLIENT-8
			-----------------------------
			Values:
			eg: 1234
			-----------------------------"
	::= { ommp81PlusPerformanceEntry 222 }

	ommp81PlusPerformanceTableRowStatus OBJECT-TYPE
              SYNTAX      RowStatus
              MAX-ACCESS  read-write
              STATUS      current
              DESCRIPTION
			"*****************************
			This is MIB realted property,
			NOT to be considered as a card property
			*****************************"
              ::= { ommp81PlusPerformanceEntry 223 }
              
--*****************************************************************************
--				    DIAGNOSTICS
--*****************************************************************************        

	ommp81PlusDiagnosticsTable OBJECT-TYPE
	      SYNTAX  SEQUENCE OF Ommp81PlusDiagnosticsEntry
              MAX-ACCESS  not-accessible
              STATUS  current
              DESCRIPTION
                      "Category contains properties that are used for debugging
                      card software"
		::= { ommp81PlusDiagnostics 1 }	

	ommp81PlusDiagnosticsEntry   OBJECT-TYPE
              SYNTAX  Ommp81PlusDiagnosticsEntry 
              MAX-ACCESS  not-accessible
              STATUS  current
              DESCRIPTION 
              	""
		INDEX   { node, rack , subRack , slot , ommp81PlusInterfaceNumber }
		::= { ommp81PlusDiagnosticsTable 1 }
	
	Ommp81PlusDiagnosticsEntry ::= 
		SEQUENCE {
				ommp81PlusAccessHyphyRegister			INTEGER,
				ommp81PlusCnodeCrashCount			INTEGER,
				ommp81PlusKernelState				DisplayString,
				ommp81PlusDiagnosticTableRowStatus		RowStatus
			}
			
	ommp81PlusAccessHyphyRegister OBJECT-TYPE
		SYNTAX  INTEGER
		MAX-ACCESS  read-write
		STATUS  current
		DESCRIPTION
			"Sets/gets the value of any hyphy register
			-----------------------------
			ommp81PlusInterfaceNumber: 0
			-----------------------------
			Values:
			eg:
			example of hyphy register - 76071076
			value - 1
			-----------------------------"
	::= { ommp81PlusDiagnosticsEntry 1 }

	ommp81PlusCnodeCrashCount OBJECT-TYPE
		SYNTAX  INTEGER
		MAX-ACCESS  read-only
		STATUS  current
		DESCRIPTION
			"Gets the count of number of times the hyphy_cnode has
			crashed
			-----------------------------
			ommp81PlusInterfaceNumber: 0
			-----------------------------
			Values: 
			eg: 0, 1, 4, 7 etc.
			-----------------------------"
	::= { ommp81PlusDiagnosticsEntry 2 }

	ommp81PlusKernelState OBJECT-TYPE
		SYNTAX  DisplayString
		MAX-ACCESS  read-only
		STATUS  current
		DESCRIPTION
			"Gets the state of the kernel
			-----------------------------
			ommp81PlusInterfaceNumber: 0
			-----------------------------
			Values:
			non-tainted - kernel is working fine
			tainted - kernel panic has occured
			-----------------------------"
	::= { ommp81PlusDiagnosticsEntry 3 }
	
	ommp81PlusDiagnosticTableRowStatus OBJECT-TYPE
              SYNTAX      RowStatus
              MAX-ACCESS  read-write
              STATUS      current
              DESCRIPTION
			"*****************************
			This is MIB realted property,
			NOT to be considered as a card property
			*****************************"
	::= { ommp81PlusDiagnosticsEntry 4 }

--*****************************************************************************

--*****************************************************************************

	snmpCurrentNotificationsGroup NOTIFICATION-GROUP
		NOTIFICATIONS { 
					ommp81PlusXfpInputPowerFailureAlarmTrap,
					ommp81PlusXfpOutputPowerFailureAlarmTrap,
					ommp81PlusXfpHighTemperatureAlarmTrap,
					ommp81PlusXfpLowTemperatureAlarmTrap,
					ommp81PlusXfpHighTemperatureWarningTrap,
					ommp81PlusXfpLowTemperatureWarningTrap,
					ommp81PlusXfpHighBiasCurrentAlarmTrap,
					ommp81PlusXfpLowBiasCurrentAlarmTrap,
					ommp81PlusXfpHighBiasCurrentWarningTrap,
					ommp81PlusXfpLowBiasCurrentWarningTrap,
					ommp81PlusXfpInputHighPowerAlarmTrap,
					ommp81PlusXfpInputLowPowerAlarmTrap,
					ommp81PlusXfpInputHighPowerWarningTrap,
					ommp81PlusXfpInputLowPowerWarningTrap,
					ommp81PlusXfpOutputHighPowerAlarmTrap,
					ommp81PlusXfpOutputLowPowerAlarmTrap,
					ommp81PlusXfpOutputHighPowerWarningTrap,
					ommp81PlusXfpOutputLowPowerWarningTrap,
					ommp81PlusXfpHighSupplyVoltageAlarmTrap,
					ommp81PlusXfpLowSupplyVoltageAlarmTrap,
					ommp81PlusXfpHighSupplyVoltageWarningTrap,
					ommp81PlusXfpLowSupplyVoltageWarningTrap,
					ommp81PlusXfpPresenceAbsenceNotificationTrap,
					ommp81PlusSfpInputPowerFailureAlarmTrap,
					ommp81PlusSfpOutputPowerFailureAlarmTrap,
					ommp81PlusSfpHighTemperatureAlarmTrap,
					ommp81PlusSfpLowTemperatureAlarmTrap,
					ommp81PlusSfpHighTemperatureWarningTrap,
					ommp81PlusSfpLowTemperatureWarningTrap,
					ommp81PlusSfpHighBiasCurrentAlarmTrap,
					ommp81PlusSfpLowBiasCurrentAlarmTrap,
					ommp81PlusSfpHighBiasCurrentWarningTrap,
					ommp81PlusSfpLowBiasCurrentWarningTrap,
					ommp81PlusSfpInputHighPowerAlarmTrap,
					ommp81PlusSfpInputLowPowerAlarmTrap,
					ommp81PlusSfpInputHighPowerWarningTrap,
					ommp81PlusSfpInputLowPowerWarningTrap,
					ommp81PlusSfpOutputHighPowerAlarmTrap,
					ommp81PlusSfpOutputLowPowerAlarmTrap,
					ommp81PlusSfpOutputHighPowerWarningTrap,
					ommp81PlusSfpOutputLowPowerWarningTrap,
					ommp81PlusSfpHighSupplyVoltageAlarmTrap,
					ommp81PlusSfpLowSupplyVoltageAlarmTrap,
					ommp81PlusSfpHighSupplyVoltageWarningTrap,
					ommp81PlusSfpLowSupplyVoltageWarningTrap,
					ommp81PlusSfpPresenceAbsenceNotificationTrap,
					ommp81PlusSfpTransmitFaultPresenceAlarmTrap,
					ommp81PlusOtuLossOfSignalAlarmTrap,
					ommp81PlusOtuLossOfFrameAlarmTrap,
					ommp81PlusOtuOutOfFrameAlarmTrap,
					ommp81PlusOtuLossOfMultiFrameAlarmTrap,
					ommp81PlusOtuOutOfMultiFrameAlarmTrap,
					ommp81PlusOtuSignalFailAlarmTrap,
					ommp81PlusOtuSignalDegradeAlarmTrap,
					ommp81PlusOtuAlarmIndicationSignalAlarmTrap,
					ommp81PlusOtuIncomingAlignmentErrorAlarmTrap,
					ommp81PlusOtuTraceIdentifierMismatchAlarmTrap,
					ommp81PlusOtuBackwardIncomingAlignmentErrorAlarmTrap,
					ommp81PlusOtuBackwardDefectIndicationAlarmTrap,
					ommp81PlusOduSignalFailAlarmTrap,
					ommp81PlusOduSignalDegradeAlarmTrap,
					ommp81PlusOduAlarmIndicationSignalAlarmTrap,
					ommp81PlusOduTcm1IncomingAlignmentErrorAlarmTrap,
					ommp81PlusOduTcm2IncomingAlignmentErrorAlarmTrap,
					ommp81PlusOduTcm3IncomingAlignmentErrorAlarmTrap,
					ommp81PlusOduTcm4IncomingAlignmentErrorAlarmTrap,
					ommp81PlusOduTcm5IncomingAlignmentErrorAlarmTrap,
					ommp81PlusOduTcm6IncomingAlignmentErrorAlarmTrap,
					ommp81PlusOduTraceIdentifierMismatchAlarmTrap,
					ommp81PlusOduLockedDefectAlarmTrap,
					ommp81PlusOduOpenConnectionIndicationAlarmTrap,
					ommp81PlusOduBackwardDefectIndicationAlarmTrap,
					ommp81PlusOduTcm1BackwardIncomingAlignmentErrorAlarmTrap,
					ommp81PlusOduTcm2BackwardIncomingAlignmentErrorAlarmTrap,
					ommp81PlusOduTcm3BackwardIncomingAlignmentErrorAlarmTrap,
					ommp81PlusOduTcm4BackwardIncomingAlignmentErrorAlarmTrap,
					ommp81PlusOduTcm5BackwardIncomingAlignmentErrorAlarmTrap,
					ommp81PlusOduTcm6BackwardIncomingAlignmentErrorAlarmTrap,
					ommp81PlusOduLossOfFrameLossOfMultiframeAlarmTrap,
					ommp81PlusOpuPayloadMismatchAlarmTrap,
					ommp81PlusOchLossOfPayloadAlarmTrap,
					ommp81PlusSdhLossOfSignalAlarmTrap,
					ommp81PlusSdhOutOfFrameAlarmTrap,
					ommp81PlusSdhLossOfFrameAlarmTrap,
					ommp81PlusSdhRsAlarmIndicationSignalAlarmTrap,
					ommp81PlusSdhRsTraceIdentifierMismatchAlarmTrap,
					ommp81PlusSdhAuAlarmIndicationSignalAlarmTrap,
					ommp81PlusSdhAuLossOfPointerAlarmTrap,
					ommp81PlusSdhMsAlarmIndicationSignalAlarmTrap,
					ommp81PlusSdhMsRemoteErrorIndicationAlarmTrap,
					ommp81PlusSdhMsRemoteDefectIndicationAlarmTrap,
					ommp81PlusSdhMsRemoteFailureIndicationAlarmTrap,
					ommp81PlusSdhMsB2ExcessiveErrorAlarmTrap,
					ommp81PlusSdhMsB2SignalDegradeAlarmTrap,
					ommp81PlusSdhLossOfSequenceSynchronisationAlarmTrap,
					ommp81PlusSdhLowerOrderPathPayloadLabelMismatchAlarmTrap,
					ommp81PlusSdhLowerOrderPathUnequippedAlarmTrap,
					ommp81PlusEthernetLossOfSignalAlarmTrap,
					ommp81PlusEthernetLossOfSignalSyncAlarmTrap,
					ommp81PlusEthernetLinkFailureAlarmTrap,
					ommp81PlusEthernetAutoNegotiationAlarmTrap,
					ommp81PlusEthernetFrameCheckSequenceAlarmTrap,
					ommp81PlusEthernetCarrierStatusAlarmTrap,
					ommp81PlusEthernetHighBerAlarmTrap,
					ommp81PlusEthernetLocalFaultAlarmTrap,
					ommp81PlusEthernetRemoteFaultAlarmTrap,
					ommp81PlusFcTransmitDisparityInversionDefectAlarmTrap,
					ommp81PlusFcTransmitDigitalLossOfLinkDefectAlarmTrap,
					ommp81PlusFcTrasnmitLossOfSynchronizationDefectAlarmTrap,
					ommp81PlusFcReceiveDigitalLossOfLinkDefectAlarmTrap,
					ommp81PlusFcReceiveLossOfSynchronizationDefectAlarmTrap,
					ommp81PlusFcReceiveTransitionDetectDefectAlarmTrap,
					ommp81PlusFcReceiveAnalogLossOfSignalDefectAlarmTrap,
					ommp81PlusFcReceiveLineCodeViolationDefectAlarmTrap,
					ommp81PlusGfpCsfSignalFailAlarmTrap,
					ommp81PlusGfpCsfLinkFailAlarmTrap,
					ommp81PlusGfpCoreHeaderErrorAlarmTrap,
					ommp81PlusGfpExtentionHeaderErrorAlarmTrap
				}
  	STATUS current
	DESCRIPTION
  	   	"The UTL OMMP81-PLUS current notifications group"
  	::= { ommp81Plus 6 }

            snmpcurrentGroup OBJECT-GROUP
    OBJECTS 	{ 
			ommp81PlusInterfaceNumber,	
    			ommp81PlusEepromCardId,
			ommp81PlusEepromCardName,
			ommp81PlusEepromPartCode,
			ommp81PlusEepromCardSerialNumber,
			ommp81PlusEepromHardwareExternalReleaseVersion,
			ommp81PlusSoftwareExternalReleaseVersion,
			ommp81PlusEepromHardwareInternalReleaseVersion,
			ommp81PlusSoftwareInternalReleaseVersion,
			ommp81PlusEepromCardUidNumber,
			ommp81PlusEepromCardEui48Number,
			ommp81PlusEepromCardEui64Number,
			ommp81PlusCardRootFileSystemVersion,
			ommp81PlusCardInstallationDate,
			ommp81PlusCardCommissionDate,
			ommp81PlusCardRunningTime,
			ommp81PlusCardRestartCount,
			ommp81PlusXfpReadyForOperation,
			ommp81PlusXfpI2cCommunicationStatus,
			ommp81PlusXfpEepromPage,
			ommp81PlusCheckCodeOfXfpEepromPage,
			ommp81PlusExtendedCheckCodeOfXfpEepromPage,
			ommp81PlusXfpVendorName,
			ommp81PlusXfpVendorIeeeId,
			ommp81PlusXfpPartNumber,
			ommp81PlusXfpSerialNumber,
			ommp81PlusXfpRevisionNumber,
			ommp81PlusXfpManufacturingDate,
			ommp81PlusFixedXfpLaserWavelength,
			ommp81PlusXfpLaserWavelengthTolerance,
			ommp81PlusXfpWavelengthTunabilitySupported,
			ommp81PlusTunableXfpLaserWavelengthError,
			ommp81PlusTunableXfpLaserFrequencyError,
			ommp81PlusTunableXfpLaserFirstFrequency,
			ommp81PlusTunableXfpLaserLastFrequency,
			ommp81PlusTunableXfpWavelengthGridSpacing,
			ommp81PlusXfpConnectorType,
			ommp81PlusXfpLinkLength,
			ommp81PlusXfpCdrRateSupported,
			ommp81PlusXfpSignalEncodingTypeSupported,
			ommp81PlusXfpTransceiverCodesSupported,
			ommp81PlusXfpMaximumBitrateSupported,
			ommp81PlusXfpMinimumBitrateSupported,
			ommp81PlusXfpMaximumCaseTemperatureSupported,
			ommp81PlusXfpMaximumPowerDissipationSupported,
			ommp81PlusXfpMaximumPowerDissipationSupportedAtPowerDownMode,
			ommp81PlusXfpMaximumCurrentLimitSupportedAtPlus5vSupply,
			ommp81PlusXfpMaximumCurrentLimitSupportedAtPlus3Point3vSupply,
			ommp81PlusXfpMaximumCurrentLimitSupportedAtPlus1Point8vSupply,
			ommp81PlusXfpMaximumCurrentLimitSupportedAtMinus5Point2vSupply,
			ommp81PlusXfpLineLoopbackSupported,
			ommp81PlusXfpXfiLoopbackSupported,
			ommp81PlusXfpOptionalVpsSupported,
			ommp81PlusXfpLaserDisableThroughI2cSupported,
			ommp81PlusXfpPowerDownThroughI2cSupported,
			ommp81PlusXfpVpsLvRegulatorModeSupported,
			ommp81PlusXfpVpsBypassedRegulatorModeSupported,
			ommp81PlusXfpActiveFecControlSupported,
			ommp81PlusXfpOptionalCmuModeSupported,
			ommp81PlusXfpFecBerSupported,
			ommp81PlusXfpReceivePowerMeasurementIsInOmaOrAverage,
			ommp81PlusXfpActiveWavelengthControlSupported,
			ommp81PlusXfpTransmitterIsCooledOrUncooled,
			ommp81PlusXfpReceiverTypeIsPinOrApd,
			ommp81PlusSfpEepromPage,
			ommp81PlusCheckCodeOfSfpEepromPage,
			ommp81PlusExtendedCheckCodeOfSfpEepromPage,
			ommp81PlusSfpVendorName,
			ommp81PlusSfpVendorIeeeId,
			ommp81PlusSfpPartNumber,
			ommp81PlusSfpSerialNumber,
			ommp81PlusSfpRevisionNumber,
			ommp81PlusSfpManufacturingDate,
			ommp81PlusFixedSfpLaserWavelength,
			ommp81PlusSfpConnectorType,
			ommp81PlusSfpLinkLength,
			ommp81PlusSfpSignalEncodingTypeSupported,
			ommp81PlusSfpTransceiverCodesSupported,
			ommp81PlusSfpMaximumBitrateSupported,
			ommp81PlusSfpNominalBitrateSupported,
			ommp81PlusSfpMinimumBitrateSupported,
			ommp81PlusCardGeneralDetailsTableRowStatus,
			ommp81PlusCardSoftwareUpgrade,
			ommp81PlusCardSignalMonitorState,
			ommp81PlusCardOpticalMonitorState,
			ommp81PlusCardSoftReset,
			ommp81PlusCardFactoryReset,
			ommp81PlusCardAccessStatus,
			ommp81PlusSyncSystemTimeWithNtpServer,
			ommp81PlusSyncRtcWithNtpServer,
			ommp81PlusSyncRtcWithSystemTime,
			ommp81PlusUpdateGivenTimeIntoSystem,
			ommp81PlusUpdateGivenTimeIntoRtc,
			ommp81PlusSystemTimeAndRtcTime,
			ommp81PlusTrafficConfiguration,
			ommp81PlusLoopbackState,
			ommp81PlusPortSignalMonitorState,
			ommp81PlusPortOpticalMonitorState,
			ommp81PlusClearSignalPerformance,
			ommp81PlusAlsState,
			ommp81PlusAlsPulseRepetitionTime,
			ommp81PlusOtuFecConfiguration,
			ommp81PlusOtuSignalFailThreshold,
			ommp81PlusOtuSignalDegradeThreshold,
			ommp81PlusOtuAlarmIndicationSignalAlarmInsertion,
			ommp81PlusOtuSapiTransmitTraceMessage,
			ommp81PlusOtuDapiTransmitTraceMessage,
			ommp81PlusOtuOperatorSpecificTransmitTraceMessage,
			ommp81PlusOtuSapiExpectedTraceMessage,
			ommp81PlusOtuDapiExpectedTraceMessage,
			ommp81PlusOtuOperatorSpecificExpectedTraceMessage,
			ommp81PlusOtuSapiReceivedTraceMessage,
			ommp81PlusOtuDapiReceivedTraceMessage,
			ommp81PlusOtuOperatorSpecificReceivedTraceMessage,
			ommp81PlusOduSignalFailThreshold,
			ommp81PlusOduSignalDegradeThreshold,
			ommp81PlusOduAlarmIndicationSignalAlarmInsertion,
			ommp81PlusOduLockedDefectAlarmInsertion,
			ommp81PlusOduOpenConnectionIndicationAlarmInsertion,
			ommp81PlusOduSapiTransmitTraceMessage,
			ommp81PlusOduDapiTransmitTraceMessage,
			ommp81PlusOduOperatorSpecificTransmitTraceMessage,
			ommp81PlusOduSapiExpectedTraceMessage,
			ommp81PlusOduDapiExpectedTraceMessage,
			ommp81PlusOduOperatorSpecificExpectedTraceMessage,
			ommp81PlusOduSapiReceivedTraceMessage,
			ommp81PlusOduDapiReceivedTraceMessage,
			ommp81PlusOduOperatorSpecificReceivedTraceMessage,
			ommp81PlusOpuTransmitPayloadType,
			ommp81PlusOpuReceivedPayloadType,
			ommp81PlusSdhMsB2ExcessiveErrorThreshold,
			ommp81PlusSdhMsB2SignalDegradeThreshold,
			ommp81PlusEthernetAutoNegotiation,
			ommp81PlusCalibrateHyphyXfiSerdes,
			ommp81PlusTunableXfpLaserWavelength,
			ommp81PlusTunableXfpLaserChannelNumber,
			ommp81PlusXfpLaserState,
			ommp81PlusXfpReset,
			ommp81PlusXfpPowerDownMode,
			ommp81PlusXfpLineLoopback,
			ommp81PlusXfpXfiLoopback,
			ommp81PlusXfpAmplitudeThresholdOfReceiverForFecControl,
			ommp81PlusXfpPhaseInEyeDiagramForFecControl,
			ommp81PlusXfpSystemReportingBer,
			ommp81PlusXfpHighTemperatureAlarmThreshold,
			ommp81PlusXfpLowTemperatureAlarmThreshold,
			ommp81PlusXfpHighTemperatureWarningThreshold,
			ommp81PlusXfpLowTemperatureWarningThreshold,
			ommp81PlusXfpHighBiasCurrentAlarmThreshold,
			ommp81PlusXfpLowBiasCurrentAlarmThreshold,
			ommp81PlusXfpHighBiasCurrentWarningThreshold,
			ommp81PlusXfpLowBiasCurrentWarningThreshold,
			ommp81PlusXfpInputHighPowerAlarmThreshold,
			ommp81PlusXfpInputLowPowerAlarmThreshold,
			ommp81PlusXfpInputHighPowerWarningThreshold,
			ommp81PlusXfpInputLowPowerWarningThreshold,
			ommp81PlusXfpOutputHighPowerAlarmThreshold,
			ommp81PlusXfpOutputLowPowerAlarmThreshold,
			ommp81PlusXfpOutputHighPowerWarningThreshold,
			ommp81PlusXfpOutputLowPowerWarningThreshold,
			ommp81PlusXfpHighSupplyVoltageAlarmThreshold,
			ommp81PlusXfpLowSupplyVoltageAlarmThreshold,
			ommp81PlusXfpHighSupplyVoltageWarningThreshold,
			ommp81PlusXfpLowSupplyVoltageWarningThreshold,
			ommp81PlusSfpLaserState,
			ommp81PlusSfpHighTemperatureAlarmThreshold,
			ommp81PlusSfpLowTemperatureAlarmThreshold,
			ommp81PlusSfpHighTemperatureWarningThreshold,
			ommp81PlusSfpLowTemperatureWarningThreshold,
			ommp81PlusSfpHighBiasCurrentAlarmThreshold,
			ommp81PlusSfpLowBiasCurrentAlarmThreshold,
			ommp81PlusSfpHighBiasCurrentWarningThreshold,
			ommp81PlusSfpLowBiasCurrentWarningThreshold,
			ommp81PlusSfpInputHighPowerAlarmThreshold,
			ommp81PlusSfpInputLowPowerAlarmThreshold,
			ommp81PlusSfpInputHighPowerWarningThreshold,
			ommp81PlusSfpInputLowPowerWarningThreshold,
			ommp81PlusSfpOutputHighPowerAlarmThreshold,
			ommp81PlusSfpOutputLowPowerAlarmThreshold,
			ommp81PlusSfpOutputHighPowerWarningThreshold,
			ommp81PlusSfpOutputLowPowerWarningThreshold,
			ommp81PlusSfpHighSupplyVoltageAlarmThreshold,
			ommp81PlusSfpLowSupplyVoltageAlarmThreshold,
			ommp81PlusSfpHighSupplyVoltageWarningThreshold,
			ommp81PlusSfpLowSupplyVoltageWarningThreshold,
			ommp81PlusXfpInputPowerFailureAlarmInhibit,
			ommp81PlusXfpOutputPowerFailureAlarmInhibit,
			ommp81PlusXfpHighTemperatureAlarmInhibit,
			ommp81PlusXfpLowTemperatureAlarmInhibit,
			ommp81PlusXfpHighTemperatureWarningInhibit,
			ommp81PlusXfpLowTemperatureWarningInhibit,
			ommp81PlusXfpHighBiasCurrentAlarmInhibit,
			ommp81PlusXfpLowBiasCurrentAlarmInhibit,
			ommp81PlusXfpHighBiasCurrentWarningInhibit,
			ommp81PlusXfpLowBiasCurrentWarningInhibit,
			ommp81PlusXfpInputHighPowerAlarmInhibit,
			ommp81PlusXfpInputLowPowerAlarmInhibit,
			ommp81PlusXfpInputHighPowerWarningInhibit,
			ommp81PlusXfpInputLowPowerWarningInhibit,
			ommp81PlusXfpOutputHighPowerAlarmInhibit,
			ommp81PlusXfpOutputLowPowerAlarmInhibit,
			ommp81PlusXfpOutputHighPowerWarningInhibit,
			ommp81PlusXfpOutputLowPowerWarningInhibit,
			ommp81PlusXfpHighSupplyVoltageAlarmInhibit,
			ommp81PlusXfpLowSupplyVoltageAlarmInhibit,
			ommp81PlusXfpHighSupplyVoltageWarningInhibit,
			ommp81PlusXfpLowSupplyVoltageWarningInhibit,
			ommp81PlusXfpPresenceAbsenceNotificationInhibit,
			ommp81PlusSfpInputPowerFailureAlarmInhibit,
			ommp81PlusSfpOutputPowerFailureAlarmInhibit,
			ommp81PlusSfpHighTemperatureAlarmInhibit,
			ommp81PlusSfpLowTemperatureAlarmInhibit,
			ommp81PlusSfpHighTemperatureWarningInhibit,
			ommp81PlusSfpLowTemperatureWarningInhibit,
			ommp81PlusSfpHighBiasCurrentAlarmInhibit,
			ommp81PlusSfpLowBiasCurrentAlarmInhibit,
			ommp81PlusSfpHighBiasCurrentWarningInhibit,
			ommp81PlusSfpLowBiasCurrentWarningInhibit,
			ommp81PlusSfpInputHighPowerAlarmInhibit,
			ommp81PlusSfpInputLowPowerAlarmInhibit,
			ommp81PlusSfpInputHighPowerWarningInhibit,
			ommp81PlusSfpInputLowPowerWarningInhibit,
			ommp81PlusSfpOutputHighPowerAlarmInhibit,
			ommp81PlusSfpOutputLowPowerAlarmInhibit,
			ommp81PlusSfpOutputHighPowerWarningInhibit,
			ommp81PlusSfpOutputLowPowerWarningInhibit,
			ommp81PlusSfpHighSupplyVoltageAlarmInhibit,
			ommp81PlusSfpLowSupplyVoltageAlarmInhibit,
			ommp81PlusSfpHighSupplyVoltageWarningInhibit,
			ommp81PlusSfpLowSupplyVoltageWarningInhibit,
			ommp81PlusSfpPresenceAbsenceNotificationInhibit,
			ommp81PlusSfpTransmitFaultPresenceAlarmInhibit,
			ommp81PlusOtuLossOfSignalAlarmInhibit,
			ommp81PlusOtuLossOfFrameAlarmInhibit,
			ommp81PlusOtuOutOfFrameAlarmInhibit,
			ommp81PlusOtuLossOfMultiFrameAlarmInhibit,
			ommp81PlusOtuOutOfMultiFrameAlarmInhibit,
			ommp81PlusOtuSignalFailAlarmInhibit,
			ommp81PlusOtuSignalDegradeAlarmInhibit,
			ommp81PlusOtuAlarmIndicationSignalAlarmInhibit,
			ommp81PlusOtuIncomingAlignmentErrorAlarmInhibit,
			ommp81PlusOtuTraceIdentifierMismatchAlarmInhibit,
			ommp81PlusOtuBackwardIncomingAlignmentErrorAlarmInhibit,
			ommp81PlusOtuBackwardDefectIndicationAlarmInhibit,
			ommp81PlusOduSignalFailAlarmInhibit,
			ommp81PlusOduSignalDegradeAlarmInhibit,
			ommp81PlusOduAlarmIndicationSignalAlarmInhibit,
			ommp81PlusOduTcm1IncomingAlignmentErrorAlarmInhibit,
			ommp81PlusOduTcm2IncomingAlignmentErrorAlarmInhibit,
			ommp81PlusOduTcm3IncomingAlignmentErrorAlarmInhibit,
			ommp81PlusOduTcm4IncomingAlignmentErrorAlarmInhibit,
			ommp81PlusOduTcm5IncomingAlignmentErrorAlarmInhibit,
			ommp81PlusOduTcm6IncomingAlignmentErrorAlarmInhibit,
			ommp81PlusOduTraceIdentifierMismatchAlarmInhibit,
			ommp81PlusOduLockedDefectAlarmInhibit,
			ommp81PlusOduOpenConnectionIndicationAlarmInhibit,
			ommp81PlusOduBackwardDefectIndicationAlarmInhibit,
			ommp81PlusOduTcm1BackwardIncomingAlignmentErrorAlarmInhibit,
			ommp81PlusOduTcm2BackwardIncomingAlignmentErrorAlarmInhibit,
			ommp81PlusOduTcm3BackwardIncomingAlignmentErrorAlarmInhibit,
			ommp81PlusOduTcm4BackwardIncomingAlignmentErrorAlarmInhibit,
			ommp81PlusOduTcm5BackwardIncomingAlignmentErrorAlarmInhibit,
			ommp81PlusOduTcm6BackwardIncomingAlignmentErrorAlarmInhibit,
			ommp81PlusOduLossOfFrameLossOfMultiframeAlarmInhibit,
			ommp81PlusOpuPayloadMismatchAlarmInhibit,
			ommp81PlusOchLossOfPayloadAlarmInhibit,
			ommp81PlusSdhLossOfSignalAlarmInhibit,
			ommp81PlusSdhOutOfFrameAlarmInhibit,
			ommp81PlusSdhLossOfFrameAlarmInhibit,
			ommp81PlusSdhRsAlarmIndicationSignalAlarmInhibit,
			ommp81PlusSdhRsTraceIdentifierMismatchAlarmInhibit,
			ommp81PlusSdhAuAlarmIndicationSignalAlarmInhibit,
			ommp81PlusSdhAuLossOfPointerAlarmInhibit,
			ommp81PlusSdhMsAlarmIndicationSignalAlarmInhibit,
			ommp81PlusSdhMsRemoteErrorIndicationAlarmInhibit,
			ommp81PlusSdhMsRemoteDefectIndicationAlarmInhibit,
			ommp81PlusSdhMsRemoteFailureIndicationAlarmInhibit,
			ommp81PlusSdhMsB2ExcessiveErrorAlarmInhibit,
			ommp81PlusSdhMsB2SignalDegradeAlarmInhibit,
			ommp81PlusSdhLossOfSequenceSynchronisationAlarmInhibit,
			ommp81PlusSdhLowerOrderPathPayloadLabelMismatchAlarmInhibit,
			ommp81PlusSdhLowerOrderPathUnequippedAlarmInhibit,
			ommp81PlusEthernetLossOfSignalAlarmInhibit,
			ommp81PlusEthernetLossOfSignalSyncAlarmInhibit,
			ommp81PlusEthernetLinkFailureAlarmInhibit,
			ommp81PlusEthernetAutoNegotiationAlarmInhibit,
			ommp81PlusEthernetFrameCheckSequenceAlarmInhibit,
			ommp81PlusEthernetCarrierStatusAlarmInhibit,
			ommp81PlusEthernetHighBerAlarmInhibit,
			ommp81PlusEthernetLocalFaultAlarmInhibit,
			ommp81PlusEthernetRemoteFaultAlarmInhibit,
			ommp81PlusFcTransmitDisparityInversionDefectAlarmInhibit,
			ommp81PlusFcTransmitDigitalLossOfLinkDefectAlarmInhibit,
			ommp81PlusFcTrasnmitLossOfSynchronizationDefectAlarmInhibit,
			ommp81PlusFcReceiveDigitalLossOfLinkDefectAlarmInhibit,
			ommp81PlusFcReceiveLossOfSynchronizationDefectAlarmInhibit,
			ommp81PlusFcReceiveTransitionDetectDefectAlarmInhibit,
			ommp81PlusFcReceiveAnalogLossOfSignalDefectAlarmInhibit,
			ommp81PlusFcReceiveLineCodeViolationDefectAlarmInhibit,
			ommp81PlusGfpCsfSignalFailAlarmInhibit,
			ommp81PlusGfpCsfLinkFailAlarmInhibit,
			ommp81PlusGfpCoreHeaderErrorAlarmInhibit,
			ommp81PlusGfpExtentionHeaderErrorAlarmInhibit,
			ommp81PlusXfpInputPowerFailureAlarmSeverity,
			ommp81PlusXfpOutputPowerFailureAlarmSeverity,
			ommp81PlusXfpHighTemperatureAlarmSeverity,
			ommp81PlusXfpLowTemperatureAlarmSeverity,
			ommp81PlusXfpHighTemperatureWarningSeverity,
			ommp81PlusXfpLowTemperatureWarningSeverity,
			ommp81PlusXfpHighBiasCurrentAlarmSeverity,
			ommp81PlusXfpLowBiasCurrentAlarmSeverity,
			ommp81PlusXfpHighBiasCurrentWarningSeverity,
			ommp81PlusXfpLowBiasCurrentWarningSeverity,
			ommp81PlusXfpInputHighPowerAlarmSeverity,
			ommp81PlusXfpInputLowPowerAlarmSeverity,
			ommp81PlusXfpInputHighPowerWarningSeverity,
			ommp81PlusXfpInputLowPowerWarningSeverity,
			ommp81PlusXfpOutputHighPowerAlarmSeverity,
			ommp81PlusXfpOutputLowPowerAlarmSeverity,
			ommp81PlusXfpOutputHighPowerWarningSeverity,
			ommp81PlusXfpOutputLowPowerWarningSeverity,
			ommp81PlusXfpHighSupplyVoltageAlarmSeverity,
			ommp81PlusXfpLowSupplyVoltageAlarmSeverity,
			ommp81PlusXfpHighSupplyVoltageWarningSeverity,
			ommp81PlusXfpLowSupplyVoltageWarningSeverity,
			ommp81PlusXfpPresenceAbsenceNotificationSeverity,
			ommp81PlusSfpInputPowerFailureAlarmSeverity,
			ommp81PlusSfpOutputPowerFailureAlarmSeverity,
			ommp81PlusSfpHighTemperatureAlarmSeverity,
			ommp81PlusSfpLowTemperatureAlarmSeverity,
			ommp81PlusSfpHighTemperatureWarningSeverity,
			ommp81PlusSfpLowTemperatureWarningSeverity,
			ommp81PlusSfpHighBiasCurrentAlarmSeverity,
			ommp81PlusSfpLowBiasCurrentAlarmSeverity,
			ommp81PlusSfpHighBiasCurrentWarningSeverity,
			ommp81PlusSfpLowBiasCurrentWarningSeverity,
			ommp81PlusSfpInputHighPowerAlarmSeverity,
			ommp81PlusSfpInputLowPowerAlarmSeverity,
			ommp81PlusSfpInputHighPowerWarningSeverity,
			ommp81PlusSfpInputLowPowerWarningSeverity,
			ommp81PlusSfpOutputHighPowerAlarmSeverity,
			ommp81PlusSfpOutputLowPowerAlarmSeverity,
			ommp81PlusSfpOutputHighPowerWarningSeverity,
			ommp81PlusSfpOutputLowPowerWarningSeverity,
			ommp81PlusSfpHighSupplyVoltageAlarmSeverity,
			ommp81PlusSfpLowSupplyVoltageAlarmSeverity,
			ommp81PlusSfpHighSupplyVoltageWarningSeverity,
			ommp81PlusSfpLowSupplyVoltageWarningSeverity,
			ommp81PlusSfpPresenceAbsenceNotificationSeverity,
			ommp81PlusSfpTransmitFaultPresenceAlarmSeverity,
			ommp81PlusOtuLossOfSignalAlarmSeverity,
			ommp81PlusOtuLossOfFrameAlarmSeverity,
			ommp81PlusOtuOutOfFrameAlarmSeverity,
			ommp81PlusOtuLossOfMultiFrameAlarmSeverity,
			ommp81PlusOtuOutOfMultiFrameAlarmSeverity,
			ommp81PlusOtuSignalFailAlarmSeverity,
			ommp81PlusOtuSignalDegradeAlarmSeverity,
			ommp81PlusOtuAlarmIndicationSignalAlarmSeverity,
			ommp81PlusOtuIncomingAlignmentErrorAlarmSeverity,
			ommp81PlusOtuTraceIdentifierMismatchAlarmSeverity,
			ommp81PlusOtuBackwardIncomingAlignmentErrorAlarmSeverity,
			ommp81PlusOtuBackwardDefectIndicationAlarmSeverity,
			ommp81PlusOduSignalFailAlarmSeverity,
			ommp81PlusOduSignalDegradeAlarmSeverity,
			ommp81PlusOduAlarmIndicationSignalAlarmSeverity,
			ommp81PlusOduTcm1IncomingAlignmentErrorAlarmSeverity,
			ommp81PlusOduTcm2IncomingAlignmentErrorAlarmSeverity,
			ommp81PlusOduTcm3IncomingAlignmentErrorAlarmSeverity,
			ommp81PlusOduTcm4IncomingAlignmentErrorAlarmSeverity,
			ommp81PlusOduTcm5IncomingAlignmentErrorAlarmSeverity,
			ommp81PlusOduTcm6IncomingAlignmentErrorAlarmSeverity,
			ommp81PlusOduTraceIdentifierMismatchAlarmSeverity,
			ommp81PlusOduLockedDefectAlarmSeverity,
			ommp81PlusOduOpenConnectionIndicationAlarmSeverity,
			ommp81PlusOduBackwardDefectIndicationAlarmSeverity,
			ommp81PlusOduTcm1BackwardIncomingAlignmentErrorAlarmSeverity,
			ommp81PlusOduTcm2BackwardIncomingAlignmentErrorAlarmSeverity,
			ommp81PlusOduTcm3BackwardIncomingAlignmentErrorAlarmSeverity,
			ommp81PlusOduTcm4BackwardIncomingAlignmentErrorAlarmSeverity,
			ommp81PlusOduTcm5BackwardIncomingAlignmentErrorAlarmSeverity,
			ommp81PlusOduTcm6BackwardIncomingAlignmentErrorAlarmSeverity,
			ommp81PlusOduLossOfFrameLossOfMultiframeAlarmSeverity,
			ommp81PlusOpuPayloadMismatchAlarmSeverity,
			ommp81PlusOchLossOfPayloadAlarmSeverity,
			ommp81PlusSdhLossOfSignalAlarmSeverity,
			ommp81PlusSdhOutOfFrameAlarmSeverity,
			ommp81PlusSdhLossOfFrameAlarmSeverity,
			ommp81PlusSdhRsAlarmIndicationSignalAlarmSeverity,
			ommp81PlusSdhRsTraceIdentifierMismatchAlarmSeverity,
			ommp81PlusSdhAuAlarmIndicationSignalAlarmSeverity,
			ommp81PlusSdhAuLossOfPointerAlarmSeverity,
			ommp81PlusSdhMsAlarmIndicationSignalAlarmSeverity,
			ommp81PlusSdhMsRemoteErrorIndicationAlarmSeverity,
			ommp81PlusSdhMsRemoteDefectIndicationAlarmSeverity,
			ommp81PlusSdhMsRemoteFailureIndicationAlarmSeverity,
			ommp81PlusSdhMsB2ExcessiveErrorAlarmSeverity,
			ommp81PlusSdhMsB2SignalDegradeAlarmSeverity,
			ommp81PlusSdhLossOfSequenceSynchronisationAlarmSeverity,
			ommp81PlusSdhLowerOrderPathPayloadLabelMismatchAlarmSeverity,
			ommp81PlusSdhLowerOrderPathUnequippedAlarmSeverity,
			ommp81PlusEthernetLossOfSignalAlarmSeverity,
			ommp81PlusEthernetLossOfSignalSyncAlarmSeverity,
			ommp81PlusEthernetLinkFailureAlarmSeverity,
			ommp81PlusEthernetAutoNegotiationAlarmSeverity,
			ommp81PlusEthernetFrameCheckSequenceAlarmSeverity,
			ommp81PlusEthernetCarrierStatusAlarmSeverity,
			ommp81PlusEthernetHighBerAlarmSeverity,
			ommp81PlusEthernetLocalFaultAlarmSeverity,
			ommp81PlusEthernetRemoteFaultAlarmSeverity,
			ommp81PlusFcTransmitDisparityInversionDefectAlarmSeverity,
			ommp81PlusFcTransmitDigitalLossOfLinkDefectAlarmSeverity,
			ommp81PlusFcTrasnmitLossOfSynchronizationDefectAlarmSeverity,
			ommp81PlusFcReceiveDigitalLossOfLinkDefectAlarmSeverity,
			ommp81PlusFcReceiveLossOfSynchronizationDefectAlarmSeverity,
			ommp81PlusFcReceiveTransitionDetectDefectAlarmSeverity,
			ommp81PlusFcReceiveAnalogLossOfSignalDefectAlarmSeverity,
			ommp81PlusFcReceiveLineCodeViolationDefectAlarmSeverity,
			ommp81PlusGfpCsfSignalFailAlarmSeverity,
			ommp81PlusGfpCsfLinkFailAlarmSeverity,
			ommp81PlusGfpCoreHeaderErrorAlarmSeverity,
			ommp81PlusGfpExtentionHeaderErrorAlarmSeverity,
			ommp81PlusConfigurationTableRowStatus,
			ommp81PlusXfpInputPowerFailureAlarm,
			ommp81PlusXfpOutputPowerFailureAlarm,
			ommp81PlusXfpHighTemperatureAlarm,
			ommp81PlusXfpLowTemperatureAlarm,
			ommp81PlusXfpHighTemperatureWarning,
			ommp81PlusXfpLowTemperatureWarning,
			ommp81PlusXfpHighBiasCurrentAlarm,
			ommp81PlusXfpLowBiasCurrentAlarm,
			ommp81PlusXfpHighBiasCurrentWarning,
			ommp81PlusXfpLowBiasCurrentWarning,
			ommp81PlusXfpInputHighPowerAlarm,
			ommp81PlusXfpInputLowPowerAlarm,
			ommp81PlusXfpInputHighPowerWarning,
			ommp81PlusXfpInputLowPowerWarning,
			ommp81PlusXfpOutputHighPowerAlarm,
			ommp81PlusXfpOutputLowPowerAlarm,
			ommp81PlusXfpOutputHighPowerWarning,
			ommp81PlusXfpOutputLowPowerWarning,
			ommp81PlusXfpHighSupplyVoltageAlarm,
			ommp81PlusXfpLowSupplyVoltageAlarm,
			ommp81PlusXfpHighSupplyVoltageWarning,
			ommp81PlusXfpLowSupplyVoltageWarning,
			ommp81PlusXfpPresenceAbsenceNotification,
			ommp81PlusSfpInputPowerFailureAlarm,
			ommp81PlusSfpOutputPowerFailureAlarm,
			ommp81PlusSfpHighTemperatureAlarm,
			ommp81PlusSfpLowTemperatureAlarm,
			ommp81PlusSfpHighTemperatureWarning,
			ommp81PlusSfpLowTemperatureWarning,
			ommp81PlusSfpHighBiasCurrentAlarm,
			ommp81PlusSfpLowBiasCurrentAlarm,
			ommp81PlusSfpHighBiasCurrentWarning,
			ommp81PlusSfpLowBiasCurrentWarning,
			ommp81PlusSfpInputHighPowerAlarm,
			ommp81PlusSfpInputLowPowerAlarm,
			ommp81PlusSfpInputHighPowerWarning,
			ommp81PlusSfpInputLowPowerWarning,
			ommp81PlusSfpOutputHighPowerAlarm,
			ommp81PlusSfpOutputLowPowerAlarm,
			ommp81PlusSfpOutputHighPowerWarning,
			ommp81PlusSfpOutputLowPowerWarning,
			ommp81PlusSfpHighSupplyVoltageAlarm,
			ommp81PlusSfpLowSupplyVoltageAlarm,
			ommp81PlusSfpHighSupplyVoltageWarning,
			ommp81PlusSfpLowSupplyVoltageWarning,
			ommp81PlusSfpPresenceAbsenceNotification,
			ommp81PlusSfpTransmitFaultPresenceAlarm,
			ommp81PlusOtuLossOfSignalAlarm,
			ommp81PlusOtuLossOfFrameAlarm,
			ommp81PlusOtuOutOfFrameAlarm,
			ommp81PlusOtuLossOfMultiFrameAlarm,
			ommp81PlusOtuOutOfMultiFrameAlarm,
			ommp81PlusOtuSignalFailAlarm,
			ommp81PlusOtuSignalDegradeAlarm,
			ommp81PlusOtuAlarmIndicationSignalAlarm,
			ommp81PlusOtuIncomingAlignmentErrorAlarm,
			ommp81PlusOtuTraceIdentifierMismatchAlarm,
			ommp81PlusOtuBackwardIncomingAlignmentErrorAlarm,
			ommp81PlusOtuBackwardDefectIndicationAlarm,
			ommp81PlusOduSignalFailAlarm,
			ommp81PlusOduSignalDegradeAlarm,
			ommp81PlusOduAlarmIndicationSignalAlarm,
			ommp81PlusOduTcm1IncomingAlignmentErrorAlarm,
			ommp81PlusOduTcm2IncomingAlignmentErrorAlarm,
			ommp81PlusOduTcm3IncomingAlignmentErrorAlarm,
			ommp81PlusOduTcm4IncomingAlignmentErrorAlarm,
			ommp81PlusOduTcm5IncomingAlignmentErrorAlarm,
			ommp81PlusOduTcm6IncomingAlignmentErrorAlarm,
			ommp81PlusOduTraceIdentifierMismatchAlarm,
			ommp81PlusOduLockedDefectAlarm,
			ommp81PlusOduOpenConnectionIndicationAlarm,
			ommp81PlusOduBackwardDefectIndicationAlarm,
			ommp81PlusOduTcm1BackwardIncomingAlignmentErrorAlarm,
			ommp81PlusOduTcm2BackwardIncomingAlignmentErrorAlarm,
			ommp81PlusOduTcm3BackwardIncomingAlignmentErrorAlarm,
			ommp81PlusOduTcm4BackwardIncomingAlignmentErrorAlarm,
			ommp81PlusOduTcm5BackwardIncomingAlignmentErrorAlarm,
			ommp81PlusOduTcm6BackwardIncomingAlignmentErrorAlarm,
			ommp81PlusOduLossOfFrameLossOfMultiframeAlarm,
			ommp81PlusOpuPayloadMismatchAlarm,
			ommp81PlusOchLossOfPayloadAlarm,
			ommp81PlusSdhLossOfSignalAlarm,
			ommp81PlusSdhOutOfFrameAlarm,
			ommp81PlusSdhLossOfFrameAlarm,
			ommp81PlusSdhRsAlarmIndicationSignalAlarm,
			ommp81PlusSdhRsTraceIdentifierMismatchAlarm,
			ommp81PlusSdhAuAlarmIndicationSignalAlarm,
			ommp81PlusSdhAuLossOfPointerAlarm,
			ommp81PlusSdhMsAlarmIndicationSignalAlarm,
			ommp81PlusSdhMsRemoteErrorIndicationAlarm,
			ommp81PlusSdhMsRemoteDefectIndicationAlarm,
			ommp81PlusSdhMsRemoteFailureIndicationAlarm,
			ommp81PlusSdhMsB2ExcessiveErrorAlarm,
			ommp81PlusSdhMsB2SignalDegradeAlarm,
			ommp81PlusSdhLossOfSequenceSynchronisationAlarm,
			ommp81PlusSdhLowerOrderPathPayloadLabelMismatchAlarm,
			ommp81PlusSdhLowerOrderPathUnequippedAlarm,
			ommp81PlusEthernetLossOfSignalAlarm,
			ommp81PlusEthernetLossOfSignalSyncAlarm,
			ommp81PlusEthernetLinkFailureAlarm,
			ommp81PlusEthernetAutoNegotiationAlarm,
			ommp81PlusEthernetFrameCheckSequenceAlarm,
			ommp81PlusEthernetCarrierStatusAlarm,
			ommp81PlusEthernetHighBerAlarm,
			ommp81PlusEthernetLocalFaultAlarm,
			ommp81PlusEthernetRemoteFaultAlarm,
			ommp81PlusFcTransmitDisparityInversionDefectAlarm,
			ommp81PlusFcTransmitDigitalLossOfLinkDefectAlarm,
			ommp81PlusFcTrasnmitLossOfSynchronizationDefectAlarm,
			ommp81PlusFcReceiveDigitalLossOfLinkDefectAlarm,
			ommp81PlusFcReceiveLossOfSynchronizationDefectAlarm,
			ommp81PlusFcReceiveTransitionDetectDefectAlarm,
			ommp81PlusFcReceiveAnalogLossOfSignalDefectAlarm,
			ommp81PlusFcReceiveLineCodeViolationDefectAlarm,
			ommp81PlusGfpCsfSignalFailAlarm,
			ommp81PlusGfpCsfLinkFailAlarm,
			ommp81PlusGfpCoreHeaderErrorAlarm,
			ommp81PlusGfpExtentionHeaderErrorAlarm,
			ommp81PlusAlarmQueryTableRowStatus,
			ommp81PlusXfpInputPower,
			ommp81PlusXfpOutputPower,
			ommp81PlusXfpBiasCurrent,
			ommp81PlusXfpSupplyVoltage,
			ommp81PlusXfpTemperature,
			ommp81PlusSfpInputPower,
			ommp81PlusSfpOutputPower,
			ommp81PlusSfpBiasCurrent,
			ommp81PlusSfpSupplyVoltage,
			ommp81PlusSfpTemperature,
			ommp81PlusOtnFecUncorrectedWords,
			ommp81PlusOtnFecCorrectedBits,
			ommp81PlusOtnFecZerosCorrectedBits,
			ommp81PlusOtnFecOnesCorrectedBits,
			ommp81PlusOtuBitInterleavedParityErrors,
			ommp81PlusOtuIncomingAlignmentErrorSeconds,
			ommp81PlusOtuBackwardErrorIndicationErrorCount,
			ommp81PlusOtuBackwardIncomingAlignmentErrorSeconds,
			ommp81PlusOtuErrorFreeSeconds,
			ommp81PlusOtuErrorSeconds,
			ommp81PlusOtuBackgroundBlockErrors,
			ommp81PlusOtuSevereErrorSeconds,
			ommp81PlusOtuUnavailableSeconds,
			ommp81PlusOtuBackgroundBlockErrorRatio,
			ommp81PlusOtuSevereErrorSecondsErrorRatio,
			ommp81PlusOtuFarEndErrorFreeSeconds,
			ommp81PlusOtuFarEndErrorSeconds,
			ommp81PlusOtuFarEndBackgroundBlockErrors,
			ommp81PlusOtuFarEndSevereErrorSeconds,
			ommp81PlusOtuFarEndUnavailableSeconds,
			ommp81PlusOtuFarEndBackgroundBlockErrorRatio,
			ommp81PlusOtuFarEndSevereErrorSecondsErrorRatio,
			ommp81PlusOtuErrorRatio,
			ommp81PlusOtuBitErrorRate,
			ommp81PlusOtuFramesReceived,
			ommp81PlusOduBitInterleavedParityErrors,
			ommp81PlusOduTcm1BitInterleavedParityErrors,
			ommp81PlusOduTcm2BitInterleavedParityErrors,
			ommp81PlusOduTcm3BitInterleavedParityErrors,
			ommp81PlusOduTcm4BitInterleavedParityErrors,
			ommp81PlusOduTcm5BitInterleavedParityErrors,
			ommp81PlusOduTcm6BitInterleavedParityErrors,
			ommp81PlusOduTcm1IncomingAlignmentErrorSeconds,
			ommp81PlusOduBackwardErrorIndicationErrorCount,
			ommp81PlusOduTcm1BackwardErrorIndicationErrorCount,
			ommp81PlusOduTcm2BackwardErrorIndicationErrorCount,
			ommp81PlusOduTcm3BackwardErrorIndicationErrorCount,
			ommp81PlusOduTcm4BackwardErrorIndicationErrorCount,
			ommp81PlusOduTcm5BackwardErrorIndicationErrorCount,
			ommp81PlusOduTcm6BackwardErrorIndicationErrorCount,
			ommp81PlusOduTcm1BackwardIncomingAlignmentErrorSeconds,
			ommp81PlusOduDelayMeasurement,
			ommp81PlusOduErrorFreeSeconds,
			ommp81PlusOduErrorSeconds,
			ommp81PlusOduBackgroundBlockErrors,
			ommp81PlusOduSevereErrorSeconds,
			ommp81PlusOduUnavailableSeconds,
			ommp81PlusOduBackgroundBlockErrorRatio,
			ommp81PlusOduSevereErrorSecondsErrorRatio,
			ommp81PlusOduFarEndErrorFreeSeconds,
			ommp81PlusOduFarEndErrorSeconds,
			ommp81PlusOduFarEndBackgroundBlockErrors,
			ommp81PlusOduFarEndSevereErrorSeconds,
			ommp81PlusOduFarEndUnavailableSeconds,
			ommp81PlusOduFarEndBackgroundBlockErrorRatio,
			ommp81PlusOduFarEndSevereErrorSecondsErrorRatio,
			ommp81PlusSdhRsB1BitInterleavedParityErrors,
			ommp81PlusSdhMsB2BitInterleavedParityErrors,
			ommp81PlusSdhMsB3BitInterleavedParityErrors,
			ommp81PlusSdhMsRemoteErrorIndicationErrorCount,
			ommp81PlusSdhMsRemoteDefectIndicationErrorCount,
			ommp81PlusSdhErrorFreeSeconds,
			ommp81PlusSdhErrorSeconds,
			ommp81PlusSdhBackgroundBlockErrors,
			ommp81PlusSdhSevereErrorSeconds,
			ommp81PlusSdhUnavailableSeconds,
			ommp81PlusSdhErrorSecondsErrorRatio,
			ommp81PlusSdhBackgroundBlockErrorRatio,
			ommp81PlusSdhSevereErrorSecondsErrorRatio,
			ommp81PlusEthernetMacTerminatedFramesTransmitted,
			ommp81PlusEthernetMacTerminatedFramesReceived,
			ommp81PlusEthernetMacTerminatedPauseFramesTransmitted,
			ommp81PlusEthernetMacTerminatedPauseFramesReceived,
			ommp81PlusEthernetMacTerminatedUnicastFramesTransmitted,
			ommp81PlusEthernetMacTerminatedUnicastFramesReceived,
			ommp81PlusEthernetMacTerminatedMulticastFramesTransmitted,
			ommp81PlusEthernetMacTerminatedMulticastFramesReceived,
			ommp81PlusEthernetMacTerminatedBroadcastFramesTransmitted,
			ommp81PlusEthernetMacTerminatedBroadcastFramesReceived,
			ommp81PlusEthernetMacTerminatedUnderSizeFramesTransmitted,
			ommp81PlusEthernetMacTerminatedUnderSizeFramesReceived,
			ommp81PlusEthernetMacTerminatedOverSizeFramesTransmitted,
			ommp81PlusEthernetMacTerminatedOverSizeFramesReceived,
			ommp81PlusEthernetMacTerminatedVlanTaggedFramesTransmitted,
			ommp81PlusEthernetMacTerminatedVlanTaggedFramesReceived,
			ommp81PlusEthernetMacTerminatedFrameSymbolErrorsReceived,
			ommp81PlusEthernetMacTerminatedFragmentFramesReceived,
			ommp81PlusEthernetMacTerminatedFrameCheckSequenceErrorsReceived,
			ommp81PlusEthernetMacTerminatedFramesReceivedWithNoDefect,
			ommp81PlusEthernetMacTerminatedBytesTransmitted,
			ommp81PlusEthernetMacTerminatedBytesReceived,
			ommp81PlusEthernetMacTerminatedControlFramesTransmitted,
			ommp81PlusEthernetMacTerminatedControlFramesReceived,
			ommp81PlusEthernetTransparentTransmitLcvCount,
			ommp81PlusEthernetTransparentTransmitPropagationErrorDeletionCount,
			ommp81PlusEthernetTransparentTransmitIdleDeletionCount,
			ommp81PlusEthernetTransparentTransmitConfDeletionCount,
			ommp81PlusEthernetTransparentTransmitPropagationInsertionCount,
			ommp81PlusEthernetTransparentTransmitIdleInsertionCount,
			ommp81PlusEthernetTransparentTransmitConfInsertionCount,
			ommp81PlusEthernetTransparentReceiveLcvCount,
			ommp81PlusEthernetTransparentReceivePropagationErrorDeletionCount,
			ommp81PlusEthernetTransparentReceiveIdleDeletionCount,
			ommp81PlusEthernetTransparentReceiveConfDeletionCount,
			ommp81PlusEthernetTransparentReceivePacketDeletionCount,
			ommp81PlusGfpCoreHeaderErrorCount,
			ommp81PlusGfpExtentionHeaderErrorCount,
			ommp81PlusGfpFrameCountWithSingleBitError,
			ommp81PlusGfpTypeHeaderErrorCount,
			ommp81PlusGfpReceiveDropFrameCount,
			ommp81PlusGfpReceiveExtensionHeaderIdentifierFilterDropCount,
			ommp81PlusFcTransmitWordCount,
			ommp81PlusFcReceiveWordCount,
			ommp81PlusFcTransmitTotalPackets,
			ommp81PlusFcReceiveTotalPackets,
			ommp81PlusFcTransmitBadCrc,
			ommp81PlusFcReceiveBadCrc,
			ommp81PlusFcTransmitLcvCount,
			ommp81PlusFcReceiveLcvCount,
			ommp81PlusFcTransmitFillWordInsertionCount,
			ommp81PlusFcTransmitPrimitiveSequenceInsertionCount,
			ommp81PlusFcTransmitFillWordDeletionCount,
			ommp81PlusFcTransmitPrimitiveSequenceDeletionCount,
			ommp81PlusPerformanceTableRowStatus,
			ommp81PlusAccessHyphyRegister,
			ommp81PlusCnodeCrashCount,
			ommp81PlusKernelState,
			ommp81PlusDiagnosticTableRowStatus
		}
    STATUS  current
    DESCRIPTION
            "A collection of objects from RFC 1213 made current by this MIB module."
    ::= { utlrnd 2 }

	
END

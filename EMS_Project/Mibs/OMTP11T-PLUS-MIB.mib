--*****************************************************************************
--			MIB FILE FOR THE OMTP11T-PLUS CARD
--*****************************************************************************

	OMTP11T-PLUS-MIB DEFINITIONS ::= BEGIN

	IMPORTS

	RowStatus                               FROM STANDARD-MIB
	DisplayString                           FROM RFC1213-MIB
	   
	OBJECT-IDENTITY, 
	NOTIFICATION-TYPE, 
	MODULE-IDENTITY, 
	Integer32, 
	Unsigned32,
	IpAddress,

	TimeTicks		                FROM SNMPv2-SMI
	OBJECT-TYPE                             FROM RFC-1212

	MODULE-COMPLIANCE, 
	OBJECT-GROUP, 
	NOTIFICATION-GROUP                      FROM SNMPv2-CONF

	node, 
	rack, 
	subRack, 
	slot                                    FROM SCC-MIB 

	enterprises                             FROM RFC1155-SMI		

	;

	utl   MODULE-IDENTITY
		LAST-UPDATED    	"1807130630Z"
		ORGANIZATION    	"United Telecoms Limited, Bangalore-560048."
		CONTACT-INFO    	"Website: http://www.utlindia.com."                                           
		DESCRIPTION     	"MIB module for NFS."
		REVISION 	    	"1807130630Z"
		DESCRIPTION    	    	"MIB module for OMTP11T-PLUS Card."
		::= { enterprises 18036 }

	utlrnd  OBJECT-IDENTITY
		STATUS  current
		DESCRIPTION "UTL Research and Development."
		::= { utl 1 }

	dwdm OBJECT IDENTIFIER				::=	{ utlrnd 1 }
	indus OBJECT IDENTIFIER				::=	{ dwdm 1 }
	omtp11tPlus OBJECT IDENTIFIER 			::=	{ indus 72 }

	omtp11tPlusCardGeneralDetails OBJECT IDENTIFIER	::=	{ omtp11tPlus 1 }
	omtp11tPlusConfiguration OBJECT IDENTIFIER	::=	{ omtp11tPlus 2 }
	omtp11tPlusAlarm OBJECT IDENTIFIER		::=	{ omtp11tPlus 3 }
	omtp11tPlusPerformance OBJECT IDENTIFIER	::=	{ omtp11tPlus 4 }
	omtp11tPlusDiagnostics OBJECT IDENTIFIER 	::=	{ omtp11tPlus 5 }
	
	omtp11tPlusAlarmQuery OBJECT IDENTIFIER		::=	{ omtp11tPlusAlarm 1 }
	omtp11tPlusAlarmNotification OBJECT IDENTIFIER	::=	{ omtp11tPlusAlarm 2 }

--*****************************************************************************
--				   CARD GENERAL DETAILS
--*****************************************************************************

	omtp11tPlusCardGeneralDetailsTable OBJECT-TYPE
		SYNTAX SEQUENCE OF Omtp11tPlusCardGeneralDetailsEntry
		MAX-ACCESS not-accessible
		STATUS current
		DESCRIPTION
			"Contains card general details' queries for the OMTP11T-PLUS card"
		::= { omtp11tPlusCardGeneralDetails 1 }

	omtp11tPlusCardGeneralDetailsEntry OBJECT-TYPE
		SYNTAX Omtp11tPlusCardGeneralDetailsEntry
		MAX-ACCESS not-accessible
		STATUS current
		DESCRIPTION
			""				  	
		INDEX   { node, rack , subRack , slot , omtp11tPlusInterfaceNumber}
		::= { omtp11tPlusCardGeneralDetailsTable 1 }

	Omtp11tPlusCardGeneralDetailsEntry ::= 
		SEQUENCE { 
				omtp11tPlusInterfaceNumber					INTEGER,
				omtp11tPlusEepromCardId						INTEGER,
				omtp11tPlusEepromCardName					DisplayString,
				omtp11tPlusEepromPartCode					DisplayString,
				omtp11tPlusEepromCardSerialNumber				DisplayString,
				omtp11tPlusEepromHardwareExternalReleaseVersion			DisplayString,
				omtp11tPlusSoftwareExternalReleaseVersion			DisplayString,
				omtp11tPlusEepromHardwareInternalReleaseVersion			DisplayString,
				omtp11tPlusSoftwareInternalReleaseVersion			DisplayString,
				omtp11tPlusEepromCardUidNumber					DisplayString,
				omtp11tPlusEepromCardEui48Number				DisplayString,
				omtp11tPlusEepromCardEui64Number				DisplayString,
				omtp11tPlusCardRootFileSystemVersion				DisplayString,
				omtp11tPlusCardInstallationDate					DisplayString,
				omtp11tPlusCardCommissionDate					DisplayString,
				omtp11tPlusCardRunningTime					DisplayString,
				omtp11tPlusCardRestartCount					INTEGER,
				omtp11tPlusXfpReadyForOperation					INTEGER,
				omtp11tPlusXfpI2cCommunicationStatus				INTEGER,
				omtp11tPlusXfpEepromPage					INTEGER,
				omtp11tPlusCheckCodeOfXfpEepromPage				INTEGER,
				omtp11tPlusExtendedCheckCodeOfXfpEepromPage			INTEGER,
				omtp11tPlusXfpVendorName					DisplayString,
				omtp11tPlusXfpVendorIeeeId					DisplayString,
				omtp11tPlusXfpPartNumber					DisplayString,
				omtp11tPlusXfpSerialNumber					DisplayString,
				omtp11tPlusXfpRevisionNumber					DisplayString,
				omtp11tPlusXfpManufacturingDate					DisplayString,
				omtp11tPlusFixedXfpLaserWavelength				DisplayString,
				omtp11tPlusXfpLaserWavelengthTolerance				DisplayString,
				omtp11tPlusXfpWavelengthTunabilitySupported			INTEGER,
				omtp11tPlusTunableXfpLaserWavelengthError			DisplayString,
				omtp11tPlusTunableXfpLaserFrequencyError			DisplayString,
				omtp11tPlusTunableXfpLaserFirstFrequency			DisplayString,
				omtp11tPlusTunableXfpLaserLastFrequency				DisplayString,
				omtp11tPlusTunableXfpWavelengthGridSpacing			DisplayString,
				omtp11tPlusXfpConnectorType					DisplayString,
				omtp11tPlusXfpLinkLength					DisplayString,
				omtp11tPlusXfpCdrRateSupported					INTEGER,
				omtp11tPlusXfpSignalEncodingTypeSupported			INTEGER,
				omtp11tPlusXfpTransceiverCodesSupported				INTEGER,
				omtp11tPlusXfpMaximumBitrateSupported				DisplayString,
				omtp11tPlusXfpMinimumBitrateSupported				DisplayString,
				omtp11tPlusXfpMaximumCaseTemperatureSupported			INTEGER,
				omtp11tPlusXfpMaximumPowerDissipationSupported			INTEGER,
				omtp11tPlusXfpMaximumPowerDissipationSupportedAtPowerDownMode	INTEGER,
				omtp11tPlusXfpMaximumCurrentLimitSupportedAtPlus5vSupply	INTEGER,
				omtp11tPlusXfpMaximumCurrentLimitSupportedAtPlus3Point3vSupply	INTEGER,
				omtp11tPlusXfpMaximumCurrentLimitSupportedAtPlus1Point8vSupply	INTEGER,
				omtp11tPlusXfpMaximumCurrentLimitSupportedAtMinus5Point2vSupply	INTEGER,
				omtp11tPlusXfpLineLoopbackSupported				INTEGER,
				omtp11tPlusXfpXfiLoopbackSupported				INTEGER,
				omtp11tPlusXfpOptionalVpsSupported				INTEGER,
				omtp11tPlusXfpLaserDisableThroughI2cSupported			INTEGER,
				omtp11tPlusXfpPowerDownThroughI2cSupported			INTEGER,
				omtp11tPlusXfpVpsLvRegulatorModeSupported			INTEGER,
				omtp11tPlusXfpVpsBypassedRegulatorModeSupported			INTEGER,
				omtp11tPlusXfpActiveFecControlSupported				INTEGER,
				omtp11tPlusXfpOptionalCmuModeSupported				INTEGER,
				omtp11tPlusXfpFecBerSupported					INTEGER,
				omtp11tPlusXfpReceivePowerMeasurementIsInOmaOrAverage		INTEGER,
				omtp11tPlusXfpActiveWavelengthControlSupported			INTEGER,
				omtp11tPlusXfpTransmitterIsCooledOrUncooled			INTEGER,
				omtp11tPlusXfpReceiverTypeIsPinOrApd				INTEGER,
				omtp11tPlusCardGeneralDetailsTableRowStatus			RowStatus
		}

	omtp11tPlusInterfaceNumber OBJECT-TYPE
		SYNTAX INTEGER
		MAX-ACCESS not-accessible
		STATUS current
		DESCRIPTION
			"Interface number represents the port number
			InterfaceNumber to port mapping is as follows:
			1 - CLIENT-1
			2 - LINE-1
			-----------------------------
			For properties which do not apply on any interface,
			the interface number must be passed as 0
			-----------------------------"

		::= { omtp11tPlusCardGeneralDetailsEntry 1 }
		
	omtp11tPlusEepromCardId OBJECT-TYPE
		SYNTAX INTEGER
		MAX-ACCESS read-only
		STATUS current
		DESCRIPTION
			"Tells the card ID of the OMTP11T-PLUS card, present in the EEPROM
			-----------------------------
			omtp11tPlusInterfaceNumber: 0
			-----------------------------"
		::= { omtp11tPlusCardGeneralDetailsEntry 2 }
		
	omtp11tPlusEepromCardName OBJECT-TYPE
		SYNTAX DisplayString
		MAX-ACCESS read-only
		STATUS current
		DESCRIPTION
			"Tells the card name of the OMTP11T-PLUS card, present in the EEPROM
			-----------------------------
			omtp11tPlusInterfaceNumber: 0
			-----------------------------"
		::= { omtp11tPlusCardGeneralDetailsEntry 3 }
		
	omtp11tPlusEepromPartCode OBJECT-TYPE
		SYNTAX DisplayString
		MAX-ACCESS read-only
		STATUS current
		DESCRIPTION
			"Tells the part code of the OMTP11T-PLUS card, present in the EEPROM
			-----------------------------
			omtp11tPlusInterfaceNumber: 0
			-----------------------------"
		::= { omtp11tPlusCardGeneralDetailsEntry 4 }
		
	omtp11tPlusEepromCardSerialNumber OBJECT-TYPE
		SYNTAX DisplayString
		MAX-ACCESS read-write
		STATUS current
		DESCRIPTION
			"This property get / set the information about 
			OMTP11T-PLUS Card's Serial Number.
			-----------------------------
			omtp11tPlusInterfaceNumber: 0
			-----------------------------
			Values:
			eg: 123456
			-----------------------------"
		::= { omtp11tPlusCardGeneralDetailsEntry 5 }
		
	omtp11tPlusEepromHardwareExternalReleaseVersion OBJECT-TYPE
		SYNTAX DisplayString
		MAX-ACCESS read-only
		STATUS current
		DESCRIPTION
			"Get the Card's Hardware External Release Version. 
			This detail will be displayed to the customer.
			This version will increment only if there are significant
			architectural changes in the product
			-----------------------------
			omtp11tPlusInterfaceNumber: 0
			-----------------------------
			Values:
			eg: 0.1
			-----------------------------"
		::= { omtp11tPlusCardGeneralDetailsEntry 6 }
		
	omtp11tPlusSoftwareExternalReleaseVersion OBJECT-TYPE
		SYNTAX DisplayString
		MAX-ACCESS read-only
		STATUS current
		DESCRIPTION
			"Get the Card's Software External Release Version. 
			This detail will be displayed to the customer.
			This version will increment only if there are
			significant architectural changes in the product
			-----------------------------
			omtp11tPlusInterfaceNumber: 0
			-----------------------------
			Values:
			eg: 0.1
			-----------------------------"
		::= { omtp11tPlusCardGeneralDetailsEntry 7 }
		
	omtp11tPlusEepromHardwareInternalReleaseVersion OBJECT-TYPE
		SYNTAX DisplayString
		MAX-ACCESS read-only
		STATUS current
		DESCRIPTION
			"Get the Card's Hardware Internal Release Version.
			This detail is used for development purposes only.
			It differs from the external hardware version.
			-----------------------------
			omtp11tPlusInterfaceNumber: 0
			-----------------------------
			Values:
			eg: 4.1
			-----------------------------"
		::= { omtp11tPlusCardGeneralDetailsEntry 8 }
		
	omtp11tPlusSoftwareInternalReleaseVersion OBJECT-TYPE
		SYNTAX DisplayString
		MAX-ACCESS read-only
		STATUS current
		DESCRIPTION
			"Gets the Card's Software Internal Release Version.
			This detail is used for development purposes only.
			It differs from the external software version.
		      	-----------------------------
			omtp11tPlusInterfaceNumber: 0
			-----------------------------
			Values:
			eg: 5.1
			-----------------------------"
		::= { omtp11tPlusCardGeneralDetailsEntry 9 }
		
	omtp11tPlusEepromCardUidNumber OBJECT-TYPE
		SYNTAX DisplayString
		MAX-ACCESS read-only
		STATUS current
		DESCRIPTION
			"Tells the Card Unique IDentifier. It is a 4 byte
			address used to uniquely identify a card.
			----------------------------
			omtp11tPlusInterfaceNumber: 0
			------------------------------
			Values:
		      	eg: 12345678
			-----------------------------"
		::= { omtp11tPlusCardGeneralDetailsEntry 10 }
		
	omtp11tPlusEepromCardEui48Number OBJECT-TYPE
		SYNTAX DisplayString
		MAX-ACCESS read-only
		STATUS current
		DESCRIPTION
			"Tells the Card EUI-48 Number. It’s a 6 byte address
			used to uniquely identify a card.
			-----------------------------
			omtp11tPlusInterfaceNumber: 0
			-----------------------------
			Values:
		      	eg: 0004A3123456
			-----------------------------"
		::= { omtp11tPlusCardGeneralDetailsEntry 11 }
		
	omtp11tPlusEepromCardEui64Number OBJECT-TYPE
		SYNTAX DisplayString
		MAX-ACCESS read-only
		STATUS current
		DESCRIPTION
			"Tells the Card EUI-64 Number. It’s a 8 byte address
			used to uniquely identify a card.
			-----------------------------
			omtp11tPlusInterfaceNumber: 0
			-----------------------------
			Values:
		      	eg: 0004A31234567890
			-----------------------------"
		::= { omtp11tPlusCardGeneralDetailsEntry 12 }
		
        omtp11tPlusCardRootFileSystemVersion OBJECT-TYPE		 
		SYNTAX  DisplayString
		MAX-ACCESS  read-only
		STATUS current
		DESCRIPTION
			"Tells the Card's Root File System Version
			-----------------------------
			omtp11tPlusInterfaceNumber: 0
			-----------------------------
			Value:
		      	eg: 8
			-----------------------------"
		::= { omtp11tPlusCardGeneralDetailsEntry 13 }
		
	omtp11tPlusCardInstallationDate OBJECT-TYPE
		SYNTAX DisplayString
		MAX-ACCESS read-write
		STATUS current
		DESCRIPTION
			"Get the card's installation date in
			dd/mm/yyyy format
			-----------------------------
			omtp11tPlusInterfaceNumber: 0
			-----------------------------
			Values:
		      	eg: 12/03/2016
			-----------------------------"
		::= { omtp11tPlusCardGeneralDetailsEntry 21 }

	omtp11tPlusCardCommissionDate OBJECT-TYPE
		SYNTAX DisplayString
		MAX-ACCESS read-write
		STATUS current
		DESCRIPTION
			"Get the card's commission date in
			dd/mm/yyyy format
			-----------------------------
			omtp11tPlusInterfaceNumber: 0
			-----------------------------
			Values:
		      	eg: 20/03/2016
			-----------------------------"
		::= { omtp11tPlusCardGeneralDetailsEntry 22 }

	omtp11tPlusCardRunningTime OBJECT-TYPE
		SYNTAX DisplayString
		MAX-ACCESS read-only
		STATUS current
		DESCRIPTION
			"Get the duration of time for which the card is
			operational/running
			-----------------------------
			omtp11tPlusInterfaceNumber: 0
			-----------------------------
			Values:
		      	eg: 3d 2h 1m
			-----------------------------"
		::= { omtp11tPlusCardGeneralDetailsEntry 23 }
		
	omtp11tPlusCardRestartCount OBJECT-TYPE
		SYNTAX INTEGER
		MAX-ACCESS read-only
		STATUS current
		DESCRIPTION
			"Get the number of times the card has been soft reset.
			This value will get reset to 0 on factory reset.
			-----------------------------
			omtp11tPlusInterfaceNumber: 0
			-----------------------------
			Values:
		      	eg: 10
			-----------------------------"
		::= { omtp11tPlusCardGeneralDetailsEntry 24 }
		
	omtp11tPlusXfpReadyForOperation OBJECT-TYPE
		SYNTAX INTEGER
		MAX-ACCESS read-only
		STATUS current
		DESCRIPTION
			"Module not ready indicates that the XFP
			has detected a condition that tells
			transmit or receive data is invalid.
			It shall consist of logical OR of the
			following signals:
			> Transmit Signal Conditioner Loss of Lock
			> Transmitter Laser Fault
			> Receiver Signal Conditioner Loss of Lock
			(Ref: INF-8077 2.4.1)
			-----------------------------
			omtp11tPlusInterfaceNumber:
			1 - CLIENT-1
			2 - LINE-1
			-----------------------------
			Values:		
			1 - XFP is ready for operation 
			0 - XFP is not ready for operation
			-----------------------------"
		::= { omtp11tPlusCardGeneralDetailsEntry 31 }
		
	omtp11tPlusXfpI2cCommunicationStatus OBJECT-TYPE
		SYNTAX INTEGER
		MAX-ACCESS read-write
		STATUS current
		DESCRIPTION
			"Tells whether the XFP can be accessed
			on a single 2-wire interface bus or not.
			(Ref: INF-8077 2.4.2)
			-----------------------------
			omtp11tPlusInterfaceNumber:
			1 - CLIENT-1
			2 - LINE-1
			-----------------------------
			Values:			
			1 - Enable I2C communication for XFP
				i.e. the XFP responds to 2-wire serial
				communication commands.
			0 - Disable I2C communication for XFP
				i.e. the XFP will not respond to or
				acknowledge any 2-wire interface communication
				from the host.
			-----------------------------"
		::= { omtp11tPlusCardGeneralDetailsEntry 32 }
		
	omtp11tPlusXfpEepromPage OBJECT-TYPE
		SYNTAX INTEGER
		MAX-ACCESS read-write
		STATUS current
		DESCRIPTION
			"This property sets/gets the XFP EEPROM page, 
			the value represents the XFP EEPROM page number.
			-----------------------------
			omtp11tPlusInterfaceNumber:
			1 - CLIENT-1
			2 - LINE-1
			-----------------------------
			Values:			
			eg: 1(EEPROM Page number)
			-----------------------------"
		::= { omtp11tPlusCardGeneralDetailsEntry 33 }
		
	omtp11tPlusCheckCodeOfXfpEepromPage OBJECT-TYPE
		SYNTAX INTEGER
		MAX-ACCESS read-only
		STATUS current
		DESCRIPTION
			"This property provides the XFP
			check code(checksum) value for bytes 128 to 190
			present in XFP EEPROM Page number 1. 
			-----------------------------
			omtp11tPlusInterfaceNumber:
			1 - CLIENT-1
			2 - LINE-1
			-----------------------------
			Values:			
			eg: 1(EEPROM Page number)
			-----------------------------"
		::= { omtp11tPlusCardGeneralDetailsEntry 34 }
		
	omtp11tPlusExtendedCheckCodeOfXfpEepromPage OBJECT-TYPE
		SYNTAX INTEGER
		MAX-ACCESS read-only
		STATUS current
		DESCRIPTION
			"This property provides the XFP
			extended check code(checksum) value for bytes 192 to 222
			present in XFP EEPROM Page number 1. 
			-----------------------------
			omtp11tPlusInterfaceNumber:
			1 - CLIENT-1
			2 - LINE-1
			-----------------------------
			Values:			
			eg: 1(EEPROM Page number)
			-----------------------------"
		::= { omtp11tPlusCardGeneralDetailsEntry 35 }
		
	omtp11tPlusXfpVendorName OBJECT-TYPE
		SYNTAX DisplayString
		MAX-ACCESS read-only
		STATUS current
		DESCRIPTION
			"This property provides Vendor Name for given XFP. 
			The vendor name shall be the full name of the 
			corporation, a commonly accepted abbreviation of 
			the name of the corporation, the SCSI company code
			for the corporation, or the stock exchange code for
			the corporation.
			-----------------------------
			omtp11tPlusInterfaceNumber:
			1 - CLIENT-1
			2 - LINE-1
			-----------------------------
			Values:			
			eg: WTD
			-----------------------------"
		::= { omtp11tPlusCardGeneralDetailsEntry 36 }
		
	omtp11tPlusXfpVendorIeeeId OBJECT-TYPE
		SYNTAX DisplayString
		MAX-ACCESS read-only
		STATUS current
		DESCRIPTION
			"This property defines the IEEE company Identifier for
			the vendor of XFP. A value of all zero in the 3-byte
			field indicates that the Vendor OUI is unspecified.
			-----------------------------
			omtp11tPlusInterfaceNumber:
			1 - CLIENT-1
			2 - LINE-1
			-----------------------------
			Values:			
			eg: 010
			-----------------------------"
		::= { omtp11tPlusCardGeneralDetailsEntry 37 }
		
	omtp11tPlusXfpPartNumber OBJECT-TYPE
		SYNTAX DisplayString
		MAX-ACCESS read-only
		STATUS current
		DESCRIPTION
			"This property defines the vendor part number or
			product name of the XFP. A value of all zero
			indicates that the vendor Part Number is unspecified.
			-----------------------------
			omtp11tPlusInterfaceNumber:
			1 - CLIENT-1
			2 - LINE-1
			-----------------------------
			Values:			
			eg: FTRX-1811-2D2
			-----------------------------"
		::= { omtp11tPlusCardGeneralDetailsEntry 38 }
		
	omtp11tPlusXfpSerialNumber OBJECT-TYPE
		SYNTAX DisplayString
		MAX-ACCESS read-only
		STATUS current
		DESCRIPTION
			"This property provides vendor serial number defining
			the vendor’s serial number for the XFP. A value of all
			zero in the 16-byte field indicates that the vendor
			serial number is unspecified.
			-----------------------------
			omtp11tPlusInterfaceNumber:
			1 - CLIENT-1
			2 - LINE-1
			-----------------------------
			Values:			
			eg: KBG02CU
			-----------------------------"
		::= { omtp11tPlusCardGeneralDetailsEntry 39 }
		
	omtp11tPlusXfpRevisionNumber OBJECT-TYPE
		SYNTAX DisplayString
		MAX-ACCESS read-only
		STATUS current
		DESCRIPTION
			"The vendor revision number defining the vendor’s
			 product revision number. A value of all zero indicates
			 that the vendor revision number is unspecified
			-----------------------------
			omtp11tPlusInterfaceNumber:
			1 - CLIENT-1
			2 - LINE-1
			-----------------------------
			Values:			
			eg: RT
			-----------------------------"
		::= { omtp11tPlusCardGeneralDetailsEntry 40 }
		
	omtp11tPlusXfpManufacturingDate OBJECT-TYPE
		SYNTAX DisplayString
		MAX-ACCESS read-only
		STATUS current
		DESCRIPTION
			"This property defines the manufacturing date for 
			XFP. A value of 8-byte field in ASCII which represents
			year, month and date of each two bytes. 
			Extra two bytes may be blank
			-----------------------------
			omtp11tPlusInterfaceNumber:
			1 - CLIENT-1
			2 - LINE-1
			-----------------------------
			Values:			
			eg: 160224
			-----------------------------"
		::= { omtp11tPlusCardGeneralDetailsEntry 41 }
		
	omtp11tPlusFixedXfpLaserWavelength OBJECT-TYPE
		SYNTAX DisplayString
		MAX-ACCESS read-only
		STATUS current
		DESCRIPTION
			"This property provides transmitter LASER wavelength(nm)
			of the XFP
			-----------------------------
			omtp11tPlusInterfaceNumber:
			1 - CLIENT-1
			2 - LINE-1
			-----------------------------
			Values:			
			eg: 1310
			-----------------------------"
		::= { omtp11tPlusCardGeneralDetailsEntry 42 }
		
	omtp11tPlusXfpLaserWavelengthTolerance OBJECT-TYPE
		SYNTAX DisplayString
		MAX-ACCESS read-only
		STATUS current
		DESCRIPTION
			"This property provides XFP wavelength tolerance in GhZ
			-----------------------------
			omtp11tPlusInterfaceNumber:
			1 - CLIENT-1
			2 - LINE-1
			-----------------------------
			Values:			
			eg: 0.02
			-----------------------------"
		::= { omtp11tPlusCardGeneralDetailsEntry 43 }
		
	omtp11tPlusXfpWavelengthTunabilitySupported OBJECT-TYPE
		SYNTAX INTEGER
		MAX-ACCESS read-only
		STATUS current
		DESCRIPTION
			"This property provides information whether the XFP
			supports wavelength tunability or not.
			-----------------------------
			omtp11tPlusInterfaceNumber:
			1 - CLIENT-1
			2 - LINE-1
			-----------------------------
			Values:			
			1 - XFP supports wavelength tunability
			0 - XFP not supports wavelength tunability
			-----------------------------"
		::= { omtp11tPlusCardGeneralDetailsEntry 44 }

	omtp11tPlusTunableXfpLaserWavelengthError OBJECT-TYPE
		SYNTAX DisplayString
		MAX-ACCESS read-only
		STATUS current
		DESCRIPTION
			"This property provides wavelength error in pm
			-----------------------------
			omtp11tPlusInterfaceNumber:
			1 - CLIENT-1
			2 - LINE-1
			-----------------------------
			Values:			
			eg: 0.02
			-----------------------------"
		::= { omtp11tPlusCardGeneralDetailsEntry 45 }
		
	omtp11tPlusTunableXfpLaserFrequencyError OBJECT-TYPE
		SYNTAX DisplayString
		MAX-ACCESS read-only
		STATUS current
		DESCRIPTION
			"This property defines the monitor of current frequency
			Error of XFP. Frequency error is reported in Ghz.
			-----------------------------
			omtp11tPlusInterfaceNumber:
			1 - CLIENT-1
			2 - LINE-1
			-----------------------------
			Values:			
			eg: 0.03
			-----------------------------"
		::= { omtp11tPlusCardGeneralDetailsEntry 46 }
		
	omtp11tPlusTunableXfpLaserFirstFrequency OBJECT-TYPE
		SYNTAX DisplayString
		MAX-ACCESS read-only
		STATUS current
		DESCRIPTION
			"This property defines the first LASER frequency of XFP.
			The two byte value is specified in units of THz.
			-----------------------------
			omtp11tPlusInterfaceNumber:
			1 - CLIENT-1
			2 - LINE-1
			-----------------------------
			Values:			
			eg: 1529.45
			-----------------------------"
		::= { omtp11tPlusCardGeneralDetailsEntry 47 }
		
	omtp11tPlusTunableXfpLaserLastFrequency OBJECT-TYPE
		SYNTAX DisplayString
		MAX-ACCESS read-only
		STATUS current
		DESCRIPTION
			"This property defines the last laser frequency of XFP.
		 	 The two byte value is specified in units of THz.
			-----------------------------
			omtp11tPlusInterfaceNumber:
			1 - CLIENT-1
			2 - LINE-1
			-----------------------------
			Values:			
			eg: 1563.45
			-----------------------------"
		::= { omtp11tPlusCardGeneralDetailsEntry 48 }
		
	omtp11tPlusTunableXfpWavelengthGridSpacing OBJECT-TYPE
		SYNTAX DisplayString
		MAX-ACCESS read-only
		STATUS current
		DESCRIPTION
			"This property gives difference in the wavelength
			between two channels In GhZ
			-----------------------------
			omtp11tPlusInterfaceNumber:
			1 - CLIENT-1
			2 - LINE-1
			-----------------------------
			Values:
			eg: 50
			-----------------------------"
		::= { omtp11tPlusCardGeneralDetailsEntry 49 }
		
	omtp11tPlusXfpConnectorType OBJECT-TYPE
		SYNTAX DisplayString
		MAX-ACCESS read-only
		STATUS current
		DESCRIPTION
			"This property provides information of the XFP
			connector, value indicates the external connector
			provided on the XFP.
			-----------------------------
			omtp11tPlusInterfaceNumber:
			1 - CLIENT-1
			2 - LINE-1
			-----------------------------
			Values:
			00h 	Unknown or unspecified
			01h 	SC
			02h 	Fibre Channel Style 1 copper connector
			03h 	Fibre Channel Style 2 copper connector
			04h 	BNC/TNC
			05h 	Fibre Channel coaxial headers
			06h 	FiberJack
			07h 	LC
			08h 	MT-RJ
			09h 	MU
			0Ah 	SG
			0Bh 	Optical pigtail
			0C-1Fh 	Reserved
			20h 	HSSDC II
			21h 	Copper Pigtail
			22h-7Fh Reserved
			80-FFh 	Vendor specific
			-----------------------------"
		::= { omtp11tPlusCardGeneralDetailsEntry 50 }
		
	omtp11tPlusXfpLinkLength OBJECT-TYPE
		SYNTAX DisplayString
		MAX-ACCESS read-only
		STATUS current
		DESCRIPTION
			"This property provides link length suported by the XFP
			-----------------------------
			omtp11tPlusInterfaceNumber:
			1 - CLIENT-1
			2 - LINE-1
			-----------------------------
			Values:
			eg: 80.00
			-----------------------------"
		::= { omtp11tPlusCardGeneralDetailsEntry 51 }
		
	omtp11tPlusXfpCdrRateSupported OBJECT-TYPE
		SYNTAX INTEGER
		MAX-ACCESS read-only
		STATUS current
		DESCRIPTION
			"This property indicates which rates are supported by
			the CDR present in XFP.
			-----------------------------
			omtp11tPlusInterfaceNumber:
			1 - CLIENT-1
			2 - LINE-1
			-----------------------------
			Values:

			Return value 1-Byte represetation:
			Byte-1  CDR Rates
			Bit-7	9.95 Gb/s
			Bit-6	10.3 Gb/s
			Bit-5	10.5 Gb/s
			Bit-4	10.7 Gb/s
			Bit-3	11.1 Gb/s
			Bit-2	Reserved
			Bit-1	Dont care for this property
			Bit-0	Dont care for this property
			-----------------------------"
		::= { omtp11tPlusCardGeneralDetailsEntry 52 }
		
	omtp11tPlusXfpSignalEncodingTypeSupported OBJECT-TYPE
		SYNTAX INTEGER
		MAX-ACCESS read-only
		STATUS current
		DESCRIPTION
			"This property indicates the serial encoding mechanisms
			that are supported by the XFP.
			-----------------------------
			omtp11tPlusInterfaceNumber:
			1 - CLIENT-1
			2 - LINE-1
			-----------------------------
			Values:

			Return value 1-Byte represetation:
			Byte-1  Encoding Type
			Bit-7	64B/66B          
			Bit-6	8B10B     	 	 
			Bit-5	SONET Scrambled  
			Bit-4	NRZ              
			Bit-3	RZ              
			Bit-2	Reserved        
			Bit-1	Reserved         
			Bit-0	Reserved 
			-----------------------------"
		::= { omtp11tPlusCardGeneralDetailsEntry 53 }
		
	omtp11tPlusXfpTransceiverCodesSupported OBJECT-TYPE
		SYNTAX INTEGER
		MAX-ACCESS read-only
		STATUS current
		DESCRIPTION
			"The identifier value specifies which transceiver
			codes are supported by the XFP
			-----------------------------
			omtp11tPlusInterfaceNumber:
			1 - CLIENT-1
			2 - LINE-1
			-----------------------------
			Values:

			Return value 8-Byte represetation:
			---------------------------------------------------------------------------------------------------------------------------------------
				  Byte-1	  Byte-2	          Byte-3	  Byte-4	          Byte-5    Byte-6    Byte-7	        Byte-8
			---------------------------------------------------------------------------------------------------------------------------------------
			Bit-7	 10GBASE-SR	 1200-MX-SN-I        	 Reserved	 1000BASE-SX/1xFC MMF	 I-64.1r   S-64.1    L-64.1	       V-64.2a
			Bit-6	 10GBASE-LR	 1200-SM-LL-L	         Reserved	 1000BASE-LX/1xFC-SMF	 I-64.1	   S-64.2a   L-64.2a	       V-64.2b
			Bit-5	 10GBASE-ER	 Extended 1550 nm	 Reserved	 2xFC-MMF/2xFC-SMF	 I-64.2r   S-64.2b   L-64.2b	       V-64.3
			Bit-4	 10GBASE-LRM	 Intermediate 1300 nm	 Reserved	 OC-48-SR	         I-64.2	   S-64.3a   L-64.2c	       Reserved
			Bit-3	 10GBASE-SW	 Reserved	         Reserved	 OC-48-IR	         I-64.3	   S-64.3b   L-64.3	       Reserved
			Bit-2	 10GBASE-LW	 Reserved	         Reserved	 OC-48-LR	         I-64.5	   S-64.5a   G.959.1 P1L1-2D2  Reserved
			Bit-1	 10GBASE-EW	 Reserved	         Reserved	 Reserved	         Reserved  S-64.5b   Reserved	       Reserved
			Bit-0	 Reserved	 Reserved	         Reserved	 Reserved	         Reserved  Reserved  Reserved	       Reserved
			-----------------------------"
		::= { omtp11tPlusCardGeneralDetailsEntry 54 }
		
	omtp11tPlusXfpMaximumBitrateSupported OBJECT-TYPE
		SYNTAX DisplayString
		MAX-ACCESS read-only
		STATUS current
		DESCRIPTION
			"This property provides maximum bit rate value of the
			given XFP
			-----------------------------
			omtp11tPlusInterfaceNumber:
			1 - CLIENT-1
			2 - LINE-1
			-----------------------------
			Values: 9.5
			-----------------------------"
		::= { omtp11tPlusCardGeneralDetailsEntry 55 }
		
	omtp11tPlusXfpMinimumBitrateSupported OBJECT-TYPE
		SYNTAX DisplayString
		MAX-ACCESS read-only
		STATUS current
		DESCRIPTION
			"This property provides minimum bit rate value of the 
			given XFP
			-----------------------------
			omtp11tPlusInterfaceNumber:
			1 - CLIENT-1
			2 - LINE-1
			-----------------------------
			Values: 5.5
			-----------------------------"
		::= { omtp11tPlusCardGeneralDetailsEntry 56 }
		
	omtp11tPlusXfpMaximumCaseTemperatureSupported OBJECT-TYPE
		SYNTAX INTEGER
		MAX-ACCESS read-only
		STATUS current
		DESCRIPTION
			"This property provides the maximum case temperature
			(degree celcius) supported by XFP.
			-----------------------------
			omtp11tPlusInterfaceNumber:
			1 - CLIENT-1
			2 - LINE-1
			-----------------------------
			Values:
			eg: 70
			-----------------------------"

		::= { omtp11tPlusCardGeneralDetailsEntry 57 }
		
	omtp11tPlusXfpMaximumPowerDissipationSupported OBJECT-TYPE
		SYNTAX INTEGER
		MAX-ACCESS read-only
		STATUS current
		DESCRIPTION
			"This property provides the maximum power dissipation(mW)
			supported from XFP.
			-----------------------------
			omtp11tPlusInterfaceNumber:
			1 - CLIENT-1
			2 - LINE-1
			-----------------------------
			Values:
			eg: 25
			-----------------------------"
		::= { omtp11tPlusCardGeneralDetailsEntry 58 }
		
	omtp11tPlusXfpMaximumPowerDissipationSupportedAtPowerDownMode OBJECT-TYPE
		SYNTAX INTEGER
		MAX-ACCESS read-only
		STATUS current
		DESCRIPTION
			"This property provides the maximum power dissipation(mW)
			supported from XFP in power-down mode.
			-----------------------------
			omtp11tPlusInterfaceNumber:
			1 - CLIENT-1
			2 - LINE-1
			-----------------------------
			Values:
			eg: 20
			-----------------------------"
		::= { omtp11tPlusCardGeneralDetailsEntry 59 }
		
	omtp11tPlusXfpMaximumCurrentLimitSupportedAtPlus5vSupply OBJECT-TYPE
		SYNTAX INTEGER
		MAX-ACCESS read-only
		STATUS current
		DESCRIPTION
			"This property defines the maximum current(mA) required
			by XFP at +5V power supply.
			-----------------------------
			omtp11tPlusInterfaceNumber:
			1 - CLIENT-1
			2 - LINE-1
			-----------------------------
			Values:
			eg: 50
			-----------------------------"
		::= { omtp11tPlusCardGeneralDetailsEntry 60 }
		
	omtp11tPlusXfpMaximumCurrentLimitSupportedAtPlus3Point3vSupply OBJECT-TYPE
		SYNTAX INTEGER
		MAX-ACCESS read-only
		STATUS current
		DESCRIPTION
			"This property defines the maximum current(mA) required
			by XFP at +3.3V power supply.
			-----------------------------
			omtp11tPlusInterfaceNumber:
			1 - CLIENT-1
			2 - LINE-1
			-----------------------------
			Values:
			eg: 50
			-----------------------------"
		::= { omtp11tPlusCardGeneralDetailsEntry 61 }
		
	omtp11tPlusXfpMaximumCurrentLimitSupportedAtPlus1Point8vSupply OBJECT-TYPE
		SYNTAX INTEGER
		MAX-ACCESS read-only
		STATUS current
		DESCRIPTION
			"This property defines the maximum current(mA) required
			by XFP at +1.8V power supply.
			-----------------------------
			omtp11tPlusInterfaceNumber:
			1 - CLIENT-1
			2 - LINE-1
			-----------------------------
			Values:
			eg: 50
			-----------------------------"
		::= { omtp11tPlusCardGeneralDetailsEntry 62 }
		
	omtp11tPlusXfpMaximumCurrentLimitSupportedAtMinus5Point2vSupply OBJECT-TYPE
		SYNTAX INTEGER
		MAX-ACCESS read-only
		STATUS current
		DESCRIPTION
			"This property defines the maximum current(mA) required
			by XFP at -5.2V power supply.
			-----------------------------
			omtp11tPlusInterfaceNumber:
			1 - CLIENT-1
			2 - LINE-1
			-----------------------------
			Values:
			eg: 50
			-----------------------------"
		::= { omtp11tPlusCardGeneralDetailsEntry 63 }
		
	omtp11tPlusXfpLineLoopbackSupported OBJECT-TYPE
		SYNTAX INTEGER
		MAX-ACCESS read-only
		STATUS current
		DESCRIPTION
			"This property provides information whether Line side
			loopback is supported or not.
			-----------------------------
			omtp11tPlusInterfaceNumber:
			1 - CLIENT-1
			2 - LINE-1
			-----------------------------
			Values:
			1 - Lineside Loopback is supported in XFP
			0 - No Lineside Loopback is supported
			-----------------------------"
		::= { omtp11tPlusCardGeneralDetailsEntry 64 }
		
	omtp11tPlusXfpXfiLoopbackSupported OBJECT-TYPE
		SYNTAX INTEGER
		MAX-ACCESS read-only
		STATUS current
		DESCRIPTION
			"This property provides information whether Line side
			loopback at the Xfi level is supported or not.
			-----------------------------
			omtp11tPlusInterfaceNumber:
			1 - CLIENT-1
			2 - LINE-1
			-----------------------------
			Values:
			1 - Xfi Loopback is supported in XFP
			0 - No Xfi Loopback is supported
			-----------------------------"
		::= { omtp11tPlusCardGeneralDetailsEntry 65 }
		
	omtp11tPlusXfpOptionalVpsSupported OBJECT-TYPE
		SYNTAX INTEGER
		MAX-ACCESS read-only
		STATUS current
		DESCRIPTION
			"This property provides information whether XFP
			supports optional variable power supply or not.
			-----------------------------
			omtp11tPlusInterfaceNumber:
			1 - CLIENT-1
			2 - LINE-1
			-----------------------------
			Values:
			1 - XFP supports optional vps
			0 - XFP not supports optional vps
			-----------------------------"
		::= { omtp11tPlusCardGeneralDetailsEntry 66 }
		
	omtp11tPlusXfpLaserDisableThroughI2cSupported OBJECT-TYPE
		SYNTAX INTEGER
		MAX-ACCESS read-only
		STATUS current
		DESCRIPTION
			"This property provides information whether XFP
			LASER can be operated through single 2-wire interface
			bus or not.
			-----------------------------
			omtp11tPlusInterfaceNumber:
			1 - CLIENT-1
			2 - LINE-1
			-----------------------------
			Values:
			1 - XFP supports LASER disable through I2C
			0 - XFP does not support LASER disable through I2C
			-----------------------------"
		::= { omtp11tPlusCardGeneralDetailsEntry 67 }
		
	omtp11tPlusXfpPowerDownThroughI2cSupported OBJECT-TYPE
		SYNTAX INTEGER
		MAX-ACCESS read-only
		STATUS current
		DESCRIPTION
			"This property provides information whether XFP-
			Power-down can be operated through single 2-wire 
			interface bus or not.
			-----------------------------
			omtp11tPlusInterfaceNumber:
			1 - CLIENT-1
			2 - LINE-1
			-----------------------------
			Values:
			1 - XFP Supports XFP-power-down through I2C  
			0 - XFP does not supports XFP-power-down through I2C  
			-----------------------------"
		::= { omtp11tPlusCardGeneralDetailsEntry 68 }
		
	omtp11tPlusXfpVpsLvRegulatorModeSupported OBJECT-TYPE
		SYNTAX INTEGER
		MAX-ACCESS read-only
		STATUS current
		DESCRIPTION
			"This property provides information whether XFP
			supports VPS_LV_regulator_mode or not.
			-----------------------------
			omtp11tPlusInterfaceNumber:
			1 - CLIENT-1
			2 - LINE-1
			-----------------------------
			Values:
			1 - XFP supports VPS_LV_regulator_mode
			0 - XFP not supports VPS_LV_regulator_mode
			-----------------------------"
		::= { omtp11tPlusCardGeneralDetailsEntry 69 }
		
	omtp11tPlusXfpVpsBypassedRegulatorModeSupported OBJECT-TYPE
		SYNTAX INTEGER
		MAX-ACCESS read-only
		STATUS current
		DESCRIPTION
			"This property provides information whether XFP
			supports VPS bypassed regulator mode or not.
			-----------------------------
			omtp11tPlusInterfaceNumber:
			1 - CLIENT-1
			2 - LINE-1
			-----------------------------
			Values:
			1 - XFP supports VPS bypassed regulator mode
			0 - XFP not supports active VPS bypassed regulator mode
			-----------------------------"
		::= { omtp11tPlusCardGeneralDetailsEntry 70 }
		
	omtp11tPlusXfpActiveFecControlSupported OBJECT-TYPE
		SYNTAX INTEGER
		MAX-ACCESS read-only
		STATUS current
		DESCRIPTION
			"This property provides information whether XFP
			supports active FEC control functions or not.
			-----------------------------
			omtp11tPlusInterfaceNumber:
			1 - CLIENT-1
			2 - LINE-1
			-----------------------------
			Values:
			1 - XFP supports active FEC control functions
			0 - XFP not supports active FEC control functions
			-----------------------------"
		::= { omtp11tPlusCardGeneralDetailsEntry 71 }
		
	omtp11tPlusXfpOptionalCmuModeSupported OBJECT-TYPE
		SYNTAX INTEGER
		MAX-ACCESS read-only
		STATUS current
		DESCRIPTION
			"This property provides information whether XFP
			supports CMU mode or not.
			-----------------------------
			omtp11tPlusInterfaceNumber:
			1 - CLIENT-1
			2 - LINE-1
			-----------------------------
			Values:
			1 - XFP supports CMU mode
			0 - XFP not supports CMU mode
			-----------------------------"
		::= { omtp11tPlusCardGeneralDetailsEntry 72 }
		
	omtp11tPlusXfpFecBerSupported OBJECT-TYPE
		SYNTAX INTEGER
		MAX-ACCESS read-only
		STATUS current
		DESCRIPTION
			"This property provides information whether XFP
			supports FEC BER or not.
			-----------------------------
			omtp11tPlusInterfaceNumber:
			1 - CLIENT-1
			2 - LINE-1
			-----------------------------
			Values:
			1 - XFP supports FEC BER
			0 - XFP not supports FEC BER
			-----------------------------"
		::= { omtp11tPlusCardGeneralDetailsEntry 73 }
		
	omtp11tPlusXfpReceivePowerMeasurementIsInOmaOrAverage OBJECT-TYPE
		SYNTAX INTEGER
		MAX-ACCESS read-only
		STATUS current
		DESCRIPTION
			"This property tells whether the received power  
			measurement from XFP is given as Oma or Average.
			-----------------------------
			omtp11tPlusInterfaceNumber:
			1 - CLIENT-1
			2 - LINE-1
			-----------------------------
			Values:
			1 - OMA
			0 - Average Power
			-----------------------------"
		::= { omtp11tPlusCardGeneralDetailsEntry 74 }
		
	omtp11tPlusXfpActiveWavelengthControlSupported OBJECT-TYPE
		SYNTAX INTEGER
		MAX-ACCESS read-only
		STATUS current
		DESCRIPTION
			"This property provides whether the XFP wavelength 
			controlling state is active or not
			-----------------------------
			omtp11tPlusInterfaceNumber:
			1 - CLIENT-1
			2 - LINE-1
			-----------------------------
			Values:
			1 - active
			0 - not active
			-----------------------------"
		::= { omtp11tPlusCardGeneralDetailsEntry 75 }
		
	omtp11tPlusXfpTransmitterIsCooledOrUncooled OBJECT-TYPE
		SYNTAX INTEGER
		MAX-ACCESS read-only
		STATUS current
		DESCRIPTION
			"This property provide information on which type of
			diode used in transmitter of the XFP
			-----------------------------
			omtp11tPlusInterfaceNumber:
			1 - CLIENT-1
			2 - LINE-1
			-----------------------------
			Values:
			1 - Cooling circuit supported for XFP transmitter. 
			0 - Cooling circuit not supported for XFP transmitter.
			-----------------------------"
		::= { omtp11tPlusCardGeneralDetailsEntry 76 }
		
	omtp11tPlusXfpReceiverTypeIsPinOrApd OBJECT-TYPE
		SYNTAX INTEGER
		MAX-ACCESS read-only
		STATUS current
		DESCRIPTION
			"This property provide information on which type of
			diode used in transmitter of the XFP.
			-----------------------------
			omtp11tPlusInterfaceNumber:
			1 - CLIENT-1
			2 - LINE-1
			-----------------------------
			Values:
			1 - PIN detector
			0 - APD detector			 
			-----------------------------"
		::= { omtp11tPlusCardGeneralDetailsEntry 77 }

	omtp11tPlusCardGeneralDetailsTableRowStatus OBJECT-TYPE
              SYNTAX      RowStatus
              MAX-ACCESS  read-write
              STATUS      current
              DESCRIPTION
                      "	This is MIB realted property,
			NOT to be considered as a card property"
              ::= { omtp11tPlusCardGeneralDetailsEntry 78 }	

--*****************************************************************************
--				CONFIGURATION
--*****************************************************************************

        omtp11tPlusConfigurationTable OBJECT-TYPE
                SYNTAX SEQUENCE OF Omtp11tPlusConfigurationEntry
                MAX-ACCESS not-accessible
                STATUS current
                DESCRIPTION
                	"Contains configuration queries of the OMTP11T-PLUS card"
                ::= { omtp11tPlusConfiguration 1 }

	omtp11tPlusConfigurationEntry OBJECT-TYPE
		SYNTAX  Omtp11tPlusConfigurationEntry
		MAX-ACCESS  not-accessible
		STATUS  current
		DESCRIPTION 
			""
		INDEX   { node, rack , subRack , slot , omtp11tPlusInterfaceNumber}
		::= { omtp11tPlusConfigurationTable 1 }

	Omtp11tPlusConfigurationEntry ::= 
		SEQUENCE { 
				omtp11tPlusCardSoftwareUpgrade						DisplayString,
				omtp11tPlusCardSignalMonitorState					INTEGER,
				omtp11tPlusCardOpticalMonitorState					INTEGER,
				omtp11tPlusCardSoftReset						INTEGER,
				omtp11tPlusCardFactoryReset						INTEGER,
				omtp11tPlusCardAccessStatus						INTEGER,
				omtp11tPlusSyncSystemTimeWithNtpServer				DisplayString,
				omtp11tPlusSyncRtcWithNtpServer						DisplayString,
				omtp11tPlusSyncRtcWithSystemTime					DisplayString,
				omtp11tPlusUpdateGivenTimeIntoSystem				DisplayString,
				omtp11tPlusUpdateGivenTimeIntoRtc					DisplayString,
				omtp11tPlusSystemTimeAndRtcTime						DisplayString,
				
				omtp11tPlusTrafficConfiguration						INTEGER,
				omtp11tPlusLoopbackState						INTEGER,
				omtp11tPlusPortSignalMonitorState					INTEGER,
				omtp11tPlusPortOpticalMonitorState					INTEGER,
				omtp11tPlusClearSignalPerformance					INTEGER,
				omtp11tPlusAlsState							INTEGER,
				omtp11tPlusAlsPulseRepetitionTime					INTEGER,
				omtp11tPlusOtuFecConfiguration						INTEGER,
				omtp11tPlusOtuSignalFailThreshold					INTEGER,
				omtp11tPlusOtuSignalDegradeThreshold					INTEGER,
				omtp11tPlusOtuAlarmIndicationSignalAlarmInsertion			INTEGER,
				omtp11tPlusOtuSapiTransmitTraceMessage					DisplayString,
				omtp11tPlusOtuDapiTransmitTraceMessage					DisplayString,
				omtp11tPlusOtuOperatorSpecificTransmitTraceMessage			DisplayString,
				omtp11tPlusOtuSapiExpectedTraceMessage					DisplayString,
				omtp11tPlusOtuDapiExpectedTraceMessage					DisplayString,
				omtp11tPlusOtuOperatorSpecificExpectedTraceMessage			DisplayString,
				omtp11tPlusOtuSapiReceivedTraceMessage					DisplayString,
				omtp11tPlusOtuDapiReceivedTraceMessage					DisplayString,
				omtp11tPlusOtuOperatorSpecificReceivedTraceMessage			DisplayString,
				omtp11tPlusOduSignalFailThreshold					INTEGER,
				omtp11tPlusOduSignalDegradeThreshold					INTEGER,
				omtp11tPlusOduAlarmIndicationSignalAlarmInsertion			INTEGER,
				omtp11tPlusOduLockedDefectAlarmInsertion				INTEGER,
				omtp11tPlusOduOpenConnectionIndicationAlarmInsertion			INTEGER,
				omtp11tPlusOduSapiTransmitTraceMessage					DisplayString,
				omtp11tPlusOduDapiTransmitTraceMessage					DisplayString,
				omtp11tPlusOduOperatorSpecificTransmitTraceMessage			DisplayString,
				omtp11tPlusOduSapiExpectedTraceMessage					DisplayString,
				omtp11tPlusOduDapiExpectedTraceMessage					DisplayString,
				omtp11tPlusOduOperatorSpecificExpectedTraceMessage			DisplayString,
				omtp11tPlusOduSapiReceivedTraceMessage					DisplayString,
				omtp11tPlusOduDapiReceivedTraceMessage					DisplayString,
				omtp11tPlusOduOperatorSpecificReceivedTraceMessage			DisplayString,
				omtp11tPlusOpuTransmitPayloadType					INTEGER,
				omtp11tPlusOpuReceivedPayloadType					INTEGER,
				omtp11tPlusTunableXfpLaserWavelength					INTEGER,
				omtp11tPlusTunableXfpLaserChannelNumber					INTEGER,
				omtp11tPlusXfpLaserState						INTEGER,
				omtp11tPlusXfpReset							INTEGER,
				omtp11tPlusXfpPowerDownMode						INTEGER,
				omtp11tPlusXfpLineLoopback						INTEGER,
				omtp11tPlusXfpXfiLoopback						INTEGER,
				omtp11tPlusXfpAmplitudeThresholdOfReceiverForFecControl			INTEGER,
				omtp11tPlusXfpPhaseInEyeDiagramForFecControl				INTEGER,
				omtp11tPlusXfpSystemReportingBer					INTEGER,
				omtp11tPlusXfpHighTemperatureAlarmThreshold				DisplayString,
				omtp11tPlusXfpLowTemperatureAlarmThreshold				DisplayString,
				omtp11tPlusXfpHighTemperatureWarningThreshold				DisplayString,
				omtp11tPlusXfpLowTemperatureWarningThreshold				DisplayString,
				omtp11tPlusXfpHighBiasCurrentAlarmThreshold				DisplayString,
				omtp11tPlusXfpLowBiasCurrentAlarmThreshold				DisplayString,
				omtp11tPlusXfpHighBiasCurrentWarningThreshold				DisplayString,
				omtp11tPlusXfpLowBiasCurrentWarningThreshold				DisplayString,
				omtp11tPlusXfpInputHighPowerAlarmThreshold				DisplayString,
				omtp11tPlusXfpInputLowPowerAlarmThreshold				DisplayString,
				omtp11tPlusXfpInputHighPowerWarningThreshold				DisplayString,
				omtp11tPlusXfpInputLowPowerWarningThreshold				DisplayString,
				omtp11tPlusXfpOutputHighPowerAlarmThreshold				DisplayString,
				omtp11tPlusXfpOutputLowPowerAlarmThreshold				DisplayString,
				omtp11tPlusXfpOutputHighPowerWarningThreshold				DisplayString,
				omtp11tPlusXfpOutputLowPowerWarningThreshold				DisplayString,
				omtp11tPlusXfpHighSupplyVoltageAlarmThreshold				DisplayString,
				omtp11tPlusXfpLowSupplyVoltageAlarmThreshold				DisplayString,
				omtp11tPlusXfpHighSupplyVoltageWarningThreshold				DisplayString,
				omtp11tPlusXfpLowSupplyVoltageWarningThreshold				DisplayString,
				omtp11tPlusXfpInputPowerFailureAlarmInhibit				INTEGER,
				omtp11tPlusXfpOutputPowerFailureAlarmInhibit				INTEGER,
				omtp11tPlusXfpHighTemperatureAlarmInhibit				INTEGER,
				omtp11tPlusXfpLowTemperatureAlarmInhibit				INTEGER,
				omtp11tPlusXfpHighTemperatureWarningInhibit				INTEGER,
				omtp11tPlusXfpLowTemperatureWarningInhibit				INTEGER,
				omtp11tPlusXfpHighBiasCurrentAlarmInhibit				INTEGER,
				omtp11tPlusXfpLowBiasCurrentAlarmInhibit				INTEGER,
				omtp11tPlusXfpHighBiasCurrentWarningInhibit				INTEGER,
				omtp11tPlusXfpLowBiasCurrentWarningInhibit				INTEGER,
				omtp11tPlusXfpInputHighPowerAlarmInhibit				INTEGER,
				omtp11tPlusXfpInputLowPowerAlarmInhibit					INTEGER,
				omtp11tPlusXfpInputHighPowerWarningInhibit				INTEGER,
				omtp11tPlusXfpInputLowPowerWarningInhibit				INTEGER,
				omtp11tPlusXfpOutputHighPowerAlarmInhibit				INTEGER,
				omtp11tPlusXfpOutputLowPowerAlarmInhibit				INTEGER,
				omtp11tPlusXfpOutputHighPowerWarningInhibit				INTEGER,
				omtp11tPlusXfpOutputLowPowerWarningInhibit				INTEGER,
				omtp11tPlusXfpHighSupplyVoltageAlarmInhibit				INTEGER,
				omtp11tPlusXfpLowSupplyVoltageAlarmInhibit				INTEGER,
				omtp11tPlusXfpHighSupplyVoltageWarningInhibit				INTEGER,
				omtp11tPlusXfpLowSupplyVoltageWarningInhibit				INTEGER,
				omtp11tPlusXfpPresenceAbsenceNotificationInhibit			INTEGER,
				omtp11tPlusOtuLossOfSignalAlarmInhibit					INTEGER,
				omtp11tPlusOtuLossOfFrameAlarmInhibit					INTEGER,
				omtp11tPlusOtuOutOfFrameAlarmInhibit					INTEGER,
				omtp11tPlusOtuLossOfMultiFrameAlarmInhibit				INTEGER,
				omtp11tPlusOtuOutOfMultiFrameAlarmInhibit				INTEGER,
				omtp11tPlusOtuSignalFailAlarmInhibit					INTEGER,
				omtp11tPlusOtuSignalDegradeAlarmInhibit					INTEGER,
				omtp11tPlusOtuAlarmIndicationSignalAlarmInhibit				INTEGER,
				omtp11tPlusOtuIncomingAlignmentErrorAlarmInhibit			INTEGER,
				omtp11tPlusOtuTraceIdentifierMismatchAlarmInhibit			INTEGER,
				omtp11tPlusOtuBackwardIncomingAlignmentErrorAlarmInhibit		INTEGER,
				omtp11tPlusOtuBackwardDefectIndicationAlarmInhibit			INTEGER,
				omtp11tPlusOduSignalFailAlarmInhibit					INTEGER,
				omtp11tPlusOduSignalDegradeAlarmInhibit					INTEGER,
				omtp11tPlusOduAlarmIndicationSignalAlarmInhibit				INTEGER,
				omtp11tPlusOduTcm1IncomingAlignmentErrorAlarmInhibit			INTEGER,
				omtp11tPlusOduTcm2IncomingAlignmentErrorAlarmInhibit			INTEGER,
				omtp11tPlusOduTcm3IncomingAlignmentErrorAlarmInhibit			INTEGER,
				omtp11tPlusOduTcm4IncomingAlignmentErrorAlarmInhibit			INTEGER,
				omtp11tPlusOduTcm5IncomingAlignmentErrorAlarmInhibit			INTEGER,
				omtp11tPlusOduTcm6IncomingAlignmentErrorAlarmInhibit			INTEGER,
				omtp11tPlusOduTraceIdentifierMismatchAlarmInhibit			INTEGER,
				omtp11tPlusOduLockedDefectAlarmInhibit					INTEGER,
				omtp11tPlusOduOpenConnectionIndicationAlarmInhibit			INTEGER,
				omtp11tPlusOduBackwardDefectIndicationAlarmInhibit			INTEGER,
				omtp11tPlusOduTcm1BackwardIncomingAlignmentErrorAlarmInhibit		INTEGER,
				omtp11tPlusOduTcm2BackwardIncomingAlignmentErrorAlarmInhibit		INTEGER,
				omtp11tPlusOduTcm3BackwardIncomingAlignmentErrorAlarmInhibit		INTEGER,
				omtp11tPlusOduTcm4BackwardIncomingAlignmentErrorAlarmInhibit		INTEGER,
				omtp11tPlusOduTcm5BackwardIncomingAlignmentErrorAlarmInhibit		INTEGER,
				omtp11tPlusOduTcm6BackwardIncomingAlignmentErrorAlarmInhibit		INTEGER,
				omtp11tPlusOpuPayloadMismatchAlarmInhibit				INTEGER,
				omtp11tPlusOchLossOfPayloadAlarmInhibit					INTEGER,
				omtp11tPlusXfpInputPowerFailureAlarmSeverity				DisplayString,
				omtp11tPlusXfpOutputPowerFailureAlarmSeverity				DisplayString,
				omtp11tPlusXfpHighTemperatureAlarmSeverity				DisplayString,
				omtp11tPlusXfpLowTemperatureAlarmSeverity				DisplayString,
				omtp11tPlusXfpHighTemperatureWarningSeverity				DisplayString,
				omtp11tPlusXfpLowTemperatureWarningSeverity				DisplayString,
				omtp11tPlusXfpHighBiasCurrentAlarmSeverity				DisplayString,
				omtp11tPlusXfpLowBiasCurrentAlarmSeverity				DisplayString,
				omtp11tPlusXfpHighBiasCurrentWarningSeverity				DisplayString,
				omtp11tPlusXfpLowBiasCurrentWarningSeverity				DisplayString,
				omtp11tPlusXfpInputHighPowerAlarmSeverity				DisplayString,
				omtp11tPlusXfpInputLowPowerAlarmSeverity				DisplayString,
				omtp11tPlusXfpInputHighPowerWarningSeverity				DisplayString,
				omtp11tPlusXfpInputLowPowerWarningSeverity				DisplayString,
				omtp11tPlusXfpOutputHighPowerAlarmSeverity				DisplayString,
				omtp11tPlusXfpOutputLowPowerAlarmSeverity				DisplayString,
				omtp11tPlusXfpOutputHighPowerWarningSeverity				DisplayString,
				omtp11tPlusXfpOutputLowPowerWarningSeverity				DisplayString,
				omtp11tPlusXfpHighSupplyVoltageAlarmSeverity				DisplayString,
				omtp11tPlusXfpLowSupplyVoltageAlarmSeverity				DisplayString,
				omtp11tPlusXfpHighSupplyVoltageWarningSeverity				DisplayString,
				omtp11tPlusXfpLowSupplyVoltageWarningSeverity				DisplayString,
				omtp11tPlusXfpPresenceAbsenceNotificationSeverity			DisplayString,
				omtp11tPlusOtuLossOfSignalAlarmSeverity					DisplayString,
				omtp11tPlusOtuLossOfFrameAlarmSeverity					DisplayString,
				omtp11tPlusOtuOutOfFrameAlarmSeverity					DisplayString,
				omtp11tPlusOtuLossOfMultiFrameAlarmSeverity				DisplayString,
				omtp11tPlusOtuOutOfMultiFrameAlarmSeverity				DisplayString,
				omtp11tPlusOtuSignalFailAlarmSeverity					DisplayString,
				omtp11tPlusOtuSignalDegradeAlarmSeverity				DisplayString,
				omtp11tPlusOtuAlarmIndicationSignalAlarmSeverity			DisplayString,
				omtp11tPlusOtuIncomingAlignmentErrorAlarmSeverity			DisplayString,
				omtp11tPlusOtuTraceIdentifierMismatchAlarmSeverity			DisplayString,
				omtp11tPlusOtuBackwardIncomingAlignmentErrorAlarmSeverity		DisplayString,
				omtp11tPlusOtuBackwardDefectIndicationAlarmSeverity			DisplayString,
				omtp11tPlusOduSignalFailAlarmSeverity					DisplayString,
				omtp11tPlusOduSignalDegradeAlarmSeverity				DisplayString,
				omtp11tPlusOduAlarmIndicationSignalAlarmSeverity			DisplayString,
				omtp11tPlusOduTcm1IncomingAlignmentErrorAlarmSeverity			DisplayString,
				omtp11tPlusOduTcm2IncomingAlignmentErrorAlarmSeverity			DisplayString,
				omtp11tPlusOduTcm3IncomingAlignmentErrorAlarmSeverity			DisplayString,
				omtp11tPlusOduTcm4IncomingAlignmentErrorAlarmSeverity			DisplayString,
				omtp11tPlusOduTcm5IncomingAlignmentErrorAlarmSeverity			DisplayString,
				omtp11tPlusOduTcm6IncomingAlignmentErrorAlarmSeverity			DisplayString,
				omtp11tPlusOduTraceIdentifierMismatchAlarmSeverity			DisplayString,
				omtp11tPlusOduLockedDefectAlarmSeverity					DisplayString,
				omtp11tPlusOduOpenConnectionIndicationAlarmSeverity			DisplayString,
				omtp11tPlusOduBackwardDefectIndicationAlarmSeverity			DisplayString,
				omtp11tPlusOduTcm1BackwardIncomingAlignmentErrorAlarmSeverity		DisplayString,
				omtp11tPlusOduTcm2BackwardIncomingAlignmentErrorAlarmSeverity		DisplayString,
				omtp11tPlusOduTcm3BackwardIncomingAlignmentErrorAlarmSeverity		DisplayString,
				omtp11tPlusOduTcm4BackwardIncomingAlignmentErrorAlarmSeverity		DisplayString,
				omtp11tPlusOduTcm5BackwardIncomingAlignmentErrorAlarmSeverity		DisplayString,
				omtp11tPlusOduTcm6BackwardIncomingAlignmentErrorAlarmSeverity		DisplayString,
				omtp11tPlusOpuPayloadMismatchAlarmSeverity				DisplayString,
				omtp11tPlusOchLossOfPayloadAlarmSeverity				DisplayString,
				omtp11tPlusConfigurationTableRowStatus					RowStatus
		}
		
	omtp11tPlusCardSoftwareUpgrade OBJECT-TYPE
		SYNTAX DisplayString
		MAX-ACCESS read-write
		STATUS current
		DESCRIPTION
			"Valid only as SET command.
			This property upgrades the software of the OMTP11T-PLUS card
			It takes the path of the software release as
			a value
			-----------------------------
			omtp11tPlusInterfaceNumber: 0
			-----------------------------
			Values:
			eg: /root/home/rel-2.0.0.tar.gz
			-----------------------------"

		::= { omtp11tPlusConfigurationEntry 1 }
		
	omtp11tPlusCardSignalMonitorState OBJECT-TYPE
		SYNTAX INTEGER
		MAX-ACCESS read-write
		STATUS current
		DESCRIPTION
			"This property sets or gets the card's signal
			monitoring state. Disabling card signal monitoring 
			will not provide any signal alarms and performances
			information to the user.
			-----------------------------
			omtp11tPlusInterfaceNumber: 0
			-----------------------------
			Values:
			1 - Card Signal Monitoring is enabled
			0 - Card Signal Monitoring is disabled
			-----------------------------"
		::= { omtp11tPlusConfigurationEntry 2 }

	omtp11tPlusCardOpticalMonitorState OBJECT-TYPE
		SYNTAX INTEGER
		MAX-ACCESS read-write
		STATUS current
		DESCRIPTION
			"This property sets or gets the card's optical
			monitoring state. Disabling card signal monitoring 
			will not provide any signal alarms and performances
			information to the user.
			-----------------------------
			omtp11tPlusInterfaceNumber: 0
			-----------------------------
			Values:
			1 - Card Optical Monitoring is enabled
			0 - Card Optical Monitoring is disabled
			-----------------------------"
		::= { omtp11tPlusConfigurationEntry 3 }
		
	omtp11tPlusCardSoftReset OBJECT-TYPE
		SYNTAX INTEGER
		MAX-ACCESS read-write
		STATUS current
		DESCRIPTION
			"Valid only as a SET command.
			Reboots the Card, Reconfigures the Card 
			i.e All Configuration Parameter	like Laser State,
			Traffic configuration, Loopback, FEC, optical and 
			signal thresholds, switching mode,
			user choice of line path, TTI messages
			will be restored to previous state
			-----------------------------
			omtp11tPlusInterfaceNumber: 0
			-----------------------------
			Values:
			Dont care, any value
			eg: 0
			-----------------------------"
		::= { omtp11tPlusConfigurationEntry 4 }
		
	omtp11tPlusCardFactoryReset OBJECT-TYPE
		SYNTAX INTEGER
		MAX-ACCESS read-write
		STATUS current
		DESCRIPTION
			"Valid only as a SET command.
			Sets the Card To Factory Default State
			i.e All User Configuration Parameters like Laser State,
			Traffic configuration, Loopback, FEC, optical and 
			signal thresholds, switching mode,
			user choice of line path, TTI messages
			will be set to default state
			-----------------------------
			omtp11tPlusInterfaceNumber: 0
			-----------------------------
			Values:
			Dont care, any value
			eg: 0
			-----------------------------"
		::= { omtp11tPlusConfigurationEntry 5 }
		
	omtp11tPlusCardAccessStatus OBJECT-TYPE
		SYNTAX INTEGER
		MAX-ACCESS read-write
		STATUS current
		DESCRIPTION
			"This property will tell whether the card is 
			accessible from EMS/LCT or not. Turning off the
			accessbility to the card, will not allow the user
			to access any configuration, alarm or performance
			of the card and also turns off fast alarm
			triggering, global alarm led indication
			-----------------------------
			omtp11tPlusInterfaceNumber: 0
			-----------------------------
			Values:
			1 - Card is accessible from EMS/LCT
			0 - Card is inaccessible from EMS/LCT
			-----------------------------"
		::= { omtp11tPlusConfigurationEntry 6 }

	omtp11tPlusSyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that ilarticular server. 
					If we are not providing NTP server IP address 
					then the system will be synced with the NTP server 
					which is already been registered with card. 
					If both are absent then error message will be returned
					-----------------------------
						Interface : 0
					-----------------------------
						If we want to provide NTP server IP address then
						Value should be a valid IP address as shown below
						: 192.168.21.25
						
						If we don't want to provide NTP server address then no
						need to pass any value. 
					---------------------------"
  						
  		::= { omtp11tPlusConfigurationEntry 7 }
  		
  	omtp11tPlusSyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 192.168.21.25
							
						If we don't want to provide NTP server address, then no
						need to ilass any value. 
						---------------------------"
  						
  		::= { omtp11tPlusConfigurationEntry 8 }
  		
  	omtp11tPlusSyncRtcWithSystemTime	 OBJECT-TYPE
		SYNTAX  		DisplayString
  		MAX-ACCESS  	read-write
  		STATUS  		current
  		DESCRIPTION	 	" when we want to manually sync the time value
  						present in RTC with the time value in linux kernel
  						we can use this OID. With this set operation, 
  						the time available with linux kernel will be updated
  						into RTC. It is not required to provide any value for 
  						this operation"
  						
  		::= { omtp11tPlusConfigurationEntry 9 }
  		
  	omtp11tPlusUpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2017-10-31 15:20:44
						---------------------------"
						
  		::= { omtp11tPlusConfigurationEntry 10 }
  		
  	omtp11tPlusUpdateGivenTimeIntoRtc	 OBJECT-TYPE
		SYNTAX  		DisplayString
  		MAX-ACCESS  	read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD H:M:S
						
						Example: 2017-10-31 15:20:44
						---------------------------"
						
  		::= { omtp11tPlusConfigurationEntry 11 }
  		
  	omtp11tPlusSystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { omtp11tPlusConfigurationEntry 12 }

	omtp11tPlusTrafficConfiguration OBJECT-TYPE
		SYNTAX INTEGER
		MAX-ACCESS read-write
		STATUS current
		DESCRIPTION
			"Set or get the traffic configuration for the
			requested port
			-----------------------------
			omtp11tPlusInterfaceNumber:
			1 - CLIENT-1
			2 - LINE-1
			-----------------------------
			Values: 
			00 - Un-configure
			06 - OTU2
			-----------------------------"
		::= { omtp11tPlusConfigurationEntry 41 }
		
	omtp11tPlusLoopbackState OBJECT-TYPE
		SYNTAX INTEGER
		MAX-ACCESS read-write
		STATUS current
		DESCRIPTION
			"Set or get the loopback state for the
			requested port
			-----------------------------
			omtp11tPlusInterfaceNumber:
			1 - CLIENT-1
			2 - LINE-1
			-----------------------------
			Values: 
			00 - No Loopback   
			01 - Near End Loopback
			02 - Far End Loopback
			-----------------------------"
		::= { omtp11tPlusConfigurationEntry 42 }
		
	omtp11tPlusPortSignalMonitorState OBJECT-TYPE
		SYNTAX INTEGER
		MAX-ACCESS read-write
		STATUS current
		DESCRIPTION
			"This property sets or gets the port's signal
			monitoring state. Disabling port signal monitoring 
			will not provide any signal alarms and performances
			information to the user.
			-----------------------------
			omtp11tPlusInterfaceNumber:
			1 - CLIENT-1
			2 - LINE-1
			-----------------------------
			Values:
			1 - Port Signal Monitoring is enabled
			0 - Port Signal Monitoring is disabled
			-----------------------------"

		::= { omtp11tPlusConfigurationEntry 43 }
		
	omtp11tPlusPortOpticalMonitorState OBJECT-TYPE
		SYNTAX INTEGER
		MAX-ACCESS read-write
		STATUS current
		DESCRIPTION
			"This property sets or gets the port's optical
			monitoring state. Disabling port optical monitoring 
			will not provide any optical alarms and performances
			information to the user.
			-----------------------------
			omtp11tPlusInterfaceNumber:
			1 - CLIENT-1
			2 - LINE-1
			-----------------------------
			Values:
			1 - Port Optical Monitoring is enabled
			0 - Port Optical Monitoring is disabled
			-----------------------------"
		::= { omtp11tPlusConfigurationEntry 44 }

	omtp11tPlusClearSignalPerformance OBJECT-TYPE
		SYNTAX INTEGER
		MAX-ACCESS read-write
		STATUS current
		DESCRIPTION
			"Valid only as a SET command.
			Clears signal performance for the requested port
			-----------------------------
			omtp11tPlusInterfaceNumber:
			1 - CLIENT-1
			2 - LINE-1
			-----------------------------
			Values:
			Dont care, any value
			eg: 0
			-----------------------------"
		::= { omtp11tPlusConfigurationEntry 45 }
		
	omtp11tPlusAlsState OBJECT-TYPE
		SYNTAX INTEGER
		MAX-ACCESS read-write
		STATUS current
		DESCRIPTION
			"Set the Automatic Laser Switching(ALS) mode for
			for requested port. Based on the RX LOS state of the
			port, the transmit LASER state will be controlled
			according to the algorithm defined for ALS in
			ITUT 664 Standard
			-----------------------------
			omtp11tPlusInterfaceNumber:
			1 - CLIENT-1
			2 - LINE-1
			-----------------------------
			Values: 
			1 - Enable ALS state
			0 - Disable ALS state
			-----------------------------" 
		::= { omtp11tPlusConfigurationEntry 46 }
		
	omtp11tPlusAlsPulseRepetitionTime OBJECT-TYPE
		SYNTAX INTEGER
		MAX-ACCESS read-write
		STATUS current
		DESCRIPTION
			"Pulse repetition time is the time for automatic 
			restart of XFP LASER once the ALS algorithm starts.
			-----------------------------
			omtp11tPlusInterfaceNumber:
			1 - CLIENT-1
			2 - LINE-1
			-----------------------------
			Values: 
			100 seconds to 300 seconds
			-----------------------------" 
		::= { omtp11tPlusConfigurationEntry 47 }
		
	omtp11tPlusOtuFecConfiguration OBJECT-TYPE
		SYNTAX INTEGER
		MAX-ACCESS read-write
		STATUS current
		DESCRIPTION
			"Set or Get FEC type for requested port configured with
			 OTU2 traffic.
			-----------------------------
			omtp11tPlusInterfaceNumber:
			1 - CLIENT-1
			2 - LINE-1
			-----------------------------
			Values: 
			00 - UFEC (I.7 FEC)
			13 - Reed-Solomon GFEC
			14 - Zero FEC 
			-----------------------------" 
		::= { omtp11tPlusConfigurationEntry 61 }

	omtp11tPlusOtuSignalFailThreshold OBJECT-TYPE
		SYNTAX INTEGER
		MAX-ACCESS read-write
		STATUS current
		DESCRIPTION
			"Set or Get SM Signal Failure 
			Threshold value for the requested port configured with 
			OTU2 traffic.
			-----------------------------
			omtp11tPlusInterfaceNumber:
			1 - CLIENT-1
			2 - LINE-1
			-----------------------------
			Values: 
			03 - 1.E -03
			04 - 1.E -04
			05 - 1.E -05
			-----------------------------" 
		::= { omtp11tPlusConfigurationEntry 62 }
		
	omtp11tPlusOtuSignalDegradeThreshold OBJECT-TYPE
		SYNTAX INTEGER
		MAX-ACCESS read-write
		STATUS current
		DESCRIPTION
			"Set or Get SM Signal Degrade 
			Threshold value for the requested port configured with 
			OTU2 traffic.
			-----------------------------
			omtp11tPlusInterfaceNumber:
			1 - CLIENT-1
			2 - LINE-1
			-----------------------------
			Values:
			05 - 1.E -05
			06 - 1.E -06
			07 - 1.E -07
			08 - 1.E -08
			09 - 1.E -09
			10 - 1.E -10
			-----------------------------" 
		::= { omtp11tPlusConfigurationEntry 63 }
		
	omtp11tPlusOtuAlarmIndicationSignalAlarmInsertion OBJECT-TYPE
		SYNTAX INTEGER
		MAX-ACCESS read-write
		STATUS current
		DESCRIPTION
			"Inserts OTU-AIS maitainance signal for the requested
			port configured with OTU2 traffic.
			-----------------------------
			omtp11tPlusInterfaceNumber:
			1 - CLIENT-1
			2 - LINE-1
			-----------------------------
			Values: 
			0 - Disable Insertion  
			1 - Enable Insertion
			-----------------------------" 
		::= { omtp11tPlusConfigurationEntry 64 }
		
	omtp11tPlusOtuSapiTransmitTraceMessage OBJECT-TYPE
		SYNTAX DisplayString
		MAX-ACCESS read-write
		STATUS current
		DESCRIPTION
			"Set or get the 15 characters SAPI Transmit TTI message
			which is put into the outgoing OTU2 frame. 
			-----------------------------
			omtp11tPlusInterfaceNumber:
			1 - CLIENT-1
			2 - LINE-1
			-----------------------------
			Values:
			eg: 123451234512345
			-----------------------------" 
		::= { omtp11tPlusConfigurationEntry 65 }

	omtp11tPlusOtuDapiTransmitTraceMessage OBJECT-TYPE
		SYNTAX DisplayString
		MAX-ACCESS read-write
		STATUS current
		DESCRIPTION
			"Set or get the 15 characters DAPI Transmit TTI message
			which is put into the outgoing OTU2 frame. 
			-----------------------------
			omtp11tPlusInterfaceNumber:
			1 - CLIENT-1
			2 - LINE-1
			-----------------------------
			Values:
			eg: 123451234512345
			-----------------------------" 
		::= { omtp11tPlusConfigurationEntry 66 }
		
	omtp11tPlusOtuOperatorSpecificTransmitTraceMessage OBJECT-TYPE
		SYNTAX DisplayString
		MAX-ACCESS read-write
		STATUS current
		DESCRIPTION
			"Set or get the 32 characters Operator Specific Transmit
			TTI message which is put into the outgoing OTU2 frame. 
			-----------------------------
			omtp11tPlusInterfaceNumber:
			1 - CLIENT-1
			2 - LINE-1
			-----------------------------
			Values:
			eg: 12345123451234512345123451234500
			-----------------------------" 
		::= { omtp11tPlusConfigurationEntry 67 }
		
	omtp11tPlusOtuSapiExpectedTraceMessage OBJECT-TYPE
		SYNTAX DisplayString
		MAX-ACCESS read-write
		STATUS current
		DESCRIPTION
			"15 characters SM SAPI Expected TTI message - Message
			set here is used for comparison with the message present
			in SM SAPI field of the incoming OTU2 frames.
			-----------------------------
			omtp11tPlusInterfaceNumber:
			1 - CLIENT-1
			2 - LINE-1
			-----------------------------
			Values:
			eg: 123451234512345
			-----------------------------" 
		::= { omtp11tPlusConfigurationEntry 68 }
		
	omtp11tPlusOtuDapiExpectedTraceMessage OBJECT-TYPE
		SYNTAX DisplayString
		MAX-ACCESS read-write
		STATUS current
		DESCRIPTION
			"15 characters SM DAPI Expected TTI message - Message
			set here is used for comparison with the message present
			in SM DAPI field of the incoming OTU2 frames.
			-----------------------------
			omtp11tPlusInterfaceNumber:
			1 - CLIENT-1
			2 - LINE-1
			-----------------------------
			Values:
			eg: 123451234512345
			-----------------------------" 
		::= { omtp11tPlusConfigurationEntry 69 }

	omtp11tPlusOtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU2 frames.
			-----------------------------
			omtp11tPlusInterfaceNumber:
			1 - CLIENT-1
			2 - LINE-1
			-----------------------------
			Values:
			eg: 12345123451234512345123451234500
			-----------------------------" 
		::= { omtp11tPlusConfigurationEntry 70 }
		
	omtp11tPlusOtuSapiReceivedTraceMessage OBJECT-TYPE
		SYNTAX DisplayString
		MAX-ACCESS read-only
		STATUS current
		DESCRIPTION
			"Gets the 15 characters SAPI TTI message
			which is extracted from the incoming OTU2
			data stream.
			-----------------------------
			omtp11tPlusInterfaceNumber:
			1 - CLIENT-1
			2 - LINE-1
			-----------------------------
			Values:
			eg: 123451234512345
			-----------------------------" 
		::= { omtp11tPlusConfigurationEntry 71 }

	omtp11tPlusOtuDapiReceivedTraceMessage OBJECT-TYPE
		SYNTAX DisplayString
		MAX-ACCESS read-only
		STATUS current
		DESCRIPTION
			"Gets the 15 characters DAPI TTI message
			which is extracted from the incoming OTU2 data
			stream.
			-----------------------------
			omtp11tPlusInterfaceNumber:
			1 - CLIENT-1
			2 - LINE-1
			-----------------------------
			Values:
			eg: 123451234512345
			-----------------------------" 
		::= { omtp11tPlusConfigurationEntry 72 }
		
	omtp11tPlusOtuOperatorSpecificReceivedTraceMessage OBJECT-TYPE
		SYNTAX DisplayString
		MAX-ACCESS read-only
		STATUS current
		DESCRIPTION
			"Gets the 32 characters DAPI TTI message
			which is extracted from the incoming OTU2 data
			stream. 
			-----------------------------
			omtp11tPlusInterfaceNumber:
			1 - CLIENT-1
			2 - LINE-1
			-----------------------------
			Values:
			eg: 12345123451234512345123451234500
			-----------------------------" 
		::= { omtp11tPlusConfigurationEntry 73 }

	omtp11tPlusOduSignalFailThreshold OBJECT-TYPE
		SYNTAX INTEGER
		MAX-ACCESS read-write
		STATUS current
		DESCRIPTION
			"Set or Get PM Signal Failure 
			Threshold value for the requested port configured with 
			OTU2 traffic.
			-----------------------------
			omtp11tPlusInterfaceNumber:
			1 - CLIENT-1
			2 - LINE-1
			-----------------------------
			Values: 
			03 - 1.E -03
			04 - 1.E -04
			05 - 1.E -05
			-----------------------------" 
		::= { omtp11tPlusConfigurationEntry 81 }
		
	omtp11tPlusOduSignalDegradeThreshold OBJECT-TYPE
		SYNTAX INTEGER
		MAX-ACCESS read-write
		STATUS current
		DESCRIPTION
			"Set or Get PM Signal Degrade 
			Threshold value for the requested port configured with 
			OTU2 traffic.
			-----------------------------
			omtp11tPlusInterfaceNumber:
			1 - CLIENT-1
			2 - LINE-1
			-----------------------------
			Values:
			05 - 1.E -05
			06 - 1.E -06
			07 - 1.E -07
			08 - 1.E -08
			09 - 1.E -09
			10 - 1.E -10
			-----------------------------" 
		::= { omtp11tPlusConfigurationEntry 82 }
		
	omtp11tPlusOduAlarmIndicationSignalAlarmInsertion OBJECT-TYPE
		SYNTAX INTEGER
		MAX-ACCESS read-write
		STATUS current
		DESCRIPTION
			"Inserts ODU-AIS maintenance signal for the requested 
			port configured with OTU2 traffic.
			-----------------------------
			omtp11tPlusInterfaceNumber:
			1 - CLIENT-1
			2 - LINE-1
			-----------------------------
			Values: 
			1 - Enable Insertion
			0 - Disable Insertion  
			-----------------------------"
		::= { omtp11tPlusConfigurationEntry 83 }

	omtp11tPlusOduLockedDefectAlarmInsertion OBJECT-TYPE
		SYNTAX INTEGER
		MAX-ACCESS read-write
		STATUS current
		DESCRIPTION
			"Inserts ODU-LCK maintenance signal for the requested 
			port configured with OTU2 traffic.
			-----------------------------
			omtp11tPlusInterfaceNumber:
			1 - CLIENT-1
			2 - LINE-1
			-----------------------------
			Values: 
			1 - Enable Insertion
			0 - Disable Insertion  
			-----------------------------"
		::= { omtp11tPlusConfigurationEntry 84 }
		
	omtp11tPlusOduOpenConnectionIndicationAlarmInsertion OBJECT-TYPE
		SYNTAX INTEGER
		MAX-ACCESS read-write
		STATUS current
		DESCRIPTION
			"Inserts ODU-OCI maintenance signal for the requested 
			port configured with OTU2 traffic.
			-----------------------------
			omtp11tPlusInterfaceNumber:
			1 - CLIENT-1
			2 - LINE-1
			-----------------------------
			Values: 
			1 - Enable Insertion
			0 - Disable Insertion  
			-----------------------------"
		::= { omtp11tPlusConfigurationEntry 85 }
		
	omtp11tPlusOduSapiTransmitTraceMessage OBJECT-TYPE
		SYNTAX DisplayString
		MAX-ACCESS read-write
		STATUS current
		DESCRIPTION
			"Set or get the 15 characters SAPI Transmit TTI message
			which is put into the outgoing OTU2 frame at the PM level. 
			-----------------------------
			omtp11tPlusInterfaceNumber:
			1 - CLIENT-1
			2 - LINE-1
			-----------------------------
			Values:
			eg: 123451234512345
			-----------------------------" 
		::= { omtp11tPlusConfigurationEntry 86 }
		
	omtp11tPlusOduDapiTransmitTraceMessage OBJECT-TYPE
		SYNTAX DisplayString
		MAX-ACCESS read-write
		STATUS current
		DESCRIPTION
			"Set or get the 15 characters DAPI Transmit TTI message
			which is put into the outgoing OTU2 frame at the PM level. 
			-----------------------------
			omtp11tPlusInterfaceNumber:
			1 - CLIENT-1
			2 - LINE-1
			-----------------------------
			Values:
			eg: 123451234512345
			-----------------------------" 
		::= { omtp11tPlusConfigurationEntry 87 }
		
	omtp11tPlusOduOperatorSpecificTransmitTraceMessage OBJECT-TYPE
		SYNTAX DisplayString
		MAX-ACCESS read-write
		STATUS current
		DESCRIPTION
			"Set or get the 32 characters Operator Specific Transmit
			TTI message which is put into the outgoing OTU2 frame at
			the PM level. 
			-----------------------------
			omtp11tPlusInterfaceNumber:
			1 - CLIENT-1
			2 - LINE-1
			-----------------------------
			Values:
			eg: 12345123451234512345123451234500
			-----------------------------" 
		::= { omtp11tPlusConfigurationEntry 88 }
		
	omtp11tPlusOduSapiExpectedTraceMessage OBJECT-TYPE
		SYNTAX DisplayString
		MAX-ACCESS read-write
		STATUS current
		DESCRIPTION
			"15 characters PM SAPI Expected TTI message - Message
			set here is used for comparison with the message present
			in PM SAPI field of the incoming OTU2 frames.
			-----------------------------
			omtp11tPlusInterfaceNumber:
			1 - CLIENT-1
			2 - LINE-1
			-----------------------------
			Values:
			eg: 123451234512345
			-----------------------------" 
		::= { omtp11tPlusConfigurationEntry 89 }

	omtp11tPlusOduDapiExpectedTraceMessage OBJECT-TYPE
		SYNTAX DisplayString
		MAX-ACCESS read-write
		STATUS current
		DESCRIPTION
			"15 characters PM DAPI Expected TTI message - Message
			set here is used for comparison with the message present
			in PM DAPI field of the incoming OTU2 frames.
			-----------------------------
			omtp11tPlusInterfaceNumber:
			1 - CLIENT-1
			2 - LINE-1
			-----------------------------
			Values:
			eg: 123451234512345
			-----------------------------" 
		::= { omtp11tPlusConfigurationEntry 90 }
		
	omtp11tPlusOduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU2 frames.
			-----------------------------
			omtp11tPlusInterfaceNumber:
			1 - CLIENT-1
			2 - LINE-1
			-----------------------------
			Values:
			eg: 12345123451234512345123451234500
			-----------------------------" 
		::= { omtp11tPlusConfigurationEntry 91 }

	omtp11tPlusOduSapiReceivedTraceMessage OBJECT-TYPE
		SYNTAX DisplayString
		MAX-ACCESS read-only
		STATUS current
		DESCRIPTION
			"Gets the 15 characters SAPI TTI message
			which is extracted from the incoming OTU2 data
			stream.
			-----------------------------
			omtp11tPlusInterfaceNumber:
			1 - CLIENT-1
			2 - LINE-1
			-----------------------------
			Values:
			eg: 123451234512345
			-----------------------------" 
		::= { omtp11tPlusConfigurationEntry 92 }

	omtp11tPlusOduDapiReceivedTraceMessage OBJECT-TYPE
		SYNTAX DisplayString
		MAX-ACCESS read-only
		STATUS current
		DESCRIPTION
			"Gets the 15 characters DAPI TTI message
			which is extracted from the incoming OTU2
			data stream.
			-----------------------------
			omtp11tPlusInterfaceNumber:
			1 - CLIENT-1
			2 - LINE-1
			-----------------------------
			Values:
			eg: 123451234512345
			-----------------------------" 
		::= {omtp11tPlusConfigurationEntry 93 }
		
	omtp11tPlusOduOperatorSpecificReceivedTraceMessage OBJECT-TYPE
		SYNTAX DisplayString
		MAX-ACCESS read-only
		STATUS current
		DESCRIPTION
			"Gets the 32 characters DAPI TTI message
			which is extracted from the incoming OTU2
			data stream.
			-----------------------------
			omtp11tPlusInterfaceNumber:
			1 - CLIENT-1
			2 - LINE-1
			-----------------------------
			Values:
			eg: 12345123451234512345123451234500
			-----------------------------" 
		::= { omtp11tPlusConfigurationEntry 94 }

	omtp11tPlusOpuTransmitPayloadType OBJECT-TYPE
		SYNTAX INTEGER
		MAX-ACCESS read-only
		STATUS current
		DESCRIPTION
			"A one-byte payload type signal is defined in the PSI[0]
			byte of the payload structure identifier to indicate the
			composition of the OPUk signal. Gets the payload type
			that is put into the outgoing OTU2 datastream.
			-----------------------------
			omtp11tPlusInterfaceNumber:
			1 - CLIENT-1
			2 - LINE-1
			-----------------------------
			Values:
			eg: 20
			-----------------------------" 
		::= { omtp11tPlusConfigurationEntry 95 }
		
	omtp11tPlusOpuReceivedPayloadType OBJECT-TYPE
		SYNTAX INTEGER
		MAX-ACCESS read-only
		STATUS current
		DESCRIPTION
			"Gives Payload Type present in Opu overhead that tells
			about the mapping informations.
			-----------------------------
			omtp11tPlusInterfaceNumber:
			1 - CLIENT-1
			2 - LINE-1
			-----------------------------
			Values:
			eg: 21
			-----------------------------" 
		::= { omtp11tPlusConfigurationEntry 96 }
		
	omtp11tPlusTunableXfpLaserWavelength OBJECT-TYPE
		SYNTAX INTEGER
		MAX-ACCESS read-write
		STATUS current
		DESCRIPTION
			"Set or Get the XFP wavelength for the requested port
			-----------------------------
			omtp11tPlusInterfaceNumber:
			1 - CLIENT-1
			2 - LINE-1
			-----------------------------
			Values:
			eg: 1529.944
			-----------------------------" 
		::= { omtp11tPlusConfigurationEntry 113 }
		
	omtp11tPlusTunableXfpLaserChannelNumber OBJECT-TYPE
		SYNTAX INTEGER
		MAX-ACCESS read-write
		STATUS current
		DESCRIPTION
			"Set or Get the XFP Channel Number for the the requested
			port
			-----------------------------
			omtp11tPlusInterfaceNumber:
			1 - CLIENT-1
			2 - LINE-1
			-----------------------------
			Values:
			eg: 10
			-----------------------------" 
		::= { omtp11tPlusConfigurationEntry 114 }

	omtp11tPlusXfpLaserState OBJECT-TYPE
		SYNTAX INTEGER
		MAX-ACCESS read-write
		STATUS current
		DESCRIPTION
			"Set or Get the XFP LASER state for the the requested
			port
			-----------------------------
			omtp11tPlusInterfaceNumber:
			1 - CLIENT-1
			2 - LINE-1
			-----------------------------
			Values: 
			00 - Laser OFF
			01 - Laser ON
			-----------------------------" 
		::= { omtp11tPlusConfigurationEntry 115 }
		
	omtp11tPlusXfpReset OBJECT-TYPE
		SYNTAX INTEGER
		MAX-ACCESS read-write
		STATUS current
		DESCRIPTION
			"Valid only as a SET command.
			Resets the XFP.
			-----------------------------
			omtp11tPlusInterfaceNumber:
			1 - CLIENT-1
			2 - LINE-1
			-----------------------------
			Values: 
			Dont care, any value
			eg: 0
			-----------------------------" 
		::= { omtp11tPlusConfigurationEntry 116 }
		
	omtp11tPlusXfpPowerDownMode OBJECT-TYPE
		SYNTAX INTEGER
		MAX-ACCESS read-write
		STATUS current
		DESCRIPTION
			"Valid only as a SET command.
			Sets the XFP in the Power Down mode i.e. low power 
			consumption mode.
			-----------------------------
			omtp11tPlusInterfaceNumber:
			1 - CLIENT-1
			2 - LINE-1
			-----------------------------
			Values: 
			01 - power down XFP
			-----------------------------" 
		::= { omtp11tPlusConfigurationEntry 117 }
		
	omtp11tPlusXfpLineLoopback OBJECT-TYPE
		SYNTAX INTEGER
		MAX-ACCESS read-write
		STATUS current
		DESCRIPTION
			"Set or Get line loopback in XFP			
			-----------------------------
			omtp11tPlusInterfaceNumber:
			1 - CLIENT-1
			2 - LINE-1
			-----------------------------
			Values: 
			1 - Enable XFP Line Loopback
			0 - Disable XFP Line Loopback
			-----------------------------" 
		::= { omtp11tPlusConfigurationEntry 118 }

	omtp11tPlusXfpXfiLoopback OBJECT-TYPE
		SYNTAX INTEGER
		MAX-ACCESS read-write
		STATUS current
		DESCRIPTION
			"Set or Get Xfi loopback in XFP			
			-----------------------------
			omtp11tPlusInterfaceNumber:
			1 - CLIENT-1
			2 - LINE-1
			-----------------------------
			Values: 
			1 - Enable XFP Xfi Loopback
			0 - Disable XFP Xfi Loopback
			-----------------------------" 
		::= { omtp11tPlusConfigurationEntry 119 }
		
	omtp11tPlusXfpAmplitudeThresholdOfReceiverForFecControl OBJECT-TYPE
		SYNTAX INTEGER
		MAX-ACCESS read-write
		STATUS current
		DESCRIPTION
			" Set or Get amplitude threshold of receiver for FEC control			
			-----------------------------
			omtp11tPlusInterfaceNumber:
			1 - CLIENT-1
			2 - LINE-1
			-----------------------------
			Values: 
			eg: Reserved
			-----------------------------" 
		::= { omtp11tPlusConfigurationEntry 120 }
		
	omtp11tPlusXfpPhaseInEyeDiagramForFecControl OBJECT-TYPE
		SYNTAX INTEGER
		MAX-ACCESS read-write
		STATUS current
		DESCRIPTION
			" Set or Get XFP phase in eye diagram for FEC control			
			-----------------------------
			omtp11tPlusInterfaceNumber:
			1 - CLIENT-1
			2 - LINE-1
			-----------------------------
			Values: 
			eg: Reserved
			-----------------------------" 
		::= { omtp11tPlusConfigurationEntry 121 }
		
	omtp11tPlusXfpSystemReportingBer OBJECT-TYPE
		SYNTAX INTEGER
		MAX-ACCESS read-write
		STATUS current
		DESCRIPTION
			" Set or Get XFP system reporting BER			
			-----------------------------
			omtp11tPlusInterfaceNumber:
			1 - CLIENT-1
			2 - LINE-1
			-----------------------------
			Values: 
			eg: Reserved
			-----------------------------" 
		::= { omtp11tPlusConfigurationEntry 122 }

	omtp11tPlusXfpHighTemperatureAlarmThreshold OBJECT-TYPE
		SYNTAX DisplayString
		MAX-ACCESS read-write
		STATUS current
		DESCRIPTION
			"Set or Get High Temperature Alarm Threshold
			(in degree celsius) for the requested port
			-----------------------------
			omtp11tPlusInterfaceNumber:
			1 - CLIENT-1
			2 - LINE-1
			-----------------------------
			Values: 
			eg: 65 
			-----------------------------" 
		::= { omtp11tPlusConfigurationEntry 131 }
		
	omtp11tPlusXfpLowTemperatureAlarmThreshold OBJECT-TYPE
		SYNTAX DisplayString
		MAX-ACCESS read-write
		STATUS current
		DESCRIPTION
			"Set or Get Low Temperature Alarm Threshold
			(in degree celsius) for the requested port
			-----------------------------
			omtp11tPlusInterfaceNumber:
			1 - CLIENT-1
			2 - LINE-1
			-----------------------------
			Values: 
			eg: 5 
			-----------------------------" 
		::= { omtp11tPlusConfigurationEntry 132 }
		
	omtp11tPlusXfpHighTemperatureWarningThreshold OBJECT-TYPE
		SYNTAX DisplayString
		MAX-ACCESS read-write
		STATUS current
		DESCRIPTION
			"Set or Get High Temperature Warning Threshold
			(in degree celsius) for the requested port
			-----------------------------
			omtp11tPlusInterfaceNumber:
			1 - CLIENT-1
			2 - LINE-1
			-----------------------------
			Values: 
			eg: 60 
			-----------------------------"
		::= { omtp11tPlusConfigurationEntry 133 }
		
	omtp11tPlusXfpLowTemperatureWarningThreshold OBJECT-TYPE
		SYNTAX DisplayString
		MAX-ACCESS read-write
		STATUS current
		DESCRIPTION
			"Set or Get Low Temperature Warning Threshold
			(in degree celsius) for the requested port
			-----------------------------
			omtp11tPlusInterfaceNumber:
			1 - CLIENT-1
			2 - LINE-1
			-----------------------------
			Values: 
			eg: 10 
			-----------------------------"
		::= { omtp11tPlusConfigurationEntry 134 }

	omtp11tPlusXfpHighBiasCurrentAlarmThreshold OBJECT-TYPE
		SYNTAX DisplayString
		MAX-ACCESS read-write
		STATUS current
		DESCRIPTION
			"Set or Get High Bias Current Alarm Threshold
			(in milli ampere) for the requested port
			-----------------------------
			omtp11tPlusInterfaceNumber:
			1 - CLIENT-1
			2 - LINE-1
			-----------------------------
			Values:
			eg: 35.6
			-----------------------------"			
		::= { omtp11tPlusConfigurationEntry 135 }
		
	omtp11tPlusXfpLowBiasCurrentAlarmThreshold OBJECT-TYPE
		SYNTAX DisplayString
		MAX-ACCESS read-write
		STATUS current
		DESCRIPTION
			"Set or Get Low Bias Current Alarm Threshold
			(in milli ampere) for the requested port
			-----------------------------
			omtp11tPlusInterfaceNumber:
			1 - CLIENT-1
			2 - LINE-1
			-----------------------------
			Values:
			eg: 31.1
			-----------------------------"
		::= { omtp11tPlusConfigurationEntry 136 }
		
	omtp11tPlusXfpHighBiasCurrentWarningThreshold OBJECT-TYPE
		SYNTAX DisplayString
		MAX-ACCESS read-write
		STATUS current
		DESCRIPTION
			"Set or Get High Bias Current Warning Threshold
			(in milli ampere) for the requested port
			-----------------------------
			omtp11tPlusInterfaceNumber:
			1 - CLIENT-1
			2 - LINE-1
			-----------------------------
			Values:
			eg: 34.5
			-----------------------------"
		::= { omtp11tPlusConfigurationEntry 137 }
		
	omtp11tPlusXfpLowBiasCurrentWarningThreshold OBJECT-TYPE
		SYNTAX DisplayString
		MAX-ACCESS read-write
		STATUS current
		DESCRIPTION
			"Set or Get Low Bias Current Warning Threshold
			(in milli ampere) for the requested port
			-----------------------------
			omtp11tPlusInterfaceNumber:
			1 - CLIENT-1
			2 - LINE-1
			-----------------------------
			Values:
			eg: 32.8
			-----------------------------"
		::= { omtp11tPlusConfigurationEntry 138 }
		
	omtp11tPlusXfpInputHighPowerAlarmThreshold OBJECT-TYPE
		SYNTAX DisplayString
		MAX-ACCESS read-write
		STATUS current
		DESCRIPTION
			"Set or Get Input High Power Alarm Threshold
			(in dbm) for the requested port
			-----------------------------
			omtp11tPlusInterfaceNumber:
			1 - CLIENT-1
			2 - LINE-1
			-----------------------------
			Values:
			eg: -9.1
			-----------------------------"
		::= { omtp11tPlusConfigurationEntry 139 }

	omtp11tPlusXfpInputLowPowerAlarmThreshold OBJECT-TYPE
		SYNTAX DisplayString
		MAX-ACCESS read-write
		STATUS current
		DESCRIPTION
			"Set or Get Input Low Power Alarm Threshold
			(in dbm) for the requested port
			-----------------------------
			omtp11tPlusInterfaceNumber:
			1 - CLIENT-1
			2 - LINE-1
			-----------------------------
			Values:
			eg: -35.6
			-----------------------------"
		::= { omtp11tPlusConfigurationEntry 140 }
		
	omtp11tPlusXfpInputHighPowerWarningThreshold OBJECT-TYPE
		SYNTAX DisplayString
		MAX-ACCESS read-write
		STATUS current
		DESCRIPTION
			"Set or Get Input High Power Warning Threshold
			(in dbm) for the requested port
			-----------------------------
			omtp11tPlusInterfaceNumber:
			1 - CLIENT-1
			2 - LINE-1
			-----------------------------
			Values:
			eg: -11.2
			-----------------------------"
		::= { omtp11tPlusConfigurationEntry 141 }
		
	omtp11tPlusXfpInputLowPowerWarningThreshold OBJECT-TYPE
		SYNTAX DisplayString
		MAX-ACCESS read-write
		STATUS current
		DESCRIPTION
			"Set or Get Input Low Power Warning Threshold
			(in dbm) for the requested port
			-----------------------------
			omtp11tPlusInterfaceNumber:
			1 - CLIENT-1
			2 - LINE-1
			-----------------------------
			Values:
			eg: -31.3
			-----------------------------"
		::= { omtp11tPlusConfigurationEntry 142 }
		
	omtp11tPlusXfpOutputHighPowerAlarmThreshold OBJECT-TYPE
		SYNTAX DisplayString
		MAX-ACCESS read-write
		STATUS current
		DESCRIPTION
			"Set or Get Output High Power Alarm Threshold
			(in dbm) for the requested port
			-----------------------------
			omtp11tPlusInterfaceNumber:
			1 - CLIENT-1
			2 - LINE-1
			-----------------------------
			Values:
			eg: +2.0
			-----------------------------"
		::= { omtp11tPlusConfigurationEntry 143 }

	omtp11tPlusXfpOutputLowPowerAlarmThreshold OBJECT-TYPE
		SYNTAX DisplayString
		MAX-ACCESS read-write
		STATUS current
		DESCRIPTION
			"Set or Get Output Low Power Alarm Threshold
			(in dbm) for the requested port
			-----------------------------
			omtp11tPlusInterfaceNumber:
			1 - CLIENT-1
			2 - LINE-1
			-----------------------------
			Values:
			eg: -3.5
			-----------------------------"
		::= { omtp11tPlusConfigurationEntry 144 }
		
	omtp11tPlusXfpOutputHighPowerWarningThreshold OBJECT-TYPE
		SYNTAX DisplayString
		MAX-ACCESS read-write
		STATUS current
		DESCRIPTION
			"Set or Get Output High Power Warning Threshold
			(in dbm) for the requested port
			-----------------------------
			omtp11tPlusInterfaceNumber:
			1 - CLIENT-1
			2 - LINE-1
			-----------------------------
			Values:
			eg: +1.3
			-----------------------------"
		::= { omtp11tPlusConfigurationEntry 145 }
		
	omtp11tPlusXfpOutputLowPowerWarningThreshold OBJECT-TYPE
		SYNTAX DisplayString
		MAX-ACCESS read-write
		STATUS current
		DESCRIPTION
			"Set or Get Output Low Power Warning Threshold
			(in dbm) for the requested port
			-----------------------------
			omtp11tPlusInterfaceNumber:
			1 - CLIENT-1
			2 - LINE-1
			-----------------------------
			Values:
			eg: -2.5
			-----------------------------"
		::= { omtp11tPlusConfigurationEntry 146 }
		
	omtp11tPlusXfpHighSupplyVoltageAlarmThreshold OBJECT-TYPE
		SYNTAX DisplayString
		MAX-ACCESS read-write
		STATUS current
		DESCRIPTION
			"Set or Get High Supply Voltage Alarm Threshold
			(in volts) for the requested port
			-----------------------------
			omtp11tPlusInterfaceNumber:
			1 - CLIENT-1
			2 - LINE-1
			-----------------------------
			Values:
			eg: +3.3
			-----------------------------"
		::= { omtp11tPlusConfigurationEntry 147 }

	omtp11tPlusXfpLowSupplyVoltageAlarmThreshold OBJECT-TYPE
		SYNTAX DisplayString
		MAX-ACCESS read-write
		STATUS current
		DESCRIPTION
			"Set or Get Low Supply Voltage Alarm Threshold
			(in volts) for the requested port
			-----------------------------
			omtp11tPlusInterfaceNumber:
			1 - CLIENT-1
			2 - LINE-1
			-----------------------------
			Values:
			eg: +3.0
			-----------------------------"
		::= { omtp11tPlusConfigurationEntry 148 }
		
	omtp11tPlusXfpHighSupplyVoltageWarningThreshold OBJECT-TYPE
		SYNTAX DisplayString
		MAX-ACCESS read-write
		STATUS current
		DESCRIPTION
			"Set or Get High Supply Voltage Warning Threshold
			(in volts) for the requested port
			-----------------------------
			omtp11tPlusInterfaceNumber:
			1 - CLIENT-1
			2 - LINE-1
			-----------------------------
			Values:
			eg: +3.2
			-----------------------------"
		::= { omtp11tPlusConfigurationEntry 149 }
		
	omtp11tPlusXfpLowSupplyVoltageWarningThreshold OBJECT-TYPE
		SYNTAX DisplayString
		MAX-ACCESS read-write
		STATUS current
		DESCRIPTION
			"Set or Get Low Supply Voltage Warning Threshold
			(in volts) for the requested port
			-----------------------------
			omtp11tPlusInterfaceNumber:
			1 - CLIENT-1
			2 - LINE-1
			-----------------------------
			Values:
			eg: +3.1
			-----------------------------"
		::= { omtp11tPlusConfigurationEntry 150 }
		
	omtp11tPlusXfpInputPowerFailureAlarmInhibit OBJECT-TYPE
	      SYNTAX  INTEGER
	      MAX-ACCESS  read-write
	      STATUS  current
	      DESCRIPTION
			"Inhibits OMTP11T-PLUS XFP Input Power Failure Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 201 }

	omtp11tPlusXfpOutputPowerFailureAlarmInhibit OBJECT-TYPE
	      SYNTAX  INTEGER
	      MAX-ACCESS  read-write
	      STATUS  current
	      DESCRIPTION
			"Inhibits OMTP11T-PLUS XFP Output Power Failure Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 202 }

	omtp11tPlusXfpHighTemperatureAlarmInhibit OBJECT-TYPE
	      SYNTAX  INTEGER
	      MAX-ACCESS  read-write
	      STATUS  current
	      DESCRIPTION
			"Inhibits OMTP11T-PLUS XFP High Temperature Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 203 }

	omtp11tPlusXfpLowTemperatureAlarmInhibit OBJECT-TYPE
	      SYNTAX  INTEGER
	      MAX-ACCESS  read-write
	      STATUS  current
	      DESCRIPTION
			"Inhibits OMTP11T-PLUS XFP Low Temperature Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 204 }

	omtp11tPlusXfpHighTemperatureWarningInhibit OBJECT-TYPE
	      SYNTAX  INTEGER
	      MAX-ACCESS  read-write
	      STATUS  current
	      DESCRIPTION
			"Inhibits OMTP11T-PLUS XFP High Temperature Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 205 }

	omtp11tPlusXfpLowTemperatureWarningInhibit OBJECT-TYPE
	      SYNTAX  INTEGER
	      MAX-ACCESS  read-write
	      STATUS  current
	      DESCRIPTION
			"Inhibits OMTP11T-PLUS XFP Low Temperature Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 206 }

	omtp11tPlusXfpHighBiasCurrentAlarmInhibit OBJECT-TYPE
	      SYNTAX  INTEGER
	      MAX-ACCESS  read-write
	      STATUS  current
	      DESCRIPTION
			"Inhibits OMTP11T-PLUS XFP High Bias Current Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 207 }

	omtp11tPlusXfpLowBiasCurrentAlarmInhibit OBJECT-TYPE
	      SYNTAX  INTEGER
	      MAX-ACCESS  read-write
	      STATUS  current
	      DESCRIPTION
			"Inhibits OMTP11T-PLUS XFP Low Bias Current Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 208 }

	omtp11tPlusXfpHighBiasCurrentWarningInhibit OBJECT-TYPE
	      SYNTAX  INTEGER
	      MAX-ACCESS  read-write
	      STATUS  current
	      DESCRIPTION
			"Inhibits OMTP11T-PLUS XFP High Bias Current Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 209 }

	omtp11tPlusXfpLowBiasCurrentWarningInhibit OBJECT-TYPE
	      SYNTAX  INTEGER
	      MAX-ACCESS  read-write
	      STATUS  current
	      DESCRIPTION
			"Inhibits OMTP11T-PLUS XFP Low Bias Current Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 210 }

	omtp11tPlusXfpInputHighPowerAlarmInhibit OBJECT-TYPE
	      SYNTAX  INTEGER
	      MAX-ACCESS  read-write
	      STATUS  current
	      DESCRIPTION
			"Inhibits OMTP11T-PLUS XFP Input High Power Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 211 }

	omtp11tPlusXfpInputLowPowerAlarmInhibit OBJECT-TYPE
	      SYNTAX  INTEGER
	      MAX-ACCESS  read-write
	      STATUS  current
	      DESCRIPTION
			"Inhibits OMTP11T-PLUS XFP Input Low Power Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 212 }

	omtp11tPlusXfpInputHighPowerWarningInhibit OBJECT-TYPE
	      SYNTAX  INTEGER
	      MAX-ACCESS  read-write
	      STATUS  current
	      DESCRIPTION
			"Inhibits OMTP11T-PLUS XFP Input High Power Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 213 }

	omtp11tPlusXfpInputLowPowerWarningInhibit OBJECT-TYPE
	      SYNTAX  INTEGER
	      MAX-ACCESS  read-write
	      STATUS  current
	      DESCRIPTION
			"Inhibits OMTP11T-PLUS XFP Input Low Power Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 214 }

	omtp11tPlusXfpOutputHighPowerAlarmInhibit OBJECT-TYPE
	      SYNTAX  INTEGER
	      MAX-ACCESS  read-write
	      STATUS  current
	      DESCRIPTION
			"Inhibits OMTP11T-PLUS XFP Output High Power Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 215 }

	omtp11tPlusXfpOutputLowPowerAlarmInhibit OBJECT-TYPE
	      SYNTAX  INTEGER
	      MAX-ACCESS  read-write
	      STATUS  current
	      DESCRIPTION
			"Inhibits OMTP11T-PLUS XFP Output Low Power Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 216 }

	omtp11tPlusXfpOutputHighPowerWarningInhibit OBJECT-TYPE
	      SYNTAX  INTEGER
	      MAX-ACCESS  read-write
	      STATUS  current
	      DESCRIPTION
			"Inhibits OMTP11T-PLUS XFP Output High Power Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 217 }

	omtp11tPlusXfpOutputLowPowerWarningInhibit OBJECT-TYPE
	      SYNTAX  INTEGER
	      MAX-ACCESS  read-write
	      STATUS  current
	      DESCRIPTION
			"Inhibits OMTP11T-PLUS XFP Output Low Power Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 218 }

	omtp11tPlusXfpHighSupplyVoltageAlarmInhibit OBJECT-TYPE
	      SYNTAX  INTEGER
	      MAX-ACCESS  read-write
	      STATUS  current
	      DESCRIPTION
			"Inhibits OMTP11T-PLUS XFP High Supply Voltage Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 219 }

	omtp11tPlusXfpLowSupplyVoltageAlarmInhibit OBJECT-TYPE
	      SYNTAX  INTEGER
	      MAX-ACCESS  read-write
	      STATUS  current
	      DESCRIPTION
			"Inhibits OMTP11T-PLUS XFP Low Supply Voltage Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 220 }

	omtp11tPlusXfpHighSupplyVoltageWarningInhibit OBJECT-TYPE
	      SYNTAX  INTEGER
	      MAX-ACCESS  read-write
	      STATUS  current
	      DESCRIPTION
			"Inhibits OMTP11T-PLUS XFP High Supply Voltage Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 221 }

	omtp11tPlusXfpLowSupplyVoltageWarningInhibit OBJECT-TYPE
	      SYNTAX  INTEGER
	      MAX-ACCESS  read-write
	      STATUS  current
	      DESCRIPTION
			"Inhibits OMTP11T-PLUS XFP Low Supply Voltage Warning
			for the requested port
			-----------------------------
			omtp11tPlusInterfaceNumber:
			1 - CLIENT-1
			2 - LINE-1
			-----------------------------
			Values:
			1 - Inhibit
			0 - Do Not Inhibit
			-----------------------------"
		::= { omtp11tPlusConfigurationEntry 222 }

	omtp11tPlusXfpPresenceAbsenceNotificationInhibit OBJECT-TYPE
	      SYNTAX  INTEGER
	      MAX-ACCESS  read-write
	      STATUS  current
	      DESCRIPTION
			"Inhibits OMTP11T-PLUS XFP Presence Absence Notification
			for the requested port
			-----------------------------
			omtp11tPlusInterfaceNumber:
			1 - CLIENT-1
			2 - LINE-1
			-----------------------------
			Values:
			1 - Inhibit
			0 - Do Not Inhibit
			-----------------------------"
		::= { omtp11tPlusConfigurationEntry 223 }

	omtp11tPlusOtuLossOfSignalAlarmInhibit OBJECT-TYPE
	      SYNTAX  INTEGER
	      MAX-ACCESS  read-write
	      STATUS  current
	      DESCRIPTION
			"Inhibits OMTP11T-PLUS OTU Loss Of Signal Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 231 }

	omtp11tPlusOtuLossOfFrameAlarmInhibit OBJECT-TYPE
	      SYNTAX  INTEGER
	      MAX-ACCESS  read-write
	      STATUS  current
	      DESCRIPTION
			"Inhibits OMTP11T-PLUS OTU Loss Of Frame Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 232 }

	omtp11tPlusOtuOutOfFrameAlarmInhibit OBJECT-TYPE
	      SYNTAX  INTEGER
	      MAX-ACCESS  read-write
	      STATUS  current
	      DESCRIPTION
			"Inhibits OMTP11T-PLUS OTU Out Of Frame Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 233 }

	omtp11tPlusOtuLossOfMultiFrameAlarmInhibit OBJECT-TYPE
	      SYNTAX  INTEGER
	      MAX-ACCESS  read-write
	      STATUS  current
	      DESCRIPTION
			"Inhibits OMTP11T-PLUS OTU Loss Of Multi Frame Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 234 }

	omtp11tPlusOtuOutOfMultiFrameAlarmInhibit OBJECT-TYPE
	      SYNTAX  INTEGER
	      MAX-ACCESS  read-write
	      STATUS  current
	      DESCRIPTION
			"Inhibits OMTP11T-PLUS OTU Out Of Multi Frame Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 235 }

	omtp11tPlusOtuSignalFailAlarmInhibit OBJECT-TYPE
	      SYNTAX  INTEGER
	      MAX-ACCESS  read-write
	      STATUS  current
	      DESCRIPTION
			"Inhibits OMTP11T-PLUS OTU Signal Fail Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 236 }

	omtp11tPlusOtuSignalDegradeAlarmInhibit OBJECT-TYPE
	      SYNTAX  INTEGER
	      MAX-ACCESS  read-write
	      STATUS  current
	      DESCRIPTION
			"Inhibits OMTP11T-PLUS OTU Signal Degrade Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 237 }

	omtp11tPlusOtuAlarmIndicationSignalAlarmInhibit OBJECT-TYPE
	      SYNTAX  INTEGER
	      MAX-ACCESS  read-write
	      STATUS  current
	      DESCRIPTION
			"Inhibits OMTP11T-PLUS OTU Alarm Indication Signal Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 238 }

	omtp11tPlusOtuIncomingAlignmentErrorAlarmInhibit OBJECT-TYPE
	      SYNTAX  INTEGER
	      MAX-ACCESS  read-write
	      STATUS  current
	      DESCRIPTION
			"Inhibits OMTP11T-PLUS OTU Incoming Alignment Error Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 239 }

	omtp11tPlusOtuTraceIdentifierMismatchAlarmInhibit OBJECT-TYPE
	      SYNTAX  INTEGER
	      MAX-ACCESS  read-write
	      STATUS  current
	      DESCRIPTION
			"Inhibits OMTP11T-PLUS OTU Trace Identifier Mismatch Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 240 }

	omtp11tPlusOtuBackwardIncomingAlignmentErrorAlarmInhibit OBJECT-TYPE
	      SYNTAX  INTEGER
	      MAX-ACCESS  read-write
	      STATUS  current
	      DESCRIPTION
			"Inhibits OMTP11T-PLUS OTU Backward Incoming Alignment Error Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 241 }

	omtp11tPlusOtuBackwardDefectIndicationAlarmInhibit OBJECT-TYPE
	      SYNTAX  INTEGER
	      MAX-ACCESS  read-write
	      STATUS  current
	      DESCRIPTION
			"Inhibits OMTP11T-PLUS OTU Backward Defect Indication Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 242 }

	omtp11tPlusOduSignalFailAlarmInhibit OBJECT-TYPE
	      SYNTAX  INTEGER
	      MAX-ACCESS  read-write
	      STATUS  current
	      DESCRIPTION
			"Inhibits OMTP11T-PLUS ODU Signal Fail Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 251 }

	omtp11tPlusOduSignalDegradeAlarmInhibit OBJECT-TYPE
	      SYNTAX  INTEGER
	      MAX-ACCESS  read-write
	      STATUS  current
	      DESCRIPTION
			"Inhibits OMTP11T-PLUS ODU Signal Degrade Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 252 }

	omtp11tPlusOduAlarmIndicationSignalAlarmInhibit OBJECT-TYPE
	      SYNTAX  INTEGER
	      MAX-ACCESS  read-write
	      STATUS  current
	      DESCRIPTION
			"Inhibits OMTP11T-PLUS ODU Alarm Indication Signal Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 253 }

	omtp11tPlusOduTcm1IncomingAlignmentErrorAlarmInhibit OBJECT-TYPE
	      SYNTAX  INTEGER
	      MAX-ACCESS  read-write
	      STATUS  current
	      DESCRIPTION
			"Inhibits OMTP11T-PLUS ODU TCM1 Incoming Alignment Error 
			Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 254 }

	omtp11tPlusOduTcm2IncomingAlignmentErrorAlarmInhibit OBJECT-TYPE
	      SYNTAX  INTEGER
	      MAX-ACCESS  read-write
	      STATUS  current
	      DESCRIPTION
			"Inhibits OMTP11T-PLUS ODU TCM2 Incoming Alignment Error 
			Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 255 }

	omtp11tPlusOduTcm3IncomingAlignmentErrorAlarmInhibit OBJECT-TYPE
	      SYNTAX  INTEGER
	      MAX-ACCESS  read-write
	      STATUS  current
	      DESCRIPTION
			"Inhibits OMTP11T-PLUS ODU TCM3 Incoming Alignment Error 
			Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 256 }

	omtp11tPlusOduTcm4IncomingAlignmentErrorAlarmInhibit OBJECT-TYPE
	      SYNTAX  INTEGER
	      MAX-ACCESS  read-write
	      STATUS  current
	      DESCRIPTION
			"Inhibits OMTP11T-PLUS ODU TCM4 Incoming Alignment Error 
			Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 257 }

	omtp11tPlusOduTcm5IncomingAlignmentErrorAlarmInhibit OBJECT-TYPE
	      SYNTAX  INTEGER
	      MAX-ACCESS  read-write
	      STATUS  current
	      DESCRIPTION
			"Inhibits OMTP11T-PLUS ODU TCM5 Incoming Alignment Error 
			Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 258 }

	omtp11tPlusOduTcm6IncomingAlignmentErrorAlarmInhibit OBJECT-TYPE
	      SYNTAX  INTEGER
	      MAX-ACCESS  read-write
	      STATUS  current
	      DESCRIPTION
			"Inhibits OMTP11T-PLUS ODU TCM6 Incoming Alignment Error 
			Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 259 }

	omtp11tPlusOduTraceIdentifierMismatchAlarmInhibit OBJECT-TYPE
	      SYNTAX  INTEGER
	      MAX-ACCESS  read-write
	      STATUS  current
	      DESCRIPTION
			"Inhibits OMTP11T-PLUS ODU Trace Identifier Mismatch Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 260 }

	omtp11tPlusOduLockedDefectAlarmInhibit OBJECT-TYPE
	      SYNTAX  INTEGER
	      MAX-ACCESS  read-write
	      STATUS  current
	      DESCRIPTION
			"Inhibits OMTP11T-PLUS ODU Locked Defect Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 261 }

	omtp11tPlusOduOpenConnectionIndicationAlarmInhibit OBJECT-TYPE
	      SYNTAX  INTEGER
	      MAX-ACCESS  read-write
	      STATUS  current
	      DESCRIPTION
			"Inhibits OMTP11T-PLUS ODU Open Connection Indication Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 262 }

	omtp11tPlusOduBackwardDefectIndicationAlarmInhibit OBJECT-TYPE
	      SYNTAX  INTEGER
	      MAX-ACCESS  read-write
	      STATUS  current
	      DESCRIPTION
			"Inhibits OMTP11T-PLUS ODU Backward Defect Indication Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 263 }

	omtp11tPlusOduTcm1BackwardIncomingAlignmentErrorAlarmInhibit OBJECT-TYPE
	      SYNTAX  INTEGER
	      MAX-ACCESS  read-write
	      STATUS  current
	      DESCRIPTION
			"Inhibits OMTP11T-PLUS ODU TCM1 Backward Incoming
			Alignment Error Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 264 }

	omtp11tPlusOduTcm2BackwardIncomingAlignmentErrorAlarmInhibit OBJECT-TYPE
	      SYNTAX  INTEGER
	      MAX-ACCESS  read-write
	      STATUS  current
	      DESCRIPTION
			"Inhibits OMTP11T-PLUS ODU TCM2 Backward Incoming
			Alignment Error Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 265 }

	omtp11tPlusOduTcm3BackwardIncomingAlignmentErrorAlarmInhibit OBJECT-TYPE
	      SYNTAX  INTEGER
	      MAX-ACCESS  read-write
	      STATUS  current
	      DESCRIPTION
			"Inhibits OMTP11T-PLUS ODU TCM3 Backward Incoming
			Alignment Error Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 266 }

	omtp11tPlusOduTcm4BackwardIncomingAlignmentErrorAlarmInhibit OBJECT-TYPE
	      SYNTAX  INTEGER
	      MAX-ACCESS  read-write
	      STATUS  current
	      DESCRIPTION
			"Inhibits OMTP11T-PLUS ODU TCM4 Backward Incoming
			Alignment Error Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 267 }

	omtp11tPlusOduTcm5BackwardIncomingAlignmentErrorAlarmInhibit OBJECT-TYPE
	      SYNTAX  INTEGER
	      MAX-ACCESS  read-write
	      STATUS  current
	      DESCRIPTION
			"Inhibits OMTP11T-PLUS ODU TCM5 Backward Incoming
			Alignment Error Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 268 }

	omtp11tPlusOduTcm6BackwardIncomingAlignmentErrorAlarmInhibit OBJECT-TYPE
	      SYNTAX  INTEGER
	      MAX-ACCESS  read-write
	      STATUS  current
	      DESCRIPTION
			"Inhibits OMTP11T-PLUS ODU TCM6 Backward Incoming
			Alignment Error Alarm for the requested port
			-----------------------------
			omtp11tPlusInterfaceNumber:
			1 - CLIENT-1
			2 - LINE-1
			-----------------------------
			Values:
			1 - Inhibit
			0 - Do Not Inhibit
			-----------------------------"
		::= { omtp11tPlusConfigurationEntry 269 }

	omtp11tPlusOpuPayloadMismatchAlarmInhibit OBJECT-TYPE
	      SYNTAX  INTEGER
	      MAX-ACCESS  read-write
	      STATUS  current
	      DESCRIPTION
			"Inhibits OMTP11T-PLUS Opu Payload Mismatch Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 270 }

	omtp11tPlusOchLossOfPayloadAlarmInhibit OBJECT-TYPE
	      SYNTAX  INTEGER
	      MAX-ACCESS  read-write
	      STATUS  current
	      DESCRIPTION
			"Inhibits OMTP11T-PLUS Och Loss Of Payload Alarm
			for the requested port
			-----------------------------
			omtp11tPlusInterfaceNumber:
			1 - CLIENT-1
			2 - LINE-1
			-----------------------------
			Values:
			1 - Inhibit
			0 - Do Not Inhibit
			-----------------------------"
		::= { omtp11tPlusConfigurationEntry 271 }

	omtp11tPlusXfpInputPowerFailureAlarmSeverity OBJECT-TYPE
	      SYNTAX  DisplayString
	      MAX-ACCESS  read-write
	      STATUS  current
	      DESCRIPTION
			"Set or Get the alarm severity level of the
			OMTP11T-PLUS XFP Input Power Failure Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 401 }

	omtp11tPlusXfpOutputPowerFailureAlarmSeverity OBJECT-TYPE
	      SYNTAX  DisplayString
	      MAX-ACCESS  read-write
	      STATUS  current
	      DESCRIPTION
			"Set or Get the alarm severity level of the
			OMTP11T-PLUS XFP Output Power Failure Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 402 }

	omtp11tPlusXfpHighTemperatureAlarmSeverity OBJECT-TYPE
	      SYNTAX  DisplayString
	      MAX-ACCESS  read-write
	      STATUS  current
	      DESCRIPTION
			"Set or Get the alarm severity level of the
			OMTP11T-PLUS XFP High Temperature Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 403 }

	omtp11tPlusXfpLowTemperatureAlarmSeverity OBJECT-TYPE
	      SYNTAX  DisplayString
	      MAX-ACCESS  read-write
	      STATUS  current
	      DESCRIPTION
			"Set or Get the alarm severity level of the
			OMTP11T-PLUS XFP Low Temperature Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 404 }

	omtp11tPlusXfpHighTemperatureWarningSeverity OBJECT-TYPE
	      SYNTAX  DisplayString
	      MAX-ACCESS  read-write
	      STATUS  current
	      DESCRIPTION
			"Set or Get the alarm severity level of the
			OMTP11T-PLUS XFP High Temperature Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 405 }

	omtp11tPlusXfpLowTemperatureWarningSeverity OBJECT-TYPE
	      SYNTAX  DisplayString
	      MAX-ACCESS  read-write
	      STATUS  current
	      DESCRIPTION
			"Set or Get the alarm severity level of the
			OMTP11T-PLUS XFP Low Temperature Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 406 }

	omtp11tPlusXfpHighBiasCurrentAlarmSeverity OBJECT-TYPE
	      SYNTAX  DisplayString
	      MAX-ACCESS  read-write
	      STATUS  current
	      DESCRIPTION
			"Set or Get the alarm severity level of the
			OMTP11T-PLUS XFP High Bias Current Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 407 }

	omtp11tPlusXfpLowBiasCurrentAlarmSeverity OBJECT-TYPE
	      SYNTAX  DisplayString
	      MAX-ACCESS  read-write
	      STATUS  current
	      DESCRIPTION
			"Set or Get the alarm severity level of the
			OMTP11T-PLUS XFP Low Bias Current Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 408 }

	omtp11tPlusXfpHighBiasCurrentWarningSeverity OBJECT-TYPE
	      SYNTAX  DisplayString
	      MAX-ACCESS  read-write
	      STATUS  current
	      DESCRIPTION
			"Set or Get the alarm severity level of the
			OMTP11T-PLUS XFP High Bias Current Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 409 }

	omtp11tPlusXfpLowBiasCurrentWarningSeverity OBJECT-TYPE
	      SYNTAX  DisplayString
	      MAX-ACCESS  read-write
	      STATUS  current
	      DESCRIPTION
			"Set or Get the alarm severity level of the
			OMTP11T-PLUS XFP Low Bias Current Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 410 }

	omtp11tPlusXfpInputHighPowerAlarmSeverity OBJECT-TYPE
	      SYNTAX  DisplayString
	      MAX-ACCESS  read-write
	      STATUS  current
	      DESCRIPTION
			"Set or Get the alarm severity level of the
			OMTP11T-PLUS XFP Input High Power Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 411 }

	omtp11tPlusXfpInputLowPowerAlarmSeverity OBJECT-TYPE
	      SYNTAX  DisplayString
	      MAX-ACCESS  read-write
	      STATUS  current
	      DESCRIPTION
			"Set or Get the alarm severity level of the
			OMTP11T-PLUS XFP Input Low Power Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 412 }

	omtp11tPlusXfpInputHighPowerWarningSeverity OBJECT-TYPE
	      SYNTAX  DisplayString
	      MAX-ACCESS  read-write
	      STATUS  current
	      DESCRIPTION
			"Set or Get the alarm severity level of the
			OMTP11T-PLUS XFP Input High Power Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 413 }

	omtp11tPlusXfpInputLowPowerWarningSeverity OBJECT-TYPE
	      SYNTAX  DisplayString
	      MAX-ACCESS  read-write
	      STATUS  current
	      DESCRIPTION
			"Set or Get the alarm severity level of the
			OMTP11T-PLUS XFP Input Low Power Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 414 }

	omtp11tPlusXfpOutputHighPowerAlarmSeverity OBJECT-TYPE
	      SYNTAX  DisplayString
	      MAX-ACCESS  read-write
	      STATUS  current
	      DESCRIPTION
			"Set or Get the alarm severity level of the
			OMTP11T-PLUS XFP Output High Power Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 415 }

	omtp11tPlusXfpOutputLowPowerAlarmSeverity OBJECT-TYPE
	      SYNTAX  DisplayString
	      MAX-ACCESS  read-write
	      STATUS  current
	      DESCRIPTION
			"Set or Get the alarm severity level of the
			OMTP11T-PLUS XFP Output Low Power Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 416 }

	omtp11tPlusXfpOutputHighPowerWarningSeverity OBJECT-TYPE
	      SYNTAX  DisplayString
	      MAX-ACCESS  read-write
	      STATUS  current
	      DESCRIPTION
			"Set or Get the alarm severity level of the
			OMTP11T-PLUS XFP Output High Power Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 417 }

	omtp11tPlusXfpOutputLowPowerWarningSeverity OBJECT-TYPE
	      SYNTAX  DisplayString
	      MAX-ACCESS  read-write
	      STATUS  current
	      DESCRIPTION
			"Set or Get the alarm severity level of the
			OMTP11T-PLUS XFP Output Low Power Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 418 }

	omtp11tPlusXfpHighSupplyVoltageAlarmSeverity OBJECT-TYPE
	      SYNTAX  DisplayString
	      MAX-ACCESS  read-write
	      STATUS  current
	      DESCRIPTION
			"Set or Get the alarm severity level of the
			OMTP11T-PLUS XFP High Supply Voltage Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 419 }

	omtp11tPlusXfpLowSupplyVoltageAlarmSeverity OBJECT-TYPE
	      SYNTAX  DisplayString
	      MAX-ACCESS  read-write
	      STATUS  current
	      DESCRIPTION
			"Set or Get the alarm severity level of the
			OMTP11T-PLUS XFP Low Supply Voltage Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 420 }

	omtp11tPlusXfpHighSupplyVoltageWarningSeverity OBJECT-TYPE
	      SYNTAX  DisplayString
	      MAX-ACCESS  read-write
	      STATUS  current
	      DESCRIPTION
			"Set or Get the alarm severity level of the
			OMTP11T-PLUS XFP High Supply Voltage Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 421 }

	omtp11tPlusXfpLowSupplyVoltageWarningSeverity OBJECT-TYPE
	      SYNTAX  DisplayString
	      MAX-ACCESS  read-write
	      STATUS  current
	      DESCRIPTION
			"Set or Get the alarm severity level of the
			OMTP11T-PLUS XFP Low Supply Voltage Warning   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 422 }

	omtp11tPlusXfpPresenceAbsenceNotificationSeverity OBJECT-TYPE
	      SYNTAX  DisplayString
	      MAX-ACCESS  read-write
	      STATUS  current
	      DESCRIPTION
			"Set or Get the alarm severity level of the
			OMTP11T-PLUS XFP Presence Absence Notification   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 423 }

	omtp11tPlusOtuLossOfSignalAlarmSeverity OBJECT-TYPE
	      SYNTAX  DisplayString
	      MAX-ACCESS  read-write
	      STATUS  current
	      DESCRIPTION
			"Set or Get the alarm severity level of the
			OMTP11T-PLUS OTU Loss Of Signal Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 431 }

	omtp11tPlusOtuLossOfFrameAlarmSeverity OBJECT-TYPE
	      SYNTAX  DisplayString
	      MAX-ACCESS  read-write
	      STATUS  current
	      DESCRIPTION
			"Set or Get the alarm severity level of the
			OMTP11T-PLUS OTU Loss Of Frame Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 432 }

	omtp11tPlusOtuOutOfFrameAlarmSeverity OBJECT-TYPE
	      SYNTAX  DisplayString
	      MAX-ACCESS  read-write
	      STATUS  current
	      DESCRIPTION
			"Set or Get the alarm severity level of the
			OMTP11T-PLUS OTU Out Of Frame Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 433 }

	omtp11tPlusOtuLossOfMultiFrameAlarmSeverity OBJECT-TYPE
	      SYNTAX  DisplayString
	      MAX-ACCESS  read-write
	      STATUS  current
	      DESCRIPTION
			"Set or Get the alarm severity level of the
			OMTP11T-PLUS OTU Loss Of Multi Frame Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 434 }

	omtp11tPlusOtuOutOfMultiFrameAlarmSeverity OBJECT-TYPE
	      SYNTAX  DisplayString
	      MAX-ACCESS  read-write
	      STATUS  current
	      DESCRIPTION
			"Set or Get the alarm severity level of the
			OMTP11T-PLUS OTU Out Of Multi Frame Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 435 }

	omtp11tPlusOtuSignalFailAlarmSeverity OBJECT-TYPE
	      SYNTAX  DisplayString
	      MAX-ACCESS  read-write
	      STATUS  current
	      DESCRIPTION
			"Set or Get the alarm severity level of the
			OMTP11T-PLUS OTU Signal Fail Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 436 }

	omtp11tPlusOtuSignalDegradeAlarmSeverity OBJECT-TYPE
	      SYNTAX  DisplayString
	      MAX-ACCESS  read-write
	      STATUS  current
	      DESCRIPTION
			"Set or Get the alarm severity level of the
			OMTP11T-PLUS OTU Signal Degrade Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 437 }

	omtp11tPlusOtuAlarmIndicationSignalAlarmSeverity OBJECT-TYPE
	      SYNTAX  DisplayString
	      MAX-ACCESS  read-write
	      STATUS  current
	      DESCRIPTION
			"Set or Get the alarm severity level of the
			OMTP11T-PLUS OTU Alarm Indication Signal Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 438 }

	omtp11tPlusOtuIncomingAlignmentErrorAlarmSeverity OBJECT-TYPE
	      SYNTAX  DisplayString
	      MAX-ACCESS  read-write
	      STATUS  current
	      DESCRIPTION
			"Set or Get the alarm severity level of the
			OMTP11T-PLUS OTU Incoming Alignment Error Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 439 }

	omtp11tPlusOtuTraceIdentifierMismatchAlarmSeverity OBJECT-TYPE
	      SYNTAX  DisplayString
	      MAX-ACCESS  read-write
	      STATUS  current
	      DESCRIPTION
			"Set or Get the alarm severity level of the
			OMTP11T-PLUS OTU Trace Identifier Mismatch Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 440 }

	omtp11tPlusOtuBackwardIncomingAlignmentErrorAlarmSeverity OBJECT-TYPE
	      SYNTAX  DisplayString
	      MAX-ACCESS  read-write
	      STATUS  current
	      DESCRIPTION
			"Set or Get the alarm severity level of the
			OMTP11T-PLUS OTU Backward Incoming Alignment Error Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 441 }

	omtp11tPlusOtuBackwardDefectIndicationAlarmSeverity OBJECT-TYPE
	      SYNTAX  DisplayString
	      MAX-ACCESS  read-write
	      STATUS  current
	      DESCRIPTION
			"Set or Get the alarm severity level of the
			OMTP11T-PLUS OTU Backward Defect Indication Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 442 }

	omtp11tPlusOduSignalFailAlarmSeverity OBJECT-TYPE
	      SYNTAX  DisplayString
	      MAX-ACCESS  read-write
	      STATUS  current
	      DESCRIPTION
			"Set or Get the alarm severity level of the
			OMTP11T-PLUS ODU Signal Fail Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 451 }

	omtp11tPlusOduSignalDegradeAlarmSeverity OBJECT-TYPE
	      SYNTAX  DisplayString
	      MAX-ACCESS  read-write
	      STATUS  current
	      DESCRIPTION
			"Set or Get the alarm severity level of the
			OMTP11T-PLUS ODU Signal Degrade Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 452 }

	omtp11tPlusOduAlarmIndicationSignalAlarmSeverity OBJECT-TYPE
	      SYNTAX  DisplayString
	      MAX-ACCESS  read-write
	      STATUS  current
	      DESCRIPTION
			"Set or Get the alarm severity level of the
			OMTP11T-PLUS ODU Alarm Indication Signal Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 453 }

	omtp11tPlusOduTcm1IncomingAlignmentErrorAlarmSeverity OBJECT-TYPE
	      SYNTAX  DisplayString
	      MAX-ACCESS  read-write
	      STATUS  current
	      DESCRIPTION
			"Set or Get the alarm severity level of the
			OMTP11T-PLUS ODU TCM1 Incoming Alignment Error Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 454 }

	omtp11tPlusOduTcm2IncomingAlignmentErrorAlarmSeverity OBJECT-TYPE
	      SYNTAX  DisplayString
	      MAX-ACCESS  read-write
	      STATUS  current
	      DESCRIPTION
			"Set or Get the alarm severity level of the
			OMTP11T-PLUS ODU TCM2 Incoming Alignment Error Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 455 }

	omtp11tPlusOduTcm3IncomingAlignmentErrorAlarmSeverity OBJECT-TYPE
	      SYNTAX  DisplayString
	      MAX-ACCESS  read-write
	      STATUS  current
	      DESCRIPTION
			"Set or Get the alarm severity level of the
			OMTP11T-PLUS ODU TCM3 Incoming Alignment Error Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 456 }

	omtp11tPlusOduTcm4IncomingAlignmentErrorAlarmSeverity OBJECT-TYPE
	      SYNTAX  DisplayString
	      MAX-ACCESS  read-write
	      STATUS  current
	      DESCRIPTION
			"Set or Get the alarm severity level of the
			OMTP11T-PLUS ODU TCM4 Incoming Alignment Error Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 457 }

	omtp11tPlusOduTcm5IncomingAlignmentErrorAlarmSeverity OBJECT-TYPE
	      SYNTAX  DisplayString
	      MAX-ACCESS  read-write
	      STATUS  current
	      DESCRIPTION
			"Set or Get the alarm severity level of the
			OMTP11T-PLUS ODU TCM5 Incoming Alignment Error Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 458 }

	omtp11tPlusOduTcm6IncomingAlignmentErrorAlarmSeverity OBJECT-TYPE
	      SYNTAX  DisplayString
	      MAX-ACCESS  read-write
	      STATUS  current
	      DESCRIPTION
			"Set or Get the alarm severity level of the
			OMTP11T-PLUS ODU TCM6 Incoming Alignment Error Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 459 }

	omtp11tPlusOduTraceIdentifierMismatchAlarmSeverity OBJECT-TYPE
	      SYNTAX  DisplayString
	      MAX-ACCESS  read-write
	      STATUS  current
	      DESCRIPTION
			"Set or Get the alarm severity level of the
			OMTP11T-PLUS ODU Trace Identifier Mismatch Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 460 }

	omtp11tPlusOduLockedDefectAlarmSeverity OBJECT-TYPE
	      SYNTAX  DisplayString
	      MAX-ACCESS  read-write
	      STATUS  current
	      DESCRIPTION
			"Set or Get the alarm severity level of the
			OMTP11T-PLUS ODU Locked Defect Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 461 }

	omtp11tPlusOduOpenConnectionIndicationAlarmSeverity OBJECT-TYPE
	      SYNTAX  DisplayString
	      MAX-ACCESS  read-write
	      STATUS  current
	      DESCRIPTION
			"Set or Get the alarm severity level of the
			OMTP11T-PLUS ODU Open Connection Indication Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 462 }

	omtp11tPlusOduBackwardDefectIndicationAlarmSeverity OBJECT-TYPE
	      SYNTAX  DisplayString
	      MAX-ACCESS  read-write
	      STATUS  current
	      DESCRIPTION
			"Set or Get the alarm severity level of the
			OMTP11T-PLUS ODU Backward Defect Indication Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 463 }

	omtp11tPlusOduTcm1BackwardIncomingAlignmentErrorAlarmSeverity OBJECT-TYPE
	      SYNTAX  DisplayString
	      MAX-ACCESS  read-write
	      STATUS  current
	      DESCRIPTION
			"Set or Get the alarm severity level of the
			OMTP11T-PLUS ODU TCM1 Backward Incoming Alignment Error
			Alarm for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 469 }

	omtp11tPlusOduTcm2BackwardIncomingAlignmentErrorAlarmSeverity OBJECT-TYPE
	      SYNTAX  DisplayString
	      MAX-ACCESS  read-write
	      STATUS  current
	      DESCRIPTION
			"Set or Get the alarm severity level of the
			OMTP11T-PLUS ODU TCM2 Backward Incoming Alignment Error
			Alarm for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 470 }

	omtp11tPlusOduTcm3BackwardIncomingAlignmentErrorAlarmSeverity OBJECT-TYPE
	      SYNTAX  DisplayString
	      MAX-ACCESS  read-write
	      STATUS  current
	      DESCRIPTION
			"Set or Get the alarm severity level of the
			OMTP11T-PLUS ODU TCM3 Backward Incoming Alignment Error
			Alarm for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 471 }

	omtp11tPlusOduTcm4BackwardIncomingAlignmentErrorAlarmSeverity OBJECT-TYPE
	      SYNTAX  DisplayString
	      MAX-ACCESS  read-write
	      STATUS  current
	      DESCRIPTION
			"Set or Get the alarm severity level of the
			OMTP11T-PLUS ODU TCM4 Backward Incoming Alignment Error
			Alarm for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 472 }

	omtp11tPlusOduTcm5BackwardIncomingAlignmentErrorAlarmSeverity OBJECT-TYPE
	      SYNTAX  DisplayString
	      MAX-ACCESS  read-write
	      STATUS  current
	      DESCRIPTION
			"Set or Get the alarm severity level of the
			OMTP11T-PLUS ODU TCM5 Backward Incoming Alignment Error
			Alarm for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 473 }

	omtp11tPlusOduTcm6BackwardIncomingAlignmentErrorAlarmSeverity OBJECT-TYPE
	      SYNTAX  DisplayString
	      MAX-ACCESS  read-write
	      STATUS  current
	      DESCRIPTION
			"Set or Get the alarm severity level of the
			OMTP11T-PLUS ODU TCM6 Backward Incoming Alignment Error
			Alarm for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 474 }

	omtp11tPlusOpuPayloadMismatchAlarmSeverity OBJECT-TYPE
	      SYNTAX  DisplayString
	      MAX-ACCESS  read-write
	      STATUS  current
	      DESCRIPTION
			"Set or Get the alarm severity level of the
			OMTP11T-PLUS Opu Payload Mismatch Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 475 }

	omtp11tPlusOchLossOfPayloadAlarmSeverity OBJECT-TYPE
	      SYNTAX  DisplayString
	      MAX-ACCESS  read-write
	      STATUS  current
	      DESCRIPTION
			"Set or Get the alarm severity level of the
			OMTP11T-PLUS Och Loss Of Payload Alarm   
			for requested port
 			-----------------------------
			omtp11tPlusInterfaceNumber:
			1 - CLIENT-1
			2 - LINE-1
			-----------------------------
			Values:
			1 - Critical
			2 - Major
			3 - Minor
			4 - Deferred
			-----------------------------"
		::= { omtp11tPlusConfigurationEntry 476 }

	omtp11tPlusConfigurationTableRowStatus OBJECT-TYPE
              SYNTAX      RowStatus
              MAX-ACCESS  read-write
              STATUS      current
              DESCRIPTION
                      "	This is MIB realted property,
			NOT to be considered as a card property"
              ::= { omtp11tPlusConfigurationEntry 575 }	

--*****************************************************************************
--				    ALARMS
--*****************************************************************************

	omtp11tPlusAlarmQueryTable OBJECT-TYPE
		SYNTAX SEQUENCE OF Omtp11tPlusAlarmQueryEntry
		MAX-ACCESS not-accessible
		STATUS current
		DESCRIPTION
			"Contains Alarm queries of the OMTP11T-PLUS card"
	
		::= { omtp11tPlusAlarmQuery 1 }

	omtp11tPlusAlarmQueryEntry OBJECT-TYPE
		SYNTAX Omtp11tPlusAlarmQueryEntry
		MAX-ACCESS not-accessible
		STATUS current
		DESCRIPTION 
			""
		
		INDEX   { node, rack , subRack , slot , omtp11tPlusInterfaceNumber}
	
		::= { omtp11tPlusAlarmQueryTable 1 }
		
	Omtp11tPlusAlarmQueryEntry ::= 
		SEQUENCE {
				omtp11tPlusXfpInputPowerFailureAlarm				DisplayString,
				omtp11tPlusXfpOutputPowerFailureAlarm				DisplayString,
				omtp11tPlusXfpHighTemperatureAlarm				DisplayString, 
				omtp11tPlusXfpLowTemperatureAlarm				DisplayString, 
				omtp11tPlusXfpHighTemperatureWarning				DisplayString, 
				omtp11tPlusXfpLowTemperatureWarning				DisplayString, 
				omtp11tPlusXfpHighBiasCurrentAlarm				DisplayString, 
				omtp11tPlusXfpLowBiasCurrentAlarm				DisplayString, 
				omtp11tPlusXfpHighBiasCurrentWarning				DisplayString, 
				omtp11tPlusXfpLowBiasCurrentWarning				DisplayString, 
				omtp11tPlusXfpInputHighPowerAlarm				DisplayString, 
				omtp11tPlusXfpInputLowPowerAlarm				DisplayString, 
				omtp11tPlusXfpInputHighPowerWarning				DisplayString, 
				omtp11tPlusXfpInputLowPowerWarning				DisplayString, 
				omtp11tPlusXfpOutputHighPowerAlarm				DisplayString, 
				omtp11tPlusXfpOutputLowPowerAlarm				DisplayString, 
				omtp11tPlusXfpOutputHighPowerWarning				DisplayString, 
				omtp11tPlusXfpOutputLowPowerWarning				DisplayString, 
				omtp11tPlusXfpHighSupplyVoltageAlarm				DisplayString, 
				omtp11tPlusXfpLowSupplyVoltageAlarm				DisplayString, 
				omtp11tPlusXfpHighSupplyVoltageWarning				DisplayString, 
				omtp11tPlusXfpLowSupplyVoltageWarning				DisplayString, 
				omtp11tPlusXfpPresenceAbsenceNotification			DisplayString, 
				omtp11tPlusOtuLossOfSignalAlarm					DisplayString, 
				omtp11tPlusOtuLossOfFrameAlarm					DisplayString, 
				omtp11tPlusOtuOutOfFrameAlarm					DisplayString, 
				omtp11tPlusOtuLossOfMultiFrameAlarm				DisplayString, 
				omtp11tPlusOtuOutOfMultiFrameAlarm				DisplayString, 
				omtp11tPlusOtuSignalFailAlarm					DisplayString, 
				omtp11tPlusOtuSignalDegradeAlarm				DisplayString, 
				omtp11tPlusOtuAlarmIndicationSignalAlarm			DisplayString, 
				omtp11tPlusOtuIncomingAlignmentErrorAlarm			DisplayString, 
				omtp11tPlusOtuTraceIdentifierMismatchAlarm			DisplayString, 
				omtp11tPlusOtuBackwardIncomingAlignmentErrorAlarm		DisplayString, 
				omtp11tPlusOtuBackwardDefectIndicationAlarm			DisplayString, 
				omtp11tPlusOduSignalFailAlarm					DisplayString, 
				omtp11tPlusOduSignalDegradeAlarm				DisplayString, 
				omtp11tPlusOduAlarmIndicationSignalAlarm			DisplayString, 
				omtp11tPlusOduTcm1IncomingAlignmentErrorAlarm			DisplayString,
				omtp11tPlusOduTcm2IncomingAlignmentErrorAlarm			DisplayString, 
				omtp11tPlusOduTcm3IncomingAlignmentErrorAlarm			DisplayString, 
				omtp11tPlusOduTcm4IncomingAlignmentErrorAlarm			DisplayString, 
				omtp11tPlusOduTcm5IncomingAlignmentErrorAlarm			DisplayString, 
				omtp11tPlusOduTcm6IncomingAlignmentErrorAlarm			DisplayString, 
				omtp11tPlusOduTraceIdentifierMismatchAlarm			DisplayString, 
				omtp11tPlusOduLockedDefectAlarm					DisplayString, 
				omtp11tPlusOduOpenConnectionIndicationAlarm			DisplayString, 
				omtp11tPlusOduBackwardDefectIndicationAlarm			DisplayString, 
				omtp11tPlusOduTcm1BackwardIncomingAlignmentErrorAlarm		DisplayString, 
				omtp11tPlusOduTcm2BackwardIncomingAlignmentErrorAlarm		DisplayString, 
				omtp11tPlusOduTcm3BackwardIncomingAlignmentErrorAlarm		DisplayString, 
				omtp11tPlusOduTcm4BackwardIncomingAlignmentErrorAlarm		DisplayString,
				omtp11tPlusOduTcm5BackwardIncomingAlignmentErrorAlarm		DisplayString, 
				omtp11tPlusOduTcm6BackwardIncomingAlignmentErrorAlarm		DisplayString, 
				omtp11tPlusOpuPayloadMismatchAlarm				DisplayString, 
				omtp11tPlusOchLossOfPayloadAlarm				DisplayString, 
				omtp11tPlusAlarmQueryTableRowStatus				RowStatus
		}


	omtp11tPlusXfpInputPowerFailureAlarm OBJECT-TYPE
		SYNTAX  DisplayString
		MAX-ACCESS  read-only
		STATUS  current
		DESCRIPTION
			"If optical input power at requested interface is less than
			-20dbm, this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 1 }

        omtp11tPlusXfpOutputPowerFailureAlarm OBJECT-TYPE
		SYNTAX  DisplayString
		MAX-ACCESS  read-only
		STATUS  current
		DESCRIPTION
			"If optical output power at requested interface is less than
			-10dbm, this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 2 }

        omtp11tPlusXfpHighTemperatureAlarm OBJECT-TYPE
		SYNTAX  DisplayString
		MAX-ACCESS  read-only
		STATUS  current
		DESCRIPTION
			"If optical temperature at requested interface is greater 
			than the High Temperature Alarm Threshold, alarm will 
			be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 3 }

        omtp11tPlusXfpLowTemperatureAlarm OBJECT-TYPE
		SYNTAX  DisplayString
		MAX-ACCESS  read-only
		STATUS  current
		DESCRIPTION
			"If optical temperature at requested interface is lower 
			than the Low Temperature Alarm Threshold, alarm will be 
			generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 4 }

        omtp11tPlusXfpHighTemperatureWarning OBJECT-TYPE
		SYNTAX  DisplayString
		MAX-ACCESS  read-only
		STATUS  current
		DESCRIPTION
       			"If optical temperature at requested interface is greater
			than the High Temperature Warning Threshold, this alarm 
			will be generated.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 5 }

        omtp11tPlusXfpLowTemperatureWarning OBJECT-TYPE
		SYNTAX  DisplayString
		MAX-ACCESS  read-only
		STATUS  current
		DESCRIPTION
       			"If optical temperature at requested interface is lesser
			than the Low Temperature Warning Threshold, this alarm 
			will be generated.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 6 }

        omtp11tPlusXfpHighBiasCurrentAlarm OBJECT-TYPE
		SYNTAX  DisplayString
		MAX-ACCESS  read-only
		STATUS  current
		DESCRIPTION
       			"If optical transmit bias current at requested interface
			is greater than the High Bias Current Alarm Threshold, 
			this this alarm will be generated.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 7 }

        omtp11tPlusXfpLowBiasCurrentAlarm OBJECT-TYPE
		SYNTAX  DisplayString
		MAX-ACCESS  read-only
		STATUS  current
		DESCRIPTION
			"If optical transmit bias current at requested interface
			is lesser than the Low Bias Current Alarm Threshold, 
			this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 8 }

        omtp11tPlusXfpHighBiasCurrentWarning OBJECT-TYPE
		SYNTAX  DisplayString
		MAX-ACCESS  read-only
		STATUS  current
		DESCRIPTION
       			"If optical transmit bias current at requested interface
			is greater than the High Bias Current Warning Threshold,
			this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 9 }

        omtp11tPlusXfpLowBiasCurrentWarning OBJECT-TYPE
		SYNTAX  DisplayString
		MAX-ACCESS  read-only
		STATUS  current
		DESCRIPTION
       			"If optical transmit bias current at requested interface
			is lesser than the Low Bias Current Warning Threshold, 
			this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 10 }

        omtp11tPlusXfpInputHighPowerAlarm OBJECT-TYPE
		SYNTAX  DisplayString
		MAX-ACCESS  read-only
		STATUS  current
		DESCRIPTION
       			"If optical Input power at requested interface is 
			greater than the High Input Power Alarm Threshold, this 
			alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 11 }

        omtp11tPlusXfpInputLowPowerAlarm OBJECT-TYPE
		SYNTAX  DisplayString
		MAX-ACCESS  read-only
		STATUS  current
		DESCRIPTION
       			"If optical Input power at requested interface is lesser
			than the Low Input Power Alarm Threshold, this alarm 
			will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 12 }

        omtp11tPlusXfpInputHighPowerWarning OBJECT-TYPE
		SYNTAX  DisplayString
		MAX-ACCESS  read-only
		STATUS  current
		DESCRIPTION
       			"If optical Input power at requested interface is 
			greater than the High Input Power Warning Threshold, 
			this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 13 }

        omtp11tPlusXfpInputLowPowerWarning OBJECT-TYPE
		SYNTAX  DisplayString
		MAX-ACCESS  read-only
		STATUS  current
		DESCRIPTION
       			"If optical Input power at requested interface is lesser
			than the Low Input Power Warning Threshold, this alarm 
			will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 14 }

        omtp11tPlusXfpOutputHighPowerAlarm OBJECT-TYPE
		SYNTAX  DisplayString
		MAX-ACCESS  read-only
		STATUS  current
		DESCRIPTION
       			"If optical Output power at requested interface is 
			greater than the High Output Power Alarm Threshold, this
			alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 15 }

        omtp11tPlusXfpOutputLowPowerAlarm OBJECT-TYPE
		SYNTAX  DisplayString
		MAX-ACCESS  read-only
		STATUS  current
		DESCRIPTION
       			"If optical Output power at requested interface is 
			lesser than the Low Output Power Alarm Threshold, this 
			alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 16 }

        omtp11tPlusXfpOutputHighPowerWarning OBJECT-TYPE
		SYNTAX  DisplayString
		MAX-ACCESS  read-only
		STATUS  current
		DESCRIPTION
       			"If optical Output power at requested interface is 
			greater than the High Output Power Warning Threshold, 
			this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 17 }

        omtp11tPlusXfpOutputLowPowerWarning OBJECT-TYPE
		SYNTAX  DisplayString
		MAX-ACCESS  read-only
		STATUS  current
		DESCRIPTION
       			"If optical Output power at requested interface is 
			lesser than the Low Output Power Warning Threshold, this
			alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 18 }

        omtp11tPlusXfpHighSupplyVoltageAlarm OBJECT-TYPE
		SYNTAX  DisplayString
		MAX-ACCESS  read-only
		STATUS  current
		DESCRIPTION
       			"If optical Supply Voltage at requested interface is 
			greater than the High Supply Voltage Alarm Threshold, 
			this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 19 }

        omtp11tPlusXfpLowSupplyVoltageAlarm OBJECT-TYPE
		SYNTAX  DisplayString
		MAX-ACCESS  read-only
		STATUS  current
		DESCRIPTION
       			"If optical Supply Voltage at requested interface is 
			lesser than the Low Supply Voltage Alarm Threshold, this
			alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 20 }

        omtp11tPlusXfpHighSupplyVoltageWarning OBJECT-TYPE
		SYNTAX  DisplayString
		MAX-ACCESS  read-only
		STATUS  current
		DESCRIPTION
       			"If optical Supply Voltage at requested interface is 
			greater than the High Supply Voltage Warning Threshold, 
			this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 21 }

        omtp11tPlusXfpLowSupplyVoltageWarning OBJECT-TYPE
		SYNTAX  DisplayString
		MAX-ACCESS  read-only
		STATUS  current
		DESCRIPTION
       			"If optical Supply Voltage at requested interface is 
			lesser than the Low Supply Voltage Warning Threshold, 
			this alarm will be generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 22 }

        omtp11tPlusXfpPresenceAbsenceNotification OBJECT-TYPE
		SYNTAX  DisplayString
		MAX-ACCESS  read-only
		STATUS  current
		DESCRIPTION
			"Whenever the XFP is jacked in or jacked out, this 
			notification is generated.
			-----------------------------
			omtp11tPlusInterfaceNumber:
			1 - LINE-1
			2 - LINE-2
			-----------------------------
			Values :
			If Alarm is Present(module absent) - Date and Time Stamp
				    eg:2017-5-18,9:47:20.0,+5:30
			If Alarm is Absent(module present) - 0
			-----------------------------"
               ::= { omtp11tPlusAlarmQueryEntry 23 }

        omtp11tPlusOtuLossOfSignalAlarm OBJECT-TYPE
		SYNTAX  DisplayString
		MAX-ACCESS  read-only
		STATUS  current
		DESCRIPTION
			"For port configured with OTU2 traffic,
			if there is no signal received then OTU-LOS Alarm
			is generated.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 31 }

        omtp11tPlusOtuLossOfFrameAlarm OBJECT-TYPE
		SYNTAX  DisplayString
		MAX-ACCESS  read-only
		STATUS  current
		DESCRIPTION
			"For port configured with OTU2 traffic, if
			OTU2 frame received are in out-of-frame (OOF)
			state for 3 ms, then OTU-LOF Alarm is generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 32 }

        omtp11tPlusOtuOutOfFrameAlarm OBJECT-TYPE
		SYNTAX  DisplayString
		MAX-ACCESS  read-only
		STATUS  current
		DESCRIPTION
			"For port configured with OTU2 traffic, if 5
			consecutive OTU2 frames are received with
			invalid framing patterns then OTU OOF Alarm is
			generated
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 33 }

        omtp11tPlusOtuLossOfMultiFrameAlarm OBJECT-TYPE
		SYNTAX  DisplayString
		MAX-ACCESS  read-only
		STATUS  current
		DESCRIPTION
		        "For port configured with OTU2 traffic, if 
			OTU2 frame received are in Out-of-multiframe
			(OOM) state for 3 ms then LOM Alarm is generated.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 34 }

        omtp11tPlusOtuOutOfMultiFrameAlarm OBJECT-TYPE
		SYNTAX  DisplayString
		MAX-ACCESS  read-only
		STATUS  current
		DESCRIPTION
		        "For port configured with OTU2 traffic, if the
			received MFAS does not match with the expected multi
			frame number for five consecutive frames then
			OTU OOM Alarm is generated.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 35 }

        omtp11tPlusOtuSignalFailAlarm OBJECT-TYPE
		SYNTAX  DisplayString
		MAX-ACCESS  read-only
		STATUS  current
		DESCRIPTION
		       "For port configured with OTU2 traffic, 
			OTU SF alarm is generated when BIP errors evaluated by 
			SM field of OTU2 frame exceeds the 
			'omtp11tPlusOtuSignalFailThreshold' threshold
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 36 }

        omtp11tPlusOtuSignalDegradeAlarm OBJECT-TYPE
		SYNTAX  DisplayString
		MAX-ACCESS  read-only
		STATUS  current
		DESCRIPTION
		        "For port configured with OTU2 traffic, 
		        OTU SD alarm is generated when BIP errors evaluated by 
			SM field of OTU2 frame exceeds the 
			'omtp11tPlusOtuSignalDegradeThreshold' threshold.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 37 }

        omtp11tPlusOtuAlarmIndicationSignalAlarm OBJECT-TYPE
		SYNTAX  DisplayString
		MAX-ACCESS  read-only
		STATUS  current
		DESCRIPTION
		         "For port configured with OTU2 traffic, 
			OTU-AIS is generated and transmitted in forward 
			direction, when LOS has been detected at far-end port.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 38 }

        omtp11tPlusOtuIncomingAlignmentErrorAlarm OBJECT-TYPE
		SYNTAX  DisplayString
		MAX-ACCESS  read-only
		STATUS  current
		DESCRIPTION
		        "For port configured with OTU2 traffic, 
			OTU-IAE alarm is generated to indicate a 
			frame alignment error 
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 39 }

        omtp11tPlusOtuTraceIdentifierMismatchAlarm OBJECT-TYPE
		SYNTAX  DisplayString
		MAX-ACCESS  read-only
		STATUS  current
		DESCRIPTION
		        "For port configured with OTU2 traffic, 
			when there is a trace identifier mismatch in the data 
			stream at SM section, OTU-TIM alarm is generated 
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 40 }

        omtp11tPlusOtuBackwardIncomingAlignmentErrorAlarm OBJECT-TYPE
		SYNTAX  DisplayString
		MAX-ACCESS  read-only
		STATUS  current
		DESCRIPTION
		        "For port configured with OTU2 traffic, 
			This alarm conveys that 
			incoming alignment error (IAE) condition that is 
			detected in the far end card
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 41 }

        omtp11tPlusOtuBackwardDefectIndicationAlarm OBJECT-TYPE
		SYNTAX  DisplayString
		MAX-ACCESS  read-only
		STATUS  current
		DESCRIPTION
		        "For port configured with OTU2 traffic, 
			OTU-BDI is sent in backward direction, to indicate that
			a defect like LOS, LOF, OTU-TIM has been detected in the
			receive direction.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 42 }

        omtp11tPlusOduSignalFailAlarm OBJECT-TYPE
		SYNTAX  DisplayString
		MAX-ACCESS  read-only
		STATUS  current
		DESCRIPTION
		        "For port configured with OTU2 traffic, 
			ODU SF alarm is generated when BIP errors evaluated by 
			PM field of OTU2 frame exceeds the 
			'omtp11tPlusOduSignalFailThreshold' threshold.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 51 }

        omtp11tPlusOduSignalDegradeAlarm OBJECT-TYPE
		SYNTAX  DisplayString
		MAX-ACCESS  read-only
		STATUS  current
		DESCRIPTION
			"For port configured with OTU2 traffic, 
			ODU SD alarm is generated when BIP errors evaluated by 
			PM field of OTU2 frame exceeds the 	
			'omtp11tPlusOduSignalDegradeThreshold' threshold.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 52 }

        omtp11tPlusOduAlarmIndicationSignalAlarm OBJECT-TYPE
		SYNTAX  DisplayString
		MAX-ACCESS  read-only
		STATUS  current
		DESCRIPTION
		        "For port configured with OTU2 traffic, 
			ODU-AIS is generated when LOS/TIM/PT mismatch has been 
			detected at far-end port.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 53 }

        omtp11tPlusOduTcm1IncomingAlignmentErrorAlarm OBJECT-TYPE
		SYNTAX  DisplayString
		MAX-ACCESS  read-only
		STATUS  current
		DESCRIPTION
			"For port configured with OTU2 traffic, TCM1 IAE
			shall be declared if the accepted STAT information is
			0b010
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 54 }

        omtp11tPlusOduTcm2IncomingAlignmentErrorAlarm OBJECT-TYPE
		SYNTAX  DisplayString
		MAX-ACCESS  read-only
		STATUS  current
		DESCRIPTION
			"For port configured with OTU2 traffic, TCM2 IAE
			shall be declared if the accepted STAT information is
			0b010
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 55 }

        omtp11tPlusOduTcm3IncomingAlignmentErrorAlarm OBJECT-TYPE
		SYNTAX  DisplayString
		MAX-ACCESS  read-only
		STATUS  current
		DESCRIPTION
			"For port configured with OTU2 traffic, TCM3 IAE
			shall be declared if the accepted STAT information is
			0b010
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 56 }

        omtp11tPlusOduTcm4IncomingAlignmentErrorAlarm OBJECT-TYPE
		SYNTAX  DisplayString
		MAX-ACCESS  read-only
		STATUS  current
		DESCRIPTION
			"For port configured with OTU2 traffic, TCM4 IAE
			shall be declared if the accepted STAT information is
			0b010
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 57 }

        omtp11tPlusOduTcm5IncomingAlignmentErrorAlarm OBJECT-TYPE
		SYNTAX  DisplayString
		MAX-ACCESS  read-only
		STATUS  current
		DESCRIPTION
			"For port configured with OTU2 traffic, TCM5 IAE
			shall be declared if the accepted STAT information is
			0b010
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 58 }

        omtp11tPlusOduTcm6IncomingAlignmentErrorAlarm OBJECT-TYPE
		SYNTAX  DisplayString
		MAX-ACCESS  read-only
		STATUS  current
		DESCRIPTION
			"For port configured with OTU2 traffic, TCM6 IAE
			shall be declared if the accepted STAT information is
			0b010
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 59 }

        omtp11tPlusOduTraceIdentifierMismatchAlarm OBJECT-TYPE
		SYNTAX  DisplayString
		MAX-ACCESS  read-only
		STATUS  current
		DESCRIPTION
			"For port configured with OTU2 traffic, 
			when there is a trace identifier mismatch in the data 
			stream at PM section ODU-TIM alarm is generated.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 60 }

        omtp11tPlusOduLockedDefectAlarm OBJECT-TYPE
		SYNTAX  DisplayString
		MAX-ACCESS  read-only
		STATUS  current
		DESCRIPTION
			"For port configured with OTU2 traffic, 
			The locked maintenance signal is generated on operator
			request in order to lock the signal from user access. It
			consists of a repeating 0b01010101 pattern in the entire
			ODUk signal, which excludes the Frame Alignment
			overhead and the OTUk overhead.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 61 }

        omtp11tPlusOduOpenConnectionIndicationAlarm OBJECT-TYPE
		SYNTAX  DisplayString
		MAX-ACCESS  read-only
		STATUS  current
		DESCRIPTION
			"For port configured with OTU2 traffic, 
			An open connection indication is sent downstream when
			no signal is detected from upstream. It consists of a
			repeating 0b01100110 pattern in the entire ODUk signal,
			which excludes the Frame Alignment overhead and the
			OTUk overhead.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 62 }

        omtp11tPlusOduBackwardDefectIndicationAlarm OBJECT-TYPE
		SYNTAX  DisplayString
		MAX-ACCESS  read-only
		STATUS  current
		DESCRIPTION
		        "For port configured with OTU2 traffic, 
			ODU-BDI is sent in backward direction, to indicate that
			a defect like LOS, LOF, ODU-TIM has been detected in the
			receive direction.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 63 }

        omtp11tPlusOduTcm1BackwardIncomingAlignmentErrorAlarm OBJECT-TYPE
		SYNTAX  DisplayString
		MAX-ACCESS  read-only
		STATUS  current
		DESCRIPTION
			"For port configured with OTU2 traffic, 
			the presence of this alarm conveys that
			TCM1 incoming alignment error (IAE) condition is 
			detected in the far-end card.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 64 }

        omtp11tPlusOduTcm2BackwardIncomingAlignmentErrorAlarm OBJECT-TYPE
		SYNTAX  DisplayString
		MAX-ACCESS  read-only
		STATUS  current
		DESCRIPTION
			"For port configured with OTU2 traffic, 
			the presence of this alarm conveys that
			TCM2 incoming alignment error (IAE) condition is 
			detected in the far-end card.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 65 }

        omtp11tPlusOduTcm3BackwardIncomingAlignmentErrorAlarm OBJECT-TYPE
		SYNTAX  DisplayString
		MAX-ACCESS  read-only
		STATUS  current
		DESCRIPTION
			"For port configured with OTU2 traffic, 
			the presence of this alarm conveys that
			TCM3 incoming alignment error (IAE) condition is 
			detected in the far-end card.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 66 }

        omtp11tPlusOduTcm4BackwardIncomingAlignmentErrorAlarm OBJECT-TYPE
		SYNTAX  DisplayString
		MAX-ACCESS  read-only
		STATUS  current
		DESCRIPTION
			"For port configured with OTU2 traffic, 
			the presence of this alarm conveys that
			TCM4 incoming alignment error (IAE) condition is 
			detected in the far-end card.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 67 }

        omtp11tPlusOduTcm5BackwardIncomingAlignmentErrorAlarm OBJECT-TYPE
		SYNTAX  DisplayString
		MAX-ACCESS  read-only
		STATUS  current
		DESCRIPTION
			"For port configured with OTU2 traffic, 
			the presence of this alarm conveys that
			TCM5 incoming alignment error (IAE) condition is 
			detected in the far-end card.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 68 }

        omtp11tPlusOduTcm6BackwardIncomingAlignmentErrorAlarm OBJECT-TYPE
		SYNTAX  DisplayString
		MAX-ACCESS  read-only
		STATUS  current
		DESCRIPTION
			"For port configured with OTU2 traffic, 
			the presence of this alarm conveys that
			TCM6 incoming alignment error (IAE) condition is 
			detected in the far-end card.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 69 }

        omtp11tPlusOpuPayloadMismatchAlarm OBJECT-TYPE
		SYNTAX  DisplayString
		MAX-ACCESS  read-only
		STATUS  current
		DESCRIPTION
		        "For port configured with OTU2 traffic, 
			OPU-PLM Alarm is declared if the accepted payload type
			is not equal to the expected payload type.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 70 }

        omtp11tPlusOchLossOfPayloadAlarm OBJECT-TYPE
		SYNTAX  DisplayString
		MAX-ACCESS  read-only
		STATUS  current
		DESCRIPTION
		        "If input power level at the XFP is less than 
			-21dbm this this alarm will be generated.
			-----------------------------
			omtp11tPlusInterfaceNumber:
			1 - LINE-1
			2 - LINE-2
			-----------------------------
			Values :
			If Alarm is Present - Date and Time Stamp
				eg:2017-5-18,9:47:20.0,+5:30
			If Alarm is Absent  - 0
			-----------------------------"
               ::= { omtp11tPlusAlarmQueryEntry 71 }

	omtp11tPlusAlarmQueryTableRowStatus OBJECT-TYPE
              SYNTAX      RowStatus
              MAX-ACCESS  read-write
              STATUS      current
              DESCRIPTION
                      "	This is MIB realted property,
			NOT to be considered as a card property"
              ::= { omtp11tPlusAlarmQueryEntry 165 }	


--*****************************************************************************
--				    PERFORMANCE
--***************************************************************************** 	
	omtp11tPlusPerformanceTable OBJECT-TYPE
		SYNTAX SEQUENCE OF Omtp11tPlusPerformanceEntry
		MAX-ACCESS not-accessible
		STATUS current
		DESCRIPTION
			"we can get performance details of the OMTP11T-PLUS Card"
	
		::= { omtp11tPlusPerformance 1 }

	omtp11tPlusPerformanceEntry OBJECT-TYPE
		SYNTAX Omtp11tPlusPerformanceEntry
		MAX-ACCESS not-accessible
		STATUS current
		DESCRIPTION 
			""
	
		INDEX   { node, rack , subRack , slot , omtp11tPlusInterfaceNumber}
	
		::= { omtp11tPlusPerformanceTable 1 }

		Omtp11tPlusPerformanceEntry ::= 
			SEQUENCE {
					omtp11tPlusXfpInputPower                                     		DisplayString,
				        omtp11tPlusXfpOutputPower                                    		DisplayString,
				        omtp11tPlusXfpBiasCurrent                                    		DisplayString,
				        omtp11tPlusXfpSupplyVoltage                                  		DisplayString,
				        omtp11tPlusXfpTemperature                                    		DisplayString,
				        omtp11tPlusOtnFecUncorrectedWords                            		DisplayString,
				        omtp11tPlusOtnFecCorrectedBits                              		DisplayString,       
				        omtp11tPlusOtnFecZerosCorrectedBits                          		DisplayString,
				        omtp11tPlusOtnFecOnesCorrectedBits                           		DisplayString,
				        omtp11tPlusOtuBitInterleavedParityErrors                     		DisplayString,
				        omtp11tPlusOtuIncomingAlignmentErrorSeconds                  		DisplayString,
				        omtp11tPlusOtuBackwardErrorIndicationErrorCount                  	DisplayString,
				        omtp11tPlusOtuBackwardIncomingAlignmentErrorSeconds          		DisplayString,
				        omtp11tPlusOtuErrorFreeSeconds						DisplayString,
				        omtp11tPlusOtuErrorSeconds						DisplayString,
				        omtp11tPlusOtuBackgroundBlockErrors					DisplayString,
				        omtp11tPlusOtuSevereErrorSeconds					DisplayString,
				        omtp11tPlusOtuUnavailableSeconds					DisplayString,
				        omtp11tPlusOtuBackgroundBlockErrorRatio					DisplayString,
				        omtp11tPlusOtuSevereErrorSecondsErrorRatio				DisplayString,
				        omtp11tPlusOtuFarEndErrorFreeSeconds					DisplayString,
				        omtp11tPlusOtuFarEndErrorSeconds					DisplayString,
				        omtp11tPlusOtuFarEndBackgroundBlockErrors				DisplayString,
				        omtp11tPlusOtuFarEndSevereErrorSeconds					DisplayString,
				        omtp11tPlusOtuFarEndUnavailableSeconds					DisplayString,
				        omtp11tPlusOtuFarEndBackgroundBlockErrorRatio				DisplayString,
				        omtp11tPlusOtuFarEndSevereErrorSecondsErrorRatio			DisplayString,
					omtp11tPlusOtuErrorRatio						DisplayString,
					omtp11tPlusOtuBitErrorRate						DisplayString,
					omtp11tPlusOtuFramesReceived						DisplayString,
				        omtp11tPlusOduBitInterleavedParityErrors				DisplayString,
				        omtp11tPlusOduTcm1BitInterleavedParityErrors				DisplayString,
				        omtp11tPlusOduTcm2BitInterleavedParityErrors				DisplayString,
				        omtp11tPlusOduTcm3BitInterleavedParityErrors				DisplayString,
				        omtp11tPlusOduTcm4BitInterleavedParityErrors				DisplayString,
				        omtp11tPlusOduTcm5BitInterleavedParityErrors				DisplayString,
				        omtp11tPlusOduTcm6BitInterleavedParityErrors				DisplayString,
				        omtp11tPlusOduTcm1IncomingAlignmentErrorSeconds				DisplayString,
				        omtp11tPlusOduBackwardErrorIndicationErrorCount				DisplayString,
				        omtp11tPlusOduTcm1BackwardErrorIndicationErrorCount			DisplayString,
				        omtp11tPlusOduTcm2BackwardErrorIndicationErrorCount			DisplayString,
				        omtp11tPlusOduTcm3BackwardErrorIndicationErrorCount			DisplayString,
				        omtp11tPlusOduTcm4BackwardErrorIndicationErrorCount			DisplayString,
				        omtp11tPlusOduTcm5BackwardErrorIndicationErrorCount			DisplayString,
				        omtp11tPlusOduTcm6BackwardErrorIndicationErrorCount			DisplayString,
				        omtp11tPlusOduTcm1BackwardIncomingAlignmentErrorSeconds			DisplayString,
				        omtp11tPlusOduDelayMeasurement						DisplayString,
				        omtp11tPlusOduErrorFreeSeconds						DisplayString,
				        omtp11tPlusOduErrorSeconds						DisplayString,
				        omtp11tPlusOduBackgroundBlockErrors					DisplayString,
				        omtp11tPlusOduSevereErrorSeconds					DisplayString,
				        omtp11tPlusOduUnavailableSeconds					DisplayString,
				        omtp11tPlusOduBackgroundBlockErrorRatio					DisplayString,
				        omtp11tPlusOduSevereErrorSecondsErrorRatio				DisplayString,
				        omtp11tPlusOduFarEndErrorFreeSeconds					DisplayString,
				        omtp11tPlusOduFarEndErrorSeconds					DisplayString,
				        omtp11tPlusOduFarEndBackgroundBlockErrors				DisplayString,
				        omtp11tPlusOduFarEndSevereErrorSeconds					DisplayString,
				        omtp11tPlusOduFarEndUnavailableSeconds					DisplayString,
				        omtp11tPlusOduFarEndBackgroundBlockErrorRatio				DisplayString,
				        omtp11tPlusOduFarEndSevereErrorSecondsErrorRatio			DisplayString,
					omtp11tPlusPerformanceTableRowStatus					RowStatus
			}
              
        omtp11tPlusXfpInputPower OBJECT-TYPE
		SYNTAX  DisplayString
		MAX-ACCESS  read-only
		STATUS  current
		DESCRIPTION
			"Gives the current Input power(dbm) received at the port
			-----------------------------
			omtp11tPlusInterfaceNumber:
			1 - CLIENT-1
			2 - LINE-1
			-----------------------------
			Values:
			eg: -9.0
			-----------------------------"
        ::= { omtp11tPlusPerformanceEntry 1 }

        omtp11tPlusXfpOutputPower OBJECT-TYPE
		SYNTAX  DisplayString
		MAX-ACCESS  read-only
		STATUS  current
		DESCRIPTION
			"Gives the current Output power(dbm) transmitted by the port
			-----------------------------
			omtp11tPlusInterfaceNumber:
			1 - CLIENT-1
			2 - LINE-1
			-----------------------------
			Values:
			eg: -0.6
			-----------------------------"
        ::= { omtp11tPlusPerformanceEntry 2 }


	omtp11tPlusXfpBiasCurrent OBJECT-TYPE
		SYNTAX  DisplayString
		MAX-ACCESS  read-only
		STATUS  current
		DESCRIPTION
			"Gives the bias current(mA) thats transmitted at the port
			-----------------------------
			omtp11tPlusInterfaceNumber:
			1 - CLIENT-1
			2 - LINE-1
			-----------------------------
			Values:
			eg: 55
			-----------------------------"
        ::= { omtp11tPlusPerformanceEntry 3 }

	omtp11tPlusXfpSupplyVoltage OBJECT-TYPE
		SYNTAX  DisplayString
		MAX-ACCESS  read-only
		STATUS  current
		DESCRIPTION
			"Gives the Supply Voltage of the port
			-----------------------------
			omtp11tPlusInterfaceNumber:
			1 - CLIENT-1
			2 - LINE-1
			-----------------------------
			Values:
			eg: 3.3
			-----------------------------"
	::= { omtp11tPlusPerformanceEntry 4 }

	omtp11tPlusXfpTemperature OBJECT-TYPE
		SYNTAX  DisplayString
		MAX-ACCESS  read-only
		STATUS  current
		DESCRIPTION
			"Gives the temperature(degree celcius) of the transmitter at  the port
			-----------------------------
			omtp11tPlusInterfaceNumber:
			1 - CLIENT-1
			2 - LINE-1
			-----------------------------
			Values:
			eg: 33.35
			-----------------------------"
        ::= { omtp11tPlusPerformanceEntry 5 }

        omtp11tPlusOtnFecUncorrectedWords OBJECT-TYPE
		SYNTAX  DisplayString
		MAX-ACCESS  read-only
		STATUS  current
		DESCRIPTION
			"For port configured with OTU2 traffic, 
			OTU Uncorrected Word Error Counter counts the number of
			FEC errored code words that could not be corrected.
			-----------------------------
			omtp11tPlusInterfaceNumber:
			1 - CLIENT-1
			2 - LINE-1
			-----------------------------
			Values:
			eg: 1234
			-----------------------------"
        ::= { omtp11tPlusPerformanceEntry 11 }

	omtp11tPlusOtnFecCorrectedBits OBJECT-TYPE
		SYNTAX  DisplayString
		MAX-ACCESS  read-only
		STATUS  current
		DESCRIPTION
			"For port configured with OTU2 traffic, 
			OTU Corrected Bit Error Counter counts the number of
			FEC error bits that could be corrected(sum of ones
			corrected and zeros corrected bits).
			-----------------------------
			omtp11tPlusInterfaceNumber:
			1 - CLIENT-1
			2 - LINE-1
			-----------------------------
			Values:
			eg: 1234
			-----------------------------"
        ::= { omtp11tPlusPerformanceEntry 12 }

        omtp11tPlusOtnFecZerosCorrectedBits OBJECT-TYPE
		SYNTAX  DisplayString
		MAX-ACCESS  read-only
		STATUS  current
		DESCRIPTION
			"For port configured with OTU2 traffic, 
			OTU Zero Corrected Bits Error Counter counts the number
			of FEC error bits that could be corrected from
			one to zero value(Expected 0 but received as 1).
			-----------------------------
			omtp11tPlusInterfaceNumber:
			1 - CLIENT-1
			2 - LINE-1
			-----------------------------
			Values:
			eg: 1234
			-----------------------------"
	::= { omtp11tPlusPerformanceEntry 13 }

        omtp11tPlusOtnFecOnesCorrectedBits OBJECT-TYPE
		SYNTAX  DisplayString
		MAX-ACCESS  read-only
		STATUS  current
		DESCRIPTION
			"For port configured with OTU2 traffic, 
			OTU Ones Corrected Byte Error Counter counts the number
			of FEC error bytes that could be corrected from
			zero to one value(Expected 1 but received as 0).
			-----------------------------
			omtp11tPlusInterfaceNumber:
			1 - CLIENT-1
			2 - LINE-1
			-----------------------------
			Values:
			eg: 1234
			-----------------------------"
		::= { omtp11tPlusPerformanceEntry 14 }

        omtp11tPlusOtuBitInterleavedParityErrors OBJECT-TYPE
		SYNTAX  DisplayString
		MAX-ACCESS  read-only
		STATUS  current
		DESCRIPTION
			"For port configured with OTU2 traffic, 
			OTU-BIP Counter counts the Parity errors evaluated by
			SM field of an OTU2 frame.
			-----------------------------
			omtp11tPlusInterfaceNumber:
			1 - CLIENT-1
			2 - LINE-1
			-----------------------------
			Values:
			eg: 1234
			-----------------------------"
	::= { omtp11tPlusPerformanceEntry 15 }

        omtp11tPlusOtuIncomingAlignmentErrorSeconds OBJECT-TYPE
		SYNTAX  DisplayString
		MAX-ACCESS  read-only
		STATUS  current
		DESCRIPTION
			"For port configured with OTU2 traffic, 
			OTU Incoming Alignment Error Count increases,
			when OTU IAE Alarm is detected in that particular second
			of the incoming OTU signal
			-----------------------------
			omtp11tPlusInterfaceNumber:
			1 - CLIENT-1
			2 - LINE-1
			-----------------------------
			Values:
			eg: 1234
			-----------------------------"
	::= { omtp11tPlusPerformanceEntry 16 }

        omtp11tPlusOtuBackwardErrorIndicationErrorCount OBJECT-TYPE
		SYNTAX  DisplayString
		MAX-ACCESS  read-only
		STATUS  current
		DESCRIPTION
			"For port configured with OTU2 traffic, 
			OTU-BEI Counter increases when SM-BEI Alarm is 
			detected in that particular second
			of the incoming OTU signal
			-----------------------------
			omtp11tPlusInterfaceNumber:
			1 - CLIENT-1
			2 - LINE-1
			-----------------------------
			Values:
			eg: 1234
			-----------------------------"
	::= { omtp11tPlusPerformanceEntry 17 }

        omtp11tPlusOtuBackwardIncomingAlignmentErrorSeconds OBJECT-TYPE
		SYNTAX  DisplayString
		MAX-ACCESS  read-only
		STATUS  current
		DESCRIPTION
			"For port configured with OTU2 traffic, 
			OTU-BIAE Counter increases when SM-BIAE Alarm is 
			detected in that particular second
			of the incoming OTU signal
			-----------------------------
			omtp11tPlusInterfaceNumber:
			1 - CLIENT-1
			2 - LINE-1
			-----------------------------
			Values:
			eg: 1234
			-----------------------------"
	::= { omtp11tPlusPerformanceEntry 18 }

        omtp11tPlusOtuErrorFreeSeconds OBJECT-TYPE
		SYNTAX  DisplayString
		MAX-ACCESS  read-only
		STATUS  current
		DESCRIPTION
			"For port configured with OTU2 traffic, 
			OTU Error Free Seconds increases when no BIP errors
			or defects are detected
			-----------------------------
			omtp11tPlusInterfaceNumber:
			1 - CLIENT-1
			2 - LINE-1
			-----------------------------
			Values:
			eg: 1234
			-----------------------------"
	::= { omtp11tPlusPerformanceEntry 19 }

        omtp11tPlusOtuErrorSeconds OBJECT-TYPE
		SYNTAX  DisplayString
		MAX-ACCESS  read-only
		STATUS  current
		DESCRIPTION
			"For port configured with OTU2 traffic, 
			OTU Error Seconds increases when any defects like 
			OTU-AIS, SM-TIM etc are detected at the
			section monitoring level
			-----------------------------
			omtp11tPlusInterfaceNumber:
			1 - CLIENT-1
			2 - LINE-1
			-----------------------------
			Values:
			eg: 1234
			-----------------------------"
	::= { omtp11tPlusPerformanceEntry 20 }

        omtp11tPlusOtuBackgroundBlockErrors OBJECT-TYPE
		SYNTAX  DisplayString
		MAX-ACCESS  read-only
		STATUS  current
		DESCRIPTION
			"For port configured with OTU2 traffic, 
			OTU Background Block Errors increases on defects 
			detected and when BIP errors are less than 15% errored
			blocks received 
			-----------------------------
			omtp11tPlusInterfaceNumber:
			1 - CLIENT-1
			2 - LINE-1
			-----------------------------
			Values:
			eg: 1234
			-----------------------------"
	::= { omtp11tPlusPerformanceEntry 21 }

        omtp11tPlusOtuSevereErrorSeconds OBJECT-TYPE
		SYNTAX  DisplayString
		MAX-ACCESS  read-only
		STATUS  current
		DESCRIPTION
			"For port configured with OTU2 traffic, 
			OTU Severe Error Seconds increases on defects
			detected and when BIP errors are greater than or
			equal to 15% errored blocks received 
			-----------------------------
			omtp11tPlusInterfaceNumber:
			1 - CLIENT-1
			2 - LINE-1
			-----------------------------
			Values:
			eg: 1234
			-----------------------------"
	::= { omtp11tPlusPerformanceEntry 22 }

        omtp11tPlusOtuUnavailableSeconds OBJECT-TYPE
		SYNTAX  DisplayString
		MAX-ACCESS  read-only
		STATUS  current
		DESCRIPTION
			"For port configured with OTU2 traffic, 
			OTU Unavailable Seconds increases,
			when 10 consecutive
			Severe OTU Error seconds are detected
			-----------------------------
			omtp11tPlusInterfaceNumber:
			1 - CLIENT-1
			2 - LINE-1
			-----------------------------
			Values:
			eg: 1234
			-----------------------------"
	::= { omtp11tPlusPerformanceEntry 23 }

        omtp11tPlusOtuBackgroundBlockErrorRatio OBJECT-TYPE
		SYNTAX  DisplayString
		MAX-ACCESS  read-only
		STATUS  current
		DESCRIPTION
			"For port configured with OTU2 traffic, 
			Gives OTU Background Block Error Seconds Error Ratio.
			The ratio of BBE in available time to total seconds
			in available time during a fixed measurement interval.
			-----------------------------
			omtp11tPlusInterfaceNumber:
			1 - CLIENT-1
			2 - LINE-1
			-----------------------------
			Values:
			eg: 1e-3
			-----------------------------"
	::= { omtp11tPlusPerformanceEntry 25 }

        omtp11tPlusOtuSevereErrorSecondsErrorRatio OBJECT-TYPE
		SYNTAX  DisplayString
		MAX-ACCESS  read-only
		STATUS  current
		DESCRIPTION
			"For port configured with OTU2 traffic, 
			Gives OTU Severe Error Seconds Error Ratio.
			The ratio of SES in available time to total seconds
			in available time during a fixed measurement interval.
			-----------------------------
			omtp11tPlusInterfaceNumber:
			1 - CLIENT-1
			2 - LINE-1
			-----------------------------
			Values:
			eg: 1e-3
			-----------------------------"
	::= { omtp11tPlusPerformanceEntry 26 }

        omtp11tPlusOtuFarEndErrorFreeSeconds OBJECT-TYPE
		SYNTAX  DisplayString
		MAX-ACCESS  read-only
		STATUS  current
		DESCRIPTION
			"For port configured with OTU2 traffic, 
			OTU Far end Error Free Seconds, increases when no
			 backward errors or defects like BDI or BEI
			are detected in the incoming OTU signal.
			-----------------------------
			omtp11tPlusInterfaceNumber:
			1 - CLIENT-1
			2 - LINE-1
			-----------------------------
			Values:
			eg: 1234
			-----------------------------"
	::= { omtp11tPlusPerformanceEntry 27 }

        omtp11tPlusOtuFarEndErrorSeconds OBJECT-TYPE
		SYNTAX  DisplayString
		MAX-ACCESS  read-only
		STATUS  current
		DESCRIPTION
			"For port configured with OTU2 traffic, 
			OTU Far End Error Seconds increases on
			detection of defects like BDI in incoming
			OTU signal.
			-----------------------------
			omtp11tPlusInterfaceNumber:
			1 - CLIENT-1
			2 - LINE-1
			-----------------------------
			Values:
			eg: 1234
			-----------------------------"
	::= { omtp11tPlusPerformanceEntry 28 }

        omtp11tPlusOtuFarEndBackgroundBlockErrors OBJECT-TYPE
		SYNTAX  DisplayString
		MAX-ACCESS  read-only
		STATUS  current
		DESCRIPTION
			"For port configured with OTU2 traffic, 
			OTU Far End Background Block Errors increases when BEI
			errors are less than 15% Errored Blocks in incoming
			OTU signal.
			-----------------------------
			omtp11tPlusInterfaceNumber:
			1 - CLIENT-1
			2 - LINE-1
			-----------------------------
			Values:
			eg: 1234
			-----------------------------"
	::= { omtp11tPlusPerformanceEntry 29 }

        omtp11tPlusOtuFarEndSevereErrorSeconds OBJECT-TYPE
		SYNTAX  DisplayString
		MAX-ACCESS  read-only
		STATUS  current
		DESCRIPTION
			"For port configured with OTU2 traffic, 
			OTU Far End Severe Error Seconds increases on defects
			like BDI are detected and when BEI errors are greater
			than or equal to 15% Errored Blocks in incoming OTU 
			signal.
			-----------------------------
			omtp11tPlusInterfaceNumber:
			1 - CLIENT-1
			2 - LINE-1
			-----------------------------
			Values:
			eg: 1234
			-----------------------------"
	::= { omtp11tPlusPerformanceEntry 30 }

        omtp11tPlusOtuFarEndUnavailableSeconds OBJECT-TYPE
		SYNTAX  DisplayString
		MAX-ACCESS  read-only
		STATUS  current
		DESCRIPTION
			"For port configured with OTU2 traffic, 
			OTU Unavailable Seconds increases, after 9 consecutive
			OTU Far End Severe Error seconds are detected
			-----------------------------
			omtp11tPlusInterfaceNumber:
			1 - CLIENT-1
			2 - LINE-1
			-----------------------------
			Values:
			eg: 1234
			-----------------------------"
	::= { omtp11tPlusPerformanceEntry 31 }

        omtp11tPlusOtuFarEndBackgroundBlockErrorRatio OBJECT-TYPE
		SYNTAX  DisplayString
		MAX-ACCESS  read-only
		STATUS  current
		DESCRIPTION
			"For port configured with OTU2 traffic, 
			Gives Otu Far End Background Block Error Ratio.
			The ratio of BBE in available time to total seconds
			in available time during a fixed measurement interval.
			-----------------------------
			omtp11tPlusInterfaceNumber:
			1 - CLIENT-1
			2 - LINE-1
			-----------------------------
			Values:
			eg: 1e-3
			-----------------------------"
	::= { omtp11tPlusPerformanceEntry 33 }

        omtp11tPlusOtuFarEndSevereErrorSecondsErrorRatio OBJECT-TYPE
		SYNTAX  DisplayString
		MAX-ACCESS  read-only
		STATUS  current
		DESCRIPTION
			"For port configured with OTU2 traffic, 
			Gives Otu Far End Severe Error Seconds Error Ratio.
			The ratio of SES in available time to total seconds
			in available time during a fixed measurement interval.
			-----------------------------
			omtp11tPlusInterfaceNumber:
			1 - CLIENT-1
			2 - LINE-1
			-----------------------------
			Values:
			eg: 1e-3
			-----------------------------"
	::= { omtp11tPlusPerformanceEntry 34 }

	omtp11tPlusOtuErrorRatio   OBJECT-TYPE
              SYNTAX  DisplayString
              MAX-ACCESS  read-only
              STATUS  current
              DESCRIPTION
			"For port configured with OTU2 traffic, 
			OTU Error Ratio for requested port. The ratio of 
			number of error bits to the number of bits received in
			a particular second
			-----------------------------
			omtp11tPlusInterfaceNumber:
			1 - CLIENT-1
			2 - LINE-1
			-----------------------------	
			Value:
			eg: 4.0
			-----------------------------"
	::= { omtp11tPlusPerformanceEntry 35 } 

	omtp11tPlusOtuBitErrorRate  OBJECT-TYPE
              SYNTAX  DisplayString
              MAX-ACCESS  read-only
              STATUS  current
              DESCRIPTION
			"For port configured with OTU2 traffic, 
			Bit error rate is the Error ratio multiplied by the
			OTU2 standard signal data-rate( 10.709225316 Gbps )
			-----------------------------
			omtp11tPlusInterfaceNumber:
			1 - CLIENT-1
			2 - LINE-1
			-----------------------------	
			Value:
			eg: 4.0
			-----------------------------"
	::= { omtp11tPlusPerformanceEntry 36 }

	omtp11tPlusOtuFramesReceived  OBJECT-TYPE
              SYNTAX  DisplayString
              MAX-ACCESS  read-only
              STATUS  current
              DESCRIPTION
			"For port configured with OTU2 traffic, gives the 
			gives the number of OTU frames transmitted.
			-----------------------------
			omtp11tPlusInterfaceNumber:
			1 - CLIENT-1
			2 - LINE-1
			-----------------------------		
			Value:
			eg: 4.0
			-----------------------------"
	::= { omtp11tPlusPerformanceEntry 37 }

        omtp11tPlusOduBitInterleavedParityErrors OBJECT-TYPE
		SYNTAX  DisplayString
		MAX-ACCESS  read-only
		STATUS  current
		DESCRIPTION
			"For port configured with OTU2 traffic, 
			ODU-BIP Counter counts the Parity errors evaluated by
			PM field of an OTU2 frame
			-----------------------------
			omtp11tPlusInterfaceNumber:
			1 - CLIENT-1
			2 - LINE-1
			-----------------------------
			Values:
			eg: 1234
			-----------------------------"
	::= { omtp11tPlusPerformanceEntry 41 }

        omtp11tPlusOduTcm1BitInterleavedParityErrors OBJECT-TYPE
		SYNTAX  DisplayString
		MAX-ACCESS  read-only
		STATUS  current
		DESCRIPTION
			"For port configured with OTU2 traffic, 
			TCM1-BIP Counter counts the Parity errors evaluated by
			TCM1 field in ODU2 frame
			-----------------------------
			omtp11tPlusInterfaceNumber:
			1 - CLIENT-1
			2 - LINE-1
			-----------------------------
			Values:
			eg: 1234
			-----------------------------"
	::= { omtp11tPlusPerformanceEntry 42 }

        omtp11tPlusOduTcm2BitInterleavedParityErrors OBJECT-TYPE
		SYNTAX  DisplayString
		MAX-ACCESS  read-only
		STATUS  current
		DESCRIPTION
			"For port configured with OTU2 traffic, 
			TCM2-BIP Counter counts the Parity errors evaluated by
			TCM2 field in ODU2 frame
			-----------------------------
			omtp11tPlusInterfaceNumber:
			1 - CLIENT-1
			2 - LINE-1
			-----------------------------
			Values:
			eg: 1234
			-----------------------------"
	::= { omtp11tPlusPerformanceEntry 43 }

        omtp11tPlusOduTcm3BitInterleavedParityErrors OBJECT-TYPE
		SYNTAX  DisplayString
		MAX-ACCESS  read-only
		STATUS  current
		DESCRIPTION
			"For port configured with OTU2 traffic, 
			TCM3-BIP Counter counts the Parity errors evaluated by
			TCM3 field in ODU2 frame
			-----------------------------
			omtp11tPlusInterfaceNumber:
			1 - CLIENT-1
			2 - LINE-1
			-----------------------------
			Values:
			eg: 1234
			-----------------------------"
	::= { omtp11tPlusPerformanceEntry 44 }

        omtp11tPlusOduTcm4BitInterleavedParityErrors OBJECT-TYPE
		SYNTAX  DisplayString
		MAX-ACCESS  read-only
		STATUS  current
		DESCRIPTION
			"For port configured with OTU2 traffic, 
			TCM4-BIP Counter counts the Parity errors evaluated by
			TCM4 field in ODU2 frame
			-----------------------------
			omtp11tPlusInterfaceNumber:
			1 - CLIENT-1
			2 - LINE-1
			-----------------------------
			Values:
			eg: 1234
			-----------------------------"
	::= { omtp11tPlusPerformanceEntry 45 }

        omtp11tPlusOduTcm5BitInterleavedParityErrors OBJECT-TYPE
		SYNTAX  DisplayString
		MAX-ACCESS  read-only
		STATUS  current
		DESCRIPTION
			"For port configured with OTU2 traffic, 
			TCM5-BIP Counter counts the Parity errors evaluated by
			TCM5 field in ODU2 frame
			-----------------------------
			omtp11tPlusInterfaceNumber:
			1 - CLIENT-1
			2 - LINE-1
			-----------------------------
			Values:
			eg: 1234
			-----------------------------"
	::= { omtp11tPlusPerformanceEntry 46 }

        omtp11tPlusOduTcm6BitInterleavedParityErrors OBJECT-TYPE
		SYNTAX  DisplayString
		MAX-ACCESS  read-only
		STATUS  current
		DESCRIPTION
			"For port configured with OTU2 traffic, 
			TCM6-BIP Counter counts the Parity errors evaluated by
			TCM6 field in ODU2 frame
			-----------------------------
			omtp11tPlusInterfaceNumber:
			1 - CLIENT-1
			2 - LINE-1
			-----------------------------
			Values:
			eg: 1234
			-----------------------------"
	::= { omtp11tPlusPerformanceEntry 47 }

        omtp11tPlusOduTcm1IncomingAlignmentErrorSeconds OBJECT-TYPE
		SYNTAX  DisplayString
		MAX-ACCESS  read-only
		STATUS  current
		DESCRIPTION
			"For port configured with OTU2 traffic,
			ODU Incoming Alignment Error Count increases,
			when ODU-TCM1-IAE is detected in that particular second
			of the incoming OTU signal
			-----------------------------
			omtp11tPlusInterfaceNumber:
			1 - CLIENT-1
			2 - LINE-1
			-----------------------------
			Values:
			eg: 1234
			-----------------------------"
	::= { omtp11tPlusPerformanceEntry 48 }

        omtp11tPlusOduBackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code.
			-----------------------------
			omtp11tPlusInterfaceNumber:
			1 - CLIENT-1
			2 - LINE-1
			-----------------------------
			Values:
			eg: 1234
			-----------------------------"
	::= { omtp11tPlusPerformanceEntry 49 }

        omtp11tPlusOduTcm1BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-1 level.
			-----------------------------
			omtp11tPlusInterfaceNumber:
			1 - CLIENT-1
			2 - LINE-1
			-----------------------------
			Values:
			eg: 1234
			-----------------------------"
	::= { omtp11tPlusPerformanceEntry 50 }

        omtp11tPlusOduTcm2BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-2 level.
			-----------------------------
			omtp11tPlusInterfaceNumber:
			1 - CLIENT-1
			2 - LINE-1
			-----------------------------
			Values:
			eg: 1234
			-----------------------------"
	::= { omtp11tPlusPerformanceEntry 51 }

        omtp11tPlusOduTcm3BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-3 level.
			-----------------------------
			omtp11tPlusInterfaceNumber:
			1 - CLIENT-1
			2 - LINE-1
			-----------------------------
			Values:
			eg: 1234
			-----------------------------"
	::= { omtp11tPlusPerformanceEntry 52 }

        omtp11tPlusOduTcm4BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-4 level.
			-----------------------------
			omtp11tPlusInterfaceNumber:
			1 - CLIENT-1
			2 - LINE-1
			-----------------------------
			Values:
			eg: 1234
			-----------------------------"
	::= { omtp11tPlusPerformanceEntry 53 }

        omtp11tPlusOduTcm5BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-5 level.
			-----------------------------
			omtp11tPlusInterfaceNumber:
			1 - CLIENT-1
			2 - LINE-1
			-----------------------------
			Values:
			eg: 1234
			-----------------------------"
	::= { omtp11tPlusPerformanceEntry 54 }

        omtp11tPlusOduTcm6BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-6 level.
			-----------------------------
			omtp11tPlusInterfaceNumber:
			1 - CLIENT-1
			2 - LINE-1
			-----------------------------
			Values:
			eg: 1234
			-----------------------------"
	::= { omtp11tPlusPerformanceEntry 55 }

        omtp11tPlusOduTcm1BackwardIncomingAlignmentErrorSeconds OBJECT-TYPE
		SYNTAX  DisplayString
		MAX-ACCESS  read-only
		STATUS  current
		DESCRIPTION
			"For port configured with OTU2 traffic,
			ODU Backward Incoming Alignment Error Count increases,
			when ODU-TCM1-BIAE is detected in that particular second
			of the incoming OTU signal
			-----------------------------
			omtp11tPlusInterfaceNumber:
			1 - CLIENT-1
			2 - LINE-1
			-----------------------------
			Values:
			eg: 1234
			-----------------------------"
	::= { omtp11tPlusPerformanceEntry 56 }

        omtp11tPlusOduDelayMeasurement OBJECT-TYPE
		SYNTAX  DisplayString
		MAX-ACCESS  read-only
		STATUS  current
		DESCRIPTION
			"For port configured with OTU2 traffic, 
			Gives Delay measurement of OTU frame
			-----------------------------
			omtp11tPlusInterfaceNumber:
			1 - CLIENT-1
			2 - LINE-1
			-----------------------------
			Values:
			eg: Reserved
			-----------------------------"
	::= { omtp11tPlusPerformanceEntry 57 }

        omtp11tPlusOduErrorFreeSeconds OBJECT-TYPE
		SYNTAX  DisplayString
		MAX-ACCESS  read-only
		STATUS  current
		DESCRIPTION
			"For port configured with OTU2 traffic, 
			ODU Error Free Seconds increases,
			when no BIP errors or defects are detected at the
			path monitoring level
			-----------------------------
			omtp11tPlusInterfaceNumber:
			1 - CLIENT-1
			2 - LINE-1
			-----------------------------
			Values:
			eg: 1234
			-----------------------------"
	::= { omtp11tPlusPerformanceEntry 58 }

        omtp11tPlusOduErrorSeconds OBJECT-TYPE
		SYNTAX  DisplayString
		MAX-ACCESS  read-only
		STATUS  current
		DESCRIPTION
			"For port configured with OTU2 traffic, 
			ODU Error Seconds increases on defects detected at the
			path monitoring level
			-----------------------------
			omtp11tPlusInterfaceNumber:
			1 - CLIENT-1
			2 - LINE-1
			-----------------------------
			Values:
			eg: 1234
			-----------------------------"
	::= { omtp11tPlusPerformanceEntry 59 }

        omtp11tPlusOduBackgroundBlockErrors OBJECT-TYPE
		SYNTAX  DisplayString
		MAX-ACCESS  read-only
		STATUS  current
		DESCRIPTION
			"For port configured with OTU2 traffic, 
			ODU Background Block Errors increases on defects 
			detected and when BIP errors are less than 15% 
			Errored Blocks in incoming OTU signal.
			-----------------------------
			omtp11tPlusInterfaceNumber:
			1 - CLIENT-1
			2 - LINE-1
			-----------------------------
			Values:
			eg: 1234
			-----------------------------"
	::= { omtp11tPlusPerformanceEntry 60 }

        omtp11tPlusOduSevereErrorSeconds OBJECT-TYPE
		SYNTAX  DisplayString
		MAX-ACCESS  read-only
		STATUS  current
		DESCRIPTION
			"For port configured with OTU2 traffic, 
			ODU Severe Error Seconds increases on defects detected
			and when BIP errors are more than 15% Errored Blocks
			in incoming OTU signal.
			-----------------------------
			omtp11tPlusInterfaceNumber:
			1 - CLIENT-1
			2 - LINE-1
			-----------------------------
			Values:
			eg: 1234
			-----------------------------"
	::= { omtp11tPlusPerformanceEntry 61 }

        omtp11tPlusOduUnavailableSeconds OBJECT-TYPE
		SYNTAX  DisplayString
		MAX-ACCESS  read-only
		STATUS  current
		DESCRIPTION
			"For port configured with OTU2 traffic, 
			ODU Unavailable Seconds increases, when 10 consecutive
			Severe
			ODU Error seconds are detected
			-----------------------------
			omtp11tPlusInterfaceNumber:
			1 - CLIENT-1
			2 - LINE-1
			-----------------------------
			Values:
			eg: 1234
			-----------------------------"
	::= { omtp11tPlusPerformanceEntry 62 }

        omtp11tPlusOduBackgroundBlockErrorRatio OBJECT-TYPE
		SYNTAX  DisplayString
		MAX-ACCESS  read-only
		STATUS  current
		DESCRIPTION
			"For port configured with OTU2 traffic, 
			Gives ODU Background Block Error Ratio
			The ratio of BBE in available time to total seconds
			in available time during a fixed measurement interval.
			-----------------------------
			omtp11tPlusInterfaceNumber:
			1 - CLIENT-1
			2 - LINE-1
			-----------------------------
			Values:
			eg: 1e-3
			-----------------------------"
	::= { omtp11tPlusPerformanceEntry 64 }

        omtp11tPlusOduSevereErrorSecondsErrorRatio OBJECT-TYPE
		SYNTAX  DisplayString
		MAX-ACCESS  read-only
		STATUS  current
		DESCRIPTION
			"For port configured with OTU2 traffic, 
			Gives ODU Severe Error Seconds Error Ratio
			The ratio of SES in available time to total seconds
			in available time during a fixed measurement interval.
			-----------------------------
			omtp11tPlusInterfaceNumber:
			1 - CLIENT-1
			2 - LINE-1
			-----------------------------
			Values:
			eg: 1e-3
			-----------------------------"
	::= { omtp11tPlusPerformanceEntry 65 }

        omtp11tPlusOduFarEndErrorFreeSeconds OBJECT-TYPE
		SYNTAX  DisplayString
		MAX-ACCESS  read-only
		STATUS  current
		DESCRIPTION
			"For port configured with OTU2 traffic, 
			ODU Far end Error Free Seconds, increases when no
			errors or defects are detected
			-----------------------------
			omtp11tPlusInterfaceNumber:
			1 - CLIENT-1
			2 - LINE-1
			-----------------------------
			Values:
			eg: 1234
			-----------------------------"
	::= { omtp11tPlusPerformanceEntry 66 }

        omtp11tPlusOduFarEndErrorSeconds OBJECT-TYPE
		SYNTAX  DisplayString
		MAX-ACCESS  read-only
		STATUS  current
		DESCRIPTION
			"For port configured with OTU2 traffic, 
			ODU Far End Error Seconds increases on detection of
			defects like BDI and BEI at path monitoring level
			-----------------------------
			omtp11tPlusInterfaceNumber:
			1 - CLIENT-1
			2 - LINE-1
			-----------------------------
			Values:
			eg: 1234
			-----------------------------"
	::= { omtp11tPlusPerformanceEntry 67 }

        omtp11tPlusOduFarEndBackgroundBlockErrors OBJECT-TYPE
		SYNTAX  DisplayString
		MAX-ACCESS  read-only
		STATUS  current
		DESCRIPTION
			"For port configured with OTU2 traffic, 
			ODU Far End Background Block Errors increases when
			BEI errors are less than 15% Errored Blocks in
			incoming OTU signal.
			-----------------------------
			omtp11tPlusInterfaceNumber:
			1 - CLIENT-1
			2 - LINE-1
			-----------------------------
			Values:
			eg: 1234
			-----------------------------"
	::= { omtp11tPlusPerformanceEntry 68 }

        omtp11tPlusOduFarEndSevereErrorSeconds OBJECT-TYPE
		SYNTAX  DisplayString
		MAX-ACCESS  read-only
		STATUS  current
		DESCRIPTION
			"For port configured with OTU2 traffic, 
			ODU Far End Severe Error Seconds increases on defects
			like BDI are detected and when BEI errors are more than
			15% Errored Blocks in incoming OTU signal.
			-----------------------------
			omtp11tPlusInterfaceNumber:
			1 - CLIENT-1
			2 - LINE-1
			-----------------------------
			Values:
			eg: 1234
			-----------------------------"
	::= { omtp11tPlusPerformanceEntry 69 }

        omtp11tPlusOduFarEndUnavailableSeconds OBJECT-TYPE
		SYNTAX  DisplayString
		MAX-ACCESS  read-only
		STATUS  current
		DESCRIPTION
			"For port configured with OTU2 traffic, 
			ODU Far End Unavailable Seconds increases, when 10
		        consecutive OTU Far End Error seconds are detected
		       -----------------------------
			omtp11tPlusInterfaceNumber:
			1 - CLIENT-1
			2 - LINE-1
			-----------------------------
			Values:
			eg: 1234
			-----------------------------"
	::= { omtp11tPlusPerformanceEntry 70 }

        omtp11tPlusOduFarEndBackgroundBlockErrorRatio OBJECT-TYPE
		SYNTAX  DisplayString
		MAX-ACCESS  read-only
		STATUS  current
		DESCRIPTION
			"For port configured with OTU2 traffic, 
			Gives ODU Far End Background Block Error Ratio
			The ratio of BBE in available time to total seconds
			in available time during a fixed measurement interval.
			-----------------------------
			omtp11tPlusInterfaceNumber:
			1 - CLIENT-1
			2 - LINE-1
			-----------------------------
			Values:
			eg: 1e-3
			-----------------------------"
	::= { omtp11tPlusPerformanceEntry 72 }

        omtp11tPlusOduFarEndSevereErrorSecondsErrorRatio OBJECT-TYPE
		SYNTAX  DisplayString
		MAX-ACCESS  read-only
		STATUS  current
		DESCRIPTION
			"For port configured with OTU2 traffic, 
			Gives ODU Far End Severe Error Seconds Error Ratio
			The ratio of SES in available time to total seconds
			in available time during a fixed measurement interval.
			-----------------------------
			omtp11tPlusInterfaceNumber:
			1 - CLIENT-1
			2 - LINE-1
			-----------------------------
			Values:
			eg: 1e-3
			-----------------------------"
	::= { omtp11tPlusPerformanceEntry 73 }

	omtp11tPlusPerformanceTableRowStatus OBJECT-TYPE
              SYNTAX      RowStatus
              MAX-ACCESS  read-write
              STATUS      current
              DESCRIPTION
                      "	This is MIB realted property,
			NOT to be considered as a card property"
              ::= { omtp11tPlusPerformanceEntry 193 }


--*****************************************************************************
--				    DIAGNOSTICS
--*****************************************************************************        

	omtp11tPlusDiagnosticsTable OBJECT-TYPE
	      SYNTAX  SEQUENCE OF Omtp11tPlusDiagnosticsEntry
              MAX-ACCESS  not-accessible
              STATUS  current
              DESCRIPTION
                      "Category contains properties that are used for debugging
                      card software"
		::= { omtp11tPlusDiagnostics 1 }	

	omtp11tPlusDiagnosticsEntry   OBJECT-TYPE
              SYNTAX  Omtp11tPlusDiagnosticsEntry 
              MAX-ACCESS  not-accessible
              STATUS  current
              DESCRIPTION 
              	""
		INDEX   { node, rack , subRack , slot , omtp11tPlusInterfaceNumber }
		::= { omtp11tPlusDiagnosticsTable 1 }
	
	Omtp11tPlusDiagnosticsEntry ::= 
		SEQUENCE {
				omtp11tPlusAccessCortinaRegister			INTEGER,
				omtp11tPlusCollectCortinaRegisterDump			INTEGER,
				omtp11tPlusCollectCortinaModulebGpllRxLockStatus	DisplayString,
				omtp11tPlusCollectCortinaModulebGpllTxLockStatus	DisplayString,
				omtp11tPlusCollectCortinaModulebTxSerdesLockStatus	DisplayString,
				omtp11tPlusCollectCortinaModulebTxSerdesVcoTunedValue	DisplayString,
				omtp11tPlusCollectCortinaModulebXfiCupllLockStatus	DisplayString,
				omtp11tPlusCollectCortinaModulebAllClockLockStatus	OCTET STRING,
				omtp11tPlusDiagnosticTableRowStatus			RowStatus
			}
			
	omtp11tPlusAccessCortinaRegister OBJECT-TYPE
		SYNTAX  INTEGER
		MAX-ACCESS  read-write
		STATUS  current
		DESCRIPTION
			"Sets/gets the value of any cortina register
			-----------------------------
			omtp11tPlusInterfaceNumber: 0
			-----------------------------
			Values:
			eg:
			example of cortina register - 76071076
			value - 1
			-----------------------------"
	::= { omtp11tPlusDiagnosticsEntry 1 }	
	
	omtp11tPlusCollectCortinaRegisterDump OBJECT-TYPE
		SYNTAX  INTEGER
		MAX-ACCESS  read-only
		STATUS  current
		DESCRIPTION
			"create register dump of all cortina register
			-----------------------------
			omtp11tPlusInterfaceNumber: 0
			-----------------------------
                     	This query will create registe dump in card's 
			root directory
			-----------------------------"
	::= { omtp11tPlusDiagnosticsEntry 2 }	

	omtp11tPlusCollectCortinaModulebGpllRxLockStatus OBJECT-TYPE
		SYNTAX  DisplayString
		MAX-ACCESS  read-only
		STATUS  current
		DESCRIPTION
			"reads GPLL Rx clock lock status for all slices
			 of module B
			 Expected value : should be 0x00049 to indicate 
			 Value is locked
			 The following register will be read:
			 0x00c59, 0x00c99, 0x00cd9, 0x00d19
			 The register that will be read is GPLLX1_SDS_COMMON_TXLOCKD0_INTSTATUS
			-----------------------------
			omtp11tPlusInterfaceNumber: 0
			-----------------------------"
	::= { omtp11tPlusDiagnosticsEntry 3 }	
	
	omtp11tPlusCollectCortinaModulebGpllTxLockStatus OBJECT-TYPE
		SYNTAX  DisplayString
		MAX-ACCESS  read-only
		STATUS  current
		DESCRIPTION
			"reads GPLL Tx clock lock status for all slices
			 of module B
			 Expected value : should be 0x00049 to indicate 
			 Value is locked
			 The following register will be read:
			 0x00d59, 0x00d99, 0x00dd9, 0x00e19
			 The register that will be read is GPLLX1_SDS_COMMON_TXLOCKD0_INTSTATUS
			-----------------------------
			omtp11tPlusInterfaceNumber: 0
			-----------------------------"
	::= { omtp11tPlusDiagnosticsEntry 4 }

	omtp11tPlusCollectCortinaModulebTxSerdesLockStatus OBJECT-TYPE
		SYNTAX  DisplayString
		MAX-ACCESS  read-only
		STATUS  current
		DESCRIPTION
			"reads Tx serdes clock lock status for all slices
			 of module B
			 Expected value : should be 0x00049 to indicate 
			 Value is locked
			 The following register will be read:
			 0x0303d, 0x0343d, 0x0383d, 0x03c3d
			 The register that will be read is 
			 XFI32X1_SDS_XFI32X1_SDS_COMMON_TXLOCKD0_INTSTATUS
			-----------------------------
			omtp11tPlusInterfaceNumber: 0
			-----------------------------"
	::= { omtp11tPlusDiagnosticsEntry 5 }	
	
	omtp11tPlusCollectCortinaModulebTxSerdesVcoTunedValue OBJECT-TYPE
		SYNTAX  DisplayString
		MAX-ACCESS  read-only
		STATUS  current
		DESCRIPTION
			"reads Tx serdes VCO tuning value for all slices
			 of module B
			 Expected value : Value when correctly tuned should not 
			 be near extremes of 0x3F or 0x00
			 The following register will be read:
			 0x03031, 0x03431, 0x03831, 0x03c31
			 The register that will be read is XFI32X1_SDS_XFI32X1_SDS_COMMON_TXVCO0_STATUS
			-----------------------------
			omtp11tPlusInterfaceNumber: 0
			-----------------------------"
	::= { omtp11tPlusDiagnosticsEntry 6 }	

	omtp11tPlusCollectCortinaModulebXfiCupllLockStatus OBJECT-TYPE
		SYNTAX  DisplayString
		MAX-ACCESS  read-only
		STATUS  current
		DESCRIPTION
			"reads XFI CUPLL Lock status for all slices
			 of module B
			 Expected value : should be 0x00049 to indicate Value is locked 
			 The following register will be read:
			 0x1b438, 0x1b478, 0x1b4b8, 0x1b4f8
			 The register that will be read is XFI_CUPLL_LOCKDET_INTSTATUS
			-----------------------------
			omtp11tPlusInterfaceNumber: 0
			-----------------------------"
	::= { omtp11tPlusDiagnosticsEntry 7 }	

	omtp11tPlusCollectCortinaModulebAllClockLockStatus OBJECT-TYPE
		SYNTAX  OCTET STRING
		MAX-ACCESS  read-only
		STATUS  current
		DESCRIPTION
			"reads Lock status of following clocks:
			 GPLL Rx/Tx, Tx serdes, Tx Serdes VCO tuned value and XFI CUPLLfor all slices
			 of module B.
			 Expected value : should be 0x00049 to indicate Value is locked 
			 The following register will be read:
			 0x1b438, 0x1b478, 0x1b4b8, 0x1b4f8
			 The register that will be read is XFI_CUPLL_LOCKDET_INTSTATUS
			-----------------------------
			omtp11tPlusInterfaceNumber: 0
			-----------------------------"
	::= { omtp11tPlusDiagnosticsEntry 8 }	

	omtp11tPlusDiagnosticTableRowStatus OBJECT-TYPE
              SYNTAX      RowStatus
              MAX-ACCESS  read-write
              STATUS      current
              DESCRIPTION
			"*****************************
			This is MIB realted property,
			NOT to be considered as a card property
			*****************************"
	::= { omtp11tPlusDiagnosticsEntry 9 }
        
--*****************************************************************************
--				    ALARM Notification Table
--*****************************************************************************

        omtp11tPlusXfpInputPowerFailureAlarmTrap NOTIFICATION-TYPE
         OBJECTS { omtp11tPlusXfpInputPowerFailureAlarm }
                STATUS  current
                DESCRIPTION
                        "OMTP11T-PLUS XFP input power failure alarm trap"
        ::= { omtp11tPlusAlarmNotification 1 }


        omtp11tPlusXfpOutputPowerFailureAlarmTrap NOTIFICATION-TYPE
         OBJECTS { omtp11tPlusXfpOutputPowerFailureAlarm }
               STATUS  current
               DESCRIPTION
                        "OMTP11T-PLUS XFP output power failure alarm trap"
        ::= { omtp11tPlusAlarmNotification 2 }


        omtp11tPlusXfpHighTemperatureAlarmTrap NOTIFICATION-TYPE
         OBJECTS { omtp11tPlusXfpHighTemperatureAlarm }
               STATUS  current
               DESCRIPTION
                        "OMTP11T-PLUS XFP high temperature alarm trap"
        ::= { omtp11tPlusAlarmNotification 3 }

        omtp11tPlusXfpLowTemperatureAlarmTrap NOTIFICATION-TYPE
         OBJECTS { omtp11tPlusXfpLowTemperatureAlarm }
               STATUS  current
               DESCRIPTION
                        "OMTP11T-PLUS XFP low temperature alarm trap"
        ::= { omtp11tPlusAlarmNotification 4 }

        omtp11tPlusXfpHighTemperatureWarningTrap NOTIFICATION-TYPE
         OBJECTS { omtp11tPlusXfpHighTemperatureWarning }
               STATUS  current
               DESCRIPTION
                        "OMTP11T-PLUS XFP high temperature warning trap"
        ::= { omtp11tPlusAlarmNotification 5 }

        omtp11tPlusXfpLowTemperatureWarningTrap NOTIFICATION-TYPE
         OBJECTS { omtp11tPlusXfpLowTemperatureWarning }
               STATUS  current
               DESCRIPTION
                        "OMTP11T-PLUS XFP low temperature warning trap"
        ::= { omtp11tPlusAlarmNotification 6 }

        omtp11tPlusXfpHighBiasCurrentAlarmTrap NOTIFICATION-TYPE
         OBJECTS { omtp11tPlusXfpHighBiasCurrentAlarm }
               STATUS  current
               DESCRIPTION
                        "OMTP11T-PLUS XFP high bias current alarm trap"
        ::= { omtp11tPlusAlarmNotification 7 }

        omtp11tPlusXfpLowBiasCurrentAlarmTrap NOTIFICATION-TYPE
         OBJECTS { omtp11tPlusXfpLowBiasCurrentAlarm }
               STATUS  current
               DESCRIPTION
                        "OMTP11T-PLUS XFP low bias current alarm trap"
        ::= { omtp11tPlusAlarmNotification 8 }

        omtp11tPlusXfpHighBiasCurrentWarningTrap NOTIFICATION-TYPE
         OBJECTS { omtp11tPlusXfpHighBiasCurrentWarning }
               STATUS  current
               DESCRIPTION
                        "OMTP11T-PLUS XFP high bias current warning trap"
        ::= { omtp11tPlusAlarmNotification 9 }

        omtp11tPlusXfpLowBiasCurrentWarningTrap NOTIFICATION-TYPE
         OBJECTS { omtp11tPlusXfpLowBiasCurrentWarning }
               STATUS  current
               DESCRIPTION
                        "OMTP11T-PLUS XFP low bias current warning trap"
        ::= { omtp11tPlusAlarmNotification 10 }

        omtp11tPlusXfpInputHighPowerAlarmTrap NOTIFICATION-TYPE
         OBJECTS { omtp11tPlusXfpInputHighPowerAlarm }
               STATUS  current
               DESCRIPTION
                        "OMTP11T-PLUS XFP input high power alarm trap"
        ::= { omtp11tPlusAlarmNotification 11 }

        omtp11tPlusXfpInputLowPowerAlarmTrap NOTIFICATION-TYPE
         OBJECTS { omtp11tPlusXfpInputLowPowerAlarm }
               STATUS  current
               DESCRIPTION
                        "OMTP11T-PLUS XFP input low power alarm trap"
        ::= { omtp11tPlusAlarmNotification 12 }

        omtp11tPlusXfpInputHighPowerWarningTrap NOTIFICATION-TYPE
         OBJECTS { omtp11tPlusXfpInputHighPowerWarning }
               STATUS  current
               DESCRIPTION
                        "OMTP11T-PLUS XFP input high power warning trap"
        ::= { omtp11tPlusAlarmNotification 13 }

        omtp11tPlusXfpInputLowPowerWarningTrap NOTIFICATION-TYPE
         OBJECTS { omtp11tPlusXfpInputLowPowerWarning }
               STATUS  current
               DESCRIPTION
                        "OMTP11T-PLUS XFP input low power warning trap"
        ::= { omtp11tPlusAlarmNotification 14 }

        omtp11tPlusXfpOutputHighPowerAlarmTrap NOTIFICATION-TYPE
         OBJECTS { omtp11tPlusXfpOutputHighPowerAlarm }
               STATUS  current
               DESCRIPTION
                        "OMTP11T-PLUS XFP output high power alarm trap"
        ::= { omtp11tPlusAlarmNotification 15 }

        omtp11tPlusXfpOutputLowPowerAlarmTrap NOTIFICATION-TYPE
         OBJECTS { omtp11tPlusXfpOutputLowPowerAlarm }
               STATUS  current
               DESCRIPTION
                        "OMTP11T-PLUS XFP output low power alarm trap"
        ::= { omtp11tPlusAlarmNotification 16 }

        omtp11tPlusXfpOutputHighPowerWarningTrap NOTIFICATION-TYPE
         OBJECTS { omtp11tPlusXfpOutputHighPowerWarning }
               STATUS  current
               DESCRIPTION
                        "OMTP11T-PLUS XFP output high power warning trap"
        ::= { omtp11tPlusAlarmNotification 17 }

        omtp11tPlusXfpOutputLowPowerWarningTrap NOTIFICATION-TYPE
         OBJECTS { omtp11tPlusXfpOutputLowPowerWarning }
               STATUS  current
               DESCRIPTION
                        "OMTP11T-PLUS XFP output low power warning trap"
        ::= { omtp11tPlusAlarmNotification 18 }

        omtp11tPlusXfpHighSupplyVoltageAlarmTrap NOTIFICATION-TYPE
         OBJECTS { omtp11tPlusXfpHighSupplyVoltageAlarm }
               STATUS  current
               DESCRIPTION
                        "OMTP11T-PLUS XFP high supply voltage alarm trap"
        ::= { omtp11tPlusAlarmNotification 19 }

        omtp11tPlusXfpLowSupplyVoltageAlarmTrap NOTIFICATION-TYPE
         OBJECTS { omtp11tPlusXfpLowSupplyVoltageAlarm }
               STATUS  current
               DESCRIPTION
                        "OMTP11T-PLUS XFP low supply voltage alarm trap"
        ::= { omtp11tPlusAlarmNotification 20 }

        omtp11tPlusXfpHighSupplyVoltageWarningTrap NOTIFICATION-TYPE
         OBJECTS { omtp11tPlusXfpHighSupplyVoltageWarning }
               STATUS  current
               DESCRIPTION
                        "OMTP11T-PLUS XFP high supply voltage warning trap"
        ::= { omtp11tPlusAlarmNotification 21 }

        omtp11tPlusXfpLowSupplyVoltageWarningTrap NOTIFICATION-TYPE
         OBJECTS { omtp11tPlusXfpLowSupplyVoltageWarning }
               STATUS  current
               DESCRIPTION
                        "OMTP11T-PLUS XFP low supply voltage warning trap"
        ::= { omtp11tPlusAlarmNotification 22 }

        omtp11tPlusXfpPresenceAbsenceNotificationTrap NOTIFICATION-TYPE
         OBJECTS { omtp11tPlusXfpPresenceAbsenceNotification }
               STATUS  current
               DESCRIPTION
                        "OMTP11T-PLUS XFP presence absence notification"
        ::= { omtp11tPlusAlarmNotification 23 }

        omtp11tPlusOtuLossOfSignalAlarmTrap NOTIFICATION-TYPE
         OBJECTS { omtp11tPlusOtuLossOfSignalAlarm }
               STATUS  current
               DESCRIPTION
                        "OMTP11T-PLUS OTU loss of signal alarm trap"
        ::= { omtp11tPlusAlarmNotification 31 }

        omtp11tPlusOtuLossOfFrameAlarmTrap NOTIFICATION-TYPE
         OBJECTS { omtp11tPlusOtuLossOfFrameAlarm }
               STATUS  current
               DESCRIPTION
                        "OMTP11T-PLUS OTU loss of frame alarm trap"
        ::= { omtp11tPlusAlarmNotification 32 }

        omtp11tPlusOtuOutOfFrameAlarmTrap NOTIFICATION-TYPE
         OBJECTS { omtp11tPlusOtuOutOfFrameAlarm }
               STATUS  current
               DESCRIPTION
                        "OMTP11T-PLUS OTU out of frame alarm trap"
        ::= { omtp11tPlusAlarmNotification 33 }

        omtp11tPlusOtuLossOfMultiFrameAlarmTrap NOTIFICATION-TYPE
         OBJECTS { omtp11tPlusOtuLossOfMultiFrameAlarm }
               STATUS  current
               DESCRIPTION
                        "OMTP11T-PLUS OTU loss of multi frame alarm trap"
        ::= { omtp11tPlusAlarmNotification 34 }

        omtp11tPlusOtuOutOfMultiFrameAlarmTrap NOTIFICATION-TYPE
         OBJECTS { omtp11tPlusOtuOutOfMultiFrameAlarm }
               STATUS  current
               DESCRIPTION
                        "OMTP11T-PLUS OTU out of multi frame alarm trap"
        ::= { omtp11tPlusAlarmNotification 35 }

        omtp11tPlusOtuSignalFailAlarmTrap NOTIFICATION-TYPE
         OBJECTS { omtp11tPlusOtuSignalFailAlarm }
               STATUS  current
               DESCRIPTION
                        "OMTP11T-PLUS OTU signal fail alarm trap"
        ::= { omtp11tPlusAlarmNotification 36 }

        omtp11tPlusOtuSignalDegradeAlarmTrap NOTIFICATION-TYPE
         OBJECTS { omtp11tPlusOtuSignalDegradeAlarm }
               STATUS  current
               DESCRIPTION
                        "OMTP11T-PLUS OTU signal degrade alarm trap"
        ::= { omtp11tPlusAlarmNotification 37 }

        omtp11tPlusOtuAlarmIndicationSignalAlarmTrap NOTIFICATION-TYPE
         OBJECTS { omtp11tPlusOtuAlarmIndicationSignalAlarm }
               STATUS  current
               DESCRIPTION
                        "OMTP11T-PLUS OTU alarm indication signal alarm trap"
        ::= { omtp11tPlusAlarmNotification 38 }

        omtp11tPlusOtuIncomingAlignmentErrorAlarmTrap NOTIFICATION-TYPE
         OBJECTS { omtp11tPlusOtuIncomingAlignmentErrorAlarm }
               STATUS  current
               DESCRIPTION
                        "OMTP11T-PLUS OTU incoming alignment error alarm trap"
        ::= { omtp11tPlusAlarmNotification 39 }

        omtp11tPlusOtuTraceIdentifierMismatchAlarmTrap NOTIFICATION-TYPE
         OBJECTS { omtp11tPlusOtuTraceIdentifierMismatchAlarm }
               STATUS  current
               DESCRIPTION
                        "OMTP11T-PLUS OTU trace identifier mismatch alarm trap"
        ::= { omtp11tPlusAlarmNotification 40 }

        omtp11tPlusOtuBackwardIncomingAlignmentErrorAlarmTrap NOTIFICATION-TYPE
         OBJECTS { omtp11tPlusOtuBackwardIncomingAlignmentErrorAlarm }
               STATUS  current
               DESCRIPTION
                        "OMTP11T-PLUS OTU backward incoming alignment error alarm trap"
        ::= { omtp11tPlusAlarmNotification 41 }

        omtp11tPlusOtuBackwardDefectIndicationAlarmTrap NOTIFICATION-TYPE
         OBJECTS { omtp11tPlusOtuBackwardDefectIndicationAlarm }
               STATUS  current
               DESCRIPTION
                        "OMTP11T-PLUS OTU backward defect indication alarm trap"
        ::= { omtp11tPlusAlarmNotification 42 }

        omtp11tPlusOduSignalFailAlarmTrap NOTIFICATION-TYPE
         OBJECTS { omtp11tPlusOduSignalFailAlarm }
               STATUS  current
               DESCRIPTION
                        "OMTP11T-PLUS ODU signal fail alarm trap"
        ::= { omtp11tPlusAlarmNotification 51 }

        omtp11tPlusOduSignalDegradeAlarmTrap NOTIFICATION-TYPE
         OBJECTS { omtp11tPlusOduSignalDegradeAlarm }
               STATUS  current
               DESCRIPTION
                        "OMTP11T-PLUS ODU signal degrade alarm trap"
        ::= { omtp11tPlusAlarmNotification 52 }

        omtp11tPlusOduAlarmIndicationSignalAlarmTrap NOTIFICATION-TYPE
         OBJECTS { omtp11tPlusOduAlarmIndicationSignalAlarm }
               STATUS  current
               DESCRIPTION
                        "OMTP11T-PLUS ODU alarm indication signal alarm trap"
        ::= { omtp11tPlusAlarmNotification 53 }

        omtp11tPlusOduTcm1IncomingAlignmentErrorAlarmTrap NOTIFICATION-TYPE
         OBJECTS { omtp11tPlusOduTcm1IncomingAlignmentErrorAlarm }
               STATUS  current
               DESCRIPTION
                        "OMTP11T-PLUS ODU TCM1 incoming alignment error alarm trap"
        ::= { omtp11tPlusAlarmNotification 54 }

        omtp11tPlusOduTcm2IncomingAlignmentErrorAlarmTrap NOTIFICATION-TYPE
         OBJECTS { omtp11tPlusOduTcm2IncomingAlignmentErrorAlarm }
               STATUS  current
               DESCRIPTION
                        "OMTP11T-PLUS ODU TCM2 incoming alignment error alarm trap"
        ::= { omtp11tPlusAlarmNotification 55 }

        omtp11tPlusOduTcm3IncomingAlignmentErrorAlarmTrap NOTIFICATION-TYPE
         OBJECTS { omtp11tPlusOduTcm3IncomingAlignmentErrorAlarm }
               STATUS  current
               DESCRIPTION
                        "OMTP11T-PLUS ODU TCM3 incoming alignment error alarm trap"
        ::= { omtp11tPlusAlarmNotification 56 }

        omtp11tPlusOduTcm4IncomingAlignmentErrorAlarmTrap NOTIFICATION-TYPE
         OBJECTS { omtp11tPlusOduTcm4IncomingAlignmentErrorAlarm }
               STATUS  current
               DESCRIPTION
                        "OMTP11T-PLUS ODU TCM4 incoming alignment error alarm trap"
        ::= { omtp11tPlusAlarmNotification 57 }

        omtp11tPlusOduTcm5IncomingAlignmentErrorAlarmTrap NOTIFICATION-TYPE
         OBJECTS { omtp11tPlusOduTcm5IncomingAlignmentErrorAlarm }
               STATUS  current
               DESCRIPTION
                        "OMTP11T-PLUS ODU TCM5 incoming alignment error alarm trap"
        ::= { omtp11tPlusAlarmNotification 58 }

        omtp11tPlusOduTcm6IncomingAlignmentErrorAlarmTrap NOTIFICATION-TYPE
         OBJECTS { omtp11tPlusOduTcm6IncomingAlignmentErrorAlarm }
               STATUS  current
               DESCRIPTION
                        "OMTP11T-PLUS ODU TCM6 incoming alignment error alarm trap"
        ::= { omtp11tPlusAlarmNotification 59 }

        omtp11tPlusOduTraceIdentifierMismatchAlarmTrap NOTIFICATION-TYPE
         OBJECTS { omtp11tPlusOduTraceIdentifierMismatchAlarm }
               STATUS  current
               DESCRIPTION
                        "OMTP11T-PLUS ODU trace identifier mismatch alarm trap"
        ::= { omtp11tPlusAlarmNotification 60 }

        omtp11tPlusOduLockedDefectAlarmTrap NOTIFICATION-TYPE
         OBJECTS { omtp11tPlusOduLockedDefectAlarm }
               STATUS  current
               DESCRIPTION
                        "OMTP11T-PLUS ODU locked defect alarm trap"
        ::= { omtp11tPlusAlarmNotification 61 }

        omtp11tPlusOduOpenConnectionIndicationAlarmTrap NOTIFICATION-TYPE
         OBJECTS { omtp11tPlusOduOpenConnectionIndicationAlarm }
               STATUS  current
               DESCRIPTION
                        "OMTP11T-PLUS ODU open connection indication alarm trap"
        ::= { omtp11tPlusAlarmNotification 62 }

        omtp11tPlusOduBackwardDefectIndicationAlarmTrap NOTIFICATION-TYPE
         OBJECTS { omtp11tPlusOduBackwardDefectIndicationAlarm }
               STATUS  current
               DESCRIPTION
                        "OMTP11T-PLUS ODU backward defect indication alarm trap"
        ::= { omtp11tPlusAlarmNotification 63 }

        omtp11tPlusOduTcm1BackwardIncomingAlignmentErrorAlarmTrap NOTIFICATION-TYPE
         OBJECTS { omtp11tPlusOduTcm1BackwardIncomingAlignmentErrorAlarm }
               STATUS  current
               DESCRIPTION
                        "OMTP11T-PLUS ODU TCM1 backward incoming alignment error alarm trap"
        ::= { omtp11tPlusAlarmNotification 64 }

        omtp11tPlusOduTcm2BackwardIncomingAlignmentErrorAlarmTrap NOTIFICATION-TYPE
         OBJECTS { omtp11tPlusOduTcm2BackwardIncomingAlignmentErrorAlarm }
               STATUS  current
               DESCRIPTION
                        "OMTP11T-PLUS ODU TCM2 backward incoming alignment error alarm trap"
        ::= { omtp11tPlusAlarmNotification 65 }

        omtp11tPlusOduTcm3BackwardIncomingAlignmentErrorAlarmTrap NOTIFICATION-TYPE
         OBJECTS { omtp11tPlusOduTcm3BackwardIncomingAlignmentErrorAlarm }
               STATUS  current
               DESCRIPTION
                        "OMTP11T-PLUS ODU TCM3 backward incoming alignment error alarm trap"
        ::= { omtp11tPlusAlarmNotification 66 }

        omtp11tPlusOduTcm4BackwardIncomingAlignmentErrorAlarmTrap NOTIFICATION-TYPE
         OBJECTS { omtp11tPlusOduTcm4BackwardIncomingAlignmentErrorAlarm }
               STATUS  current
               DESCRIPTION
                        "OMTP11T-PLUS ODU TCM4 backward incoming alignment error alarm trap"
        ::= { omtp11tPlusAlarmNotification 67 }

        omtp11tPlusOduTcm5BackwardIncomingAlignmentErrorAlarmTrap NOTIFICATION-TYPE
         OBJECTS { omtp11tPlusOduTcm5BackwardIncomingAlignmentErrorAlarm }
               STATUS  current
               DESCRIPTION
                        "OMTP11T-PLUS ODU TCM5 backward incoming alignment error alarm trap"
        ::= { omtp11tPlusAlarmNotification 68 }

        omtp11tPlusOduTcm6BackwardIncomingAlignmentErrorAlarmTrap NOTIFICATION-TYPE
         OBJECTS { omtp11tPlusOduTcm6BackwardIncomingAlignmentErrorAlarm }
               STATUS  current
               DESCRIPTION
                        "OMTP11T-PLUS ODU TCM6 backward incoming alignment error alarm trap"
        ::= { omtp11tPlusAlarmNotification 69 }

        omtp11tPlusOpuPayloadMismatchAlarmTrap NOTIFICATION-TYPE
         OBJECTS { omtp11tPlusOpuPayloadMismatchAlarm }
               STATUS  current
               DESCRIPTION
                        "OMTP11T-PLUS OPU payload mismatch alarm trap"
        ::= { omtp11tPlusAlarmNotification 70 }
        omtp11tPlusOchLossOfPayloadAlarmTrap NOTIFICATION-TYPE
         OBJECTS { omtp11tPlusOchLossOfPayloadAlarm }
               STATUS  current
               DESCRIPTION
                        "OMTP11T-PLUS Och loss of payload alarm trap"
        ::= { omtp11tPlusAlarmNotification 71 }

             
--*****************************************************************************
--				    ALARM NOTIFICATION
--*****************************************************************************

	snmpCurrentNotificationsGroup NOTIFICATION-GROUP
		NOTIFICATIONS { 
					omtp11tPlusXfpInputPowerFailureAlarmTrap,
					omtp11tPlusXfpOutputPowerFailureAlarmTrap,
					omtp11tPlusXfpHighTemperatureAlarmTrap,
					omtp11tPlusXfpLowTemperatureAlarmTrap,
					omtp11tPlusXfpHighTemperatureWarningTrap,
					omtp11tPlusXfpLowTemperatureWarningTrap,
					omtp11tPlusXfpHighBiasCurrentAlarmTrap,
					omtp11tPlusXfpLowBiasCurrentAlarmTrap,
					omtp11tPlusXfpHighBiasCurrentWarningTrap,
					omtp11tPlusXfpLowBiasCurrentWarningTrap,
					omtp11tPlusXfpInputHighPowerAlarmTrap,
					omtp11tPlusXfpInputLowPowerAlarmTrap,
					omtp11tPlusXfpInputHighPowerWarningTrap,
					omtp11tPlusXfpInputLowPowerWarningTrap,
					omtp11tPlusXfpOutputHighPowerAlarmTrap,
					omtp11tPlusXfpOutputLowPowerAlarmTrap,
					omtp11tPlusXfpOutputHighPowerWarningTrap,
					omtp11tPlusXfpOutputLowPowerWarningTrap,
					omtp11tPlusXfpHighSupplyVoltageAlarmTrap,
					omtp11tPlusXfpLowSupplyVoltageAlarmTrap,
					omtp11tPlusXfpHighSupplyVoltageWarningTrap,
					omtp11tPlusXfpLowSupplyVoltageWarningTrap,
					omtp11tPlusXfpPresenceAbsenceNotificationTrap,
					omtp11tPlusOtuLossOfSignalAlarmTrap,
					omtp11tPlusOtuLossOfFrameAlarmTrap,
					omtp11tPlusOtuOutOfFrameAlarmTrap,
					omtp11tPlusOtuLossOfMultiFrameAlarmTrap,
					omtp11tPlusOtuOutOfMultiFrameAlarmTrap,
					omtp11tPlusOtuSignalFailAlarmTrap,
					omtp11tPlusOtuSignalDegradeAlarmTrap,
					omtp11tPlusOtuAlarmIndicationSignalAlarmTrap,
					omtp11tPlusOtuIncomingAlignmentErrorAlarmTrap,
					omtp11tPlusOtuTraceIdentifierMismatchAlarmTrap,
					omtp11tPlusOtuBackwardIncomingAlignmentErrorAlarmTrap,
					omtp11tPlusOtuBackwardDefectIndicationAlarmTrap,
					omtp11tPlusOduSignalFailAlarmTrap,
					omtp11tPlusOduSignalDegradeAlarmTrap,
					omtp11tPlusOduAlarmIndicationSignalAlarmTrap,
					omtp11tPlusOduTcm1IncomingAlignmentErrorAlarmTrap,
					omtp11tPlusOduTcm2IncomingAlignmentErrorAlarmTrap,
					omtp11tPlusOduTcm3IncomingAlignmentErrorAlarmTrap,
					omtp11tPlusOduTcm4IncomingAlignmentErrorAlarmTrap,
					omtp11tPlusOduTcm5IncomingAlignmentErrorAlarmTrap,
					omtp11tPlusOduTcm6IncomingAlignmentErrorAlarmTrap,
					omtp11tPlusOduTraceIdentifierMismatchAlarmTrap,
					omtp11tPlusOduLockedDefectAlarmTrap,
					omtp11tPlusOduOpenConnectionIndicationAlarmTrap,
					omtp11tPlusOduBackwardDefectIndicationAlarmTrap,
					omtp11tPlusOduTcm1BackwardIncomingAlignmentErrorAlarmTrap,
					omtp11tPlusOduTcm2BackwardIncomingAlignmentErrorAlarmTrap,
					omtp11tPlusOduTcm3BackwardIncomingAlignmentErrorAlarmTrap,
					omtp11tPlusOduTcm4BackwardIncomingAlignmentErrorAlarmTrap,
					omtp11tPlusOduTcm5BackwardIncomingAlignmentErrorAlarmTrap,
					omtp11tPlusOduTcm6BackwardIncomingAlignmentErrorAlarmTrap,
					omtp11tPlusOpuPayloadMismatchAlarmTrap,
					omtp11tPlusOchLossOfPayloadAlarmTrap
		}
  	  STATUS current
  	  DESCRIPTION
		"The UTL OMTP11T-PLUS current notifications group"
  	  ::= { omtp11tPlus 6 }

	snmpcurrentGroup OBJECT-GROUP
		OBJECTS {
				omtp11tPlusInterfaceNumber, 
				omtp11tPlusEepromCardId,
				omtp11tPlusEepromCardName,
				omtp11tPlusEepromPartCode,
				omtp11tPlusEepromCardSerialNumber,
				omtp11tPlusEepromHardwareExternalReleaseVersion,
				omtp11tPlusSoftwareExternalReleaseVersion,
				omtp11tPlusEepromHardwareInternalReleaseVersion,
				omtp11tPlusSoftwareInternalReleaseVersion,
				omtp11tPlusEepromCardUidNumber,
				omtp11tPlusEepromCardEui48Number,
				omtp11tPlusEepromCardEui64Number,
				omtp11tPlusCardRootFileSystemVersion,
				omtp11tPlusCardInstallationDate,
				omtp11tPlusCardCommissionDate,
				omtp11tPlusCardRunningTime,
				omtp11tPlusCardRestartCount,
				omtp11tPlusXfpReadyForOperation,
				omtp11tPlusXfpI2cCommunicationStatus,
				omtp11tPlusXfpEepromPage,
				omtp11tPlusCheckCodeOfXfpEepromPage,
				omtp11tPlusExtendedCheckCodeOfXfpEepromPage,
				omtp11tPlusXfpVendorName,
				omtp11tPlusXfpVendorIeeeId,
				omtp11tPlusXfpPartNumber,
				omtp11tPlusXfpSerialNumber,
				omtp11tPlusXfpRevisionNumber,
				omtp11tPlusXfpManufacturingDate,
				omtp11tPlusFixedXfpLaserWavelength,
				omtp11tPlusXfpLaserWavelengthTolerance,
				omtp11tPlusXfpWavelengthTunabilitySupported,
				omtp11tPlusTunableXfpLaserWavelengthError,
				omtp11tPlusTunableXfpLaserFrequencyError,
				omtp11tPlusTunableXfpLaserFirstFrequency,
				omtp11tPlusTunableXfpLaserLastFrequency,
				omtp11tPlusTunableXfpWavelengthGridSpacing,
				omtp11tPlusXfpConnectorType,
				omtp11tPlusXfpLinkLength,
				omtp11tPlusXfpCdrRateSupported,
				omtp11tPlusXfpSignalEncodingTypeSupported,
				omtp11tPlusXfpTransceiverCodesSupported,
				omtp11tPlusXfpMaximumBitrateSupported,
				omtp11tPlusXfpMinimumBitrateSupported,
				omtp11tPlusXfpMaximumCaseTemperatureSupported,
				omtp11tPlusXfpMaximumPowerDissipationSupported,
				omtp11tPlusXfpMaximumPowerDissipationSupportedAtPowerDownMode,
				omtp11tPlusXfpMaximumCurrentLimitSupportedAtPlus5vSupply,
				omtp11tPlusXfpMaximumCurrentLimitSupportedAtPlus3Point3vSupply,
				omtp11tPlusXfpMaximumCurrentLimitSupportedAtPlus1Point8vSupply,
				omtp11tPlusXfpMaximumCurrentLimitSupportedAtMinus5Point2vSupply,
				omtp11tPlusXfpLineLoopbackSupported,
				omtp11tPlusXfpXfiLoopbackSupported,
				omtp11tPlusXfpOptionalVpsSupported,
				omtp11tPlusXfpLaserDisableThroughI2cSupported,
				omtp11tPlusXfpPowerDownThroughI2cSupported,
				omtp11tPlusXfpVpsLvRegulatorModeSupported,
				omtp11tPlusXfpVpsBypassedRegulatorModeSupported,
				omtp11tPlusXfpActiveFecControlSupported,
				omtp11tPlusXfpOptionalCmuModeSupported,
				omtp11tPlusXfpFecBerSupported,
				omtp11tPlusXfpReceivePowerMeasurementIsInOmaOrAverage,
				omtp11tPlusXfpActiveWavelengthControlSupported,
				omtp11tPlusXfpTransmitterIsCooledOrUncooled,
				omtp11tPlusXfpReceiverTypeIsPinOrApd,
				omtp11tPlusCardGeneralDetailsTableRowStatus,
				omtp11tPlusCardSoftwareUpgrade,
				omtp11tPlusCardSignalMonitorState,
				omtp11tPlusCardOpticalMonitorState,
				omtp11tPlusCardSoftReset,
				omtp11tPlusCardFactoryReset,
				omtp11tPlusCardAccessStatus,
				omtp11tPlusSyncSystemTimeWithNtpServer,
				omtp11tPlusSyncRtcWithNtpServer,
				omtp11tPlusSyncRtcWithSystemTime,
				omtp11tPlusUpdateGivenTimeIntoSystem,
				omtp11tPlusUpdateGivenTimeIntoRtc,
				omtp11tPlusSystemTimeAndRtcTime,
				omtp11tPlusTrafficConfiguration,
				omtp11tPlusLoopbackState,
				omtp11tPlusPortSignalMonitorState,
				omtp11tPlusPortOpticalMonitorState,
				omtp11tPlusClearSignalPerformance,
				omtp11tPlusAlsState,
				omtp11tPlusAlsPulseRepetitionTime,
				omtp11tPlusOtuFecConfiguration,
				omtp11tPlusOtuSignalFailThreshold,
				omtp11tPlusOtuSignalDegradeThreshold,
				omtp11tPlusOtuAlarmIndicationSignalAlarmInsertion,
				omtp11tPlusOtuSapiTransmitTraceMessage,
				omtp11tPlusOtuDapiTransmitTraceMessage,
				omtp11tPlusOtuOperatorSpecificTransmitTraceMessage,
				omtp11tPlusOtuSapiExpectedTraceMessage,
				omtp11tPlusOtuDapiExpectedTraceMessage,
				omtp11tPlusOtuOperatorSpecificExpectedTraceMessage,
				omtp11tPlusOtuSapiReceivedTraceMessage,
				omtp11tPlusOtuDapiReceivedTraceMessage,
				omtp11tPlusOtuOperatorSpecificReceivedTraceMessage,
				omtp11tPlusOduSignalFailThreshold,
				omtp11tPlusOduSignalDegradeThreshold,
				omtp11tPlusOduAlarmIndicationSignalAlarmInsertion,
				omtp11tPlusOduLockedDefectAlarmInsertion,
				omtp11tPlusOduOpenConnectionIndicationAlarmInsertion,
				omtp11tPlusOduSapiTransmitTraceMessage,
				omtp11tPlusOduDapiTransmitTraceMessage,
				omtp11tPlusOduOperatorSpecificTransmitTraceMessage,
				omtp11tPlusOduSapiExpectedTraceMessage,
				omtp11tPlusOduDapiExpectedTraceMessage,
				omtp11tPlusOduOperatorSpecificExpectedTraceMessage,
				omtp11tPlusOduSapiReceivedTraceMessage,
				omtp11tPlusOduDapiReceivedTraceMessage,
				omtp11tPlusOduOperatorSpecificReceivedTraceMessage,
				omtp11tPlusOpuTransmitPayloadType,
				omtp11tPlusOpuReceivedPayloadType,
				omtp11tPlusTunableXfpLaserWavelength,
				omtp11tPlusTunableXfpLaserChannelNumber,
				omtp11tPlusXfpLaserState,
				omtp11tPlusXfpReset,
				omtp11tPlusXfpPowerDownMode,
				omtp11tPlusXfpLineLoopback,
				omtp11tPlusXfpXfiLoopback,
				omtp11tPlusXfpAmplitudeThresholdOfReceiverForFecControl,
				omtp11tPlusXfpPhaseInEyeDiagramForFecControl,
				omtp11tPlusXfpSystemReportingBer,
				omtp11tPlusXfpHighTemperatureAlarmThreshold,
				omtp11tPlusXfpLowTemperatureAlarmThreshold,
				omtp11tPlusXfpHighTemperatureWarningThreshold,
				omtp11tPlusXfpLowTemperatureWarningThreshold,
				omtp11tPlusXfpHighBiasCurrentAlarmThreshold,
				omtp11tPlusXfpLowBiasCurrentAlarmThreshold,
				omtp11tPlusXfpHighBiasCurrentWarningThreshold,
				omtp11tPlusXfpLowBiasCurrentWarningThreshold,
				omtp11tPlusXfpInputHighPowerAlarmThreshold,
				omtp11tPlusXfpInputLowPowerAlarmThreshold,
				omtp11tPlusXfpInputHighPowerWarningThreshold,
				omtp11tPlusXfpInputLowPowerWarningThreshold,
				omtp11tPlusXfpOutputHighPowerAlarmThreshold,
				omtp11tPlusXfpOutputLowPowerAlarmThreshold,
				omtp11tPlusXfpOutputHighPowerWarningThreshold,
				omtp11tPlusXfpOutputLowPowerWarningThreshold,
				omtp11tPlusXfpHighSupplyVoltageAlarmThreshold,
				omtp11tPlusXfpLowSupplyVoltageAlarmThreshold,
				omtp11tPlusXfpHighSupplyVoltageWarningThreshold,
				omtp11tPlusXfpLowSupplyVoltageWarningThreshold,
				omtp11tPlusXfpInputPowerFailureAlarmInhibit,
				omtp11tPlusXfpOutputPowerFailureAlarmInhibit,
				omtp11tPlusXfpHighTemperatureAlarmInhibit,
				omtp11tPlusXfpLowTemperatureAlarmInhibit,
				omtp11tPlusXfpHighTemperatureWarningInhibit,
				omtp11tPlusXfpLowTemperatureWarningInhibit,
				omtp11tPlusXfpHighBiasCurrentAlarmInhibit,
				omtp11tPlusXfpLowBiasCurrentAlarmInhibit,
				omtp11tPlusXfpHighBiasCurrentWarningInhibit,
				omtp11tPlusXfpLowBiasCurrentWarningInhibit,
				omtp11tPlusXfpInputHighPowerAlarmInhibit,
				omtp11tPlusXfpInputLowPowerAlarmInhibit,
				omtp11tPlusXfpInputHighPowerWarningInhibit,
				omtp11tPlusXfpInputLowPowerWarningInhibit,
				omtp11tPlusXfpOutputHighPowerAlarmInhibit,
				omtp11tPlusXfpOutputLowPowerAlarmInhibit,
				omtp11tPlusXfpOutputHighPowerWarningInhibit,
				omtp11tPlusXfpOutputLowPowerWarningInhibit,
				omtp11tPlusXfpHighSupplyVoltageAlarmInhibit,
				omtp11tPlusXfpLowSupplyVoltageAlarmInhibit,
				omtp11tPlusXfpHighSupplyVoltageWarningInhibit,
				omtp11tPlusXfpLowSupplyVoltageWarningInhibit,
				omtp11tPlusXfpPresenceAbsenceNotificationInhibit,
				omtp11tPlusOtuLossOfSignalAlarmInhibit,
				omtp11tPlusOtuLossOfFrameAlarmInhibit,
				omtp11tPlusOtuOutOfFrameAlarmInhibit,
				omtp11tPlusOtuLossOfMultiFrameAlarmInhibit,
				omtp11tPlusOtuOutOfMultiFrameAlarmInhibit,
				omtp11tPlusOtuSignalFailAlarmInhibit,
				omtp11tPlusOtuSignalDegradeAlarmInhibit,
				omtp11tPlusOtuAlarmIndicationSignalAlarmInhibit,
				omtp11tPlusOtuIncomingAlignmentErrorAlarmInhibit,
				omtp11tPlusOtuTraceIdentifierMismatchAlarmInhibit,
				omtp11tPlusOtuBackwardIncomingAlignmentErrorAlarmInhibit,
				omtp11tPlusOtuBackwardDefectIndicationAlarmInhibit,
				omtp11tPlusOduSignalFailAlarmInhibit,
				omtp11tPlusOduSignalDegradeAlarmInhibit,
				omtp11tPlusOduAlarmIndicationSignalAlarmInhibit,
				omtp11tPlusOduTcm1IncomingAlignmentErrorAlarmInhibit,
				omtp11tPlusOduTcm2IncomingAlignmentErrorAlarmInhibit,
				omtp11tPlusOduTcm3IncomingAlignmentErrorAlarmInhibit,
				omtp11tPlusOduTcm4IncomingAlignmentErrorAlarmInhibit,
				omtp11tPlusOduTcm5IncomingAlignmentErrorAlarmInhibit,
				omtp11tPlusOduTcm6IncomingAlignmentErrorAlarmInhibit,
				omtp11tPlusOduTraceIdentifierMismatchAlarmInhibit,
				omtp11tPlusOduLockedDefectAlarmInhibit,
				omtp11tPlusOduOpenConnectionIndicationAlarmInhibit,
				omtp11tPlusOduBackwardDefectIndicationAlarmInhibit,
				omtp11tPlusOduTcm1BackwardIncomingAlignmentErrorAlarmInhibit,
				omtp11tPlusOduTcm2BackwardIncomingAlignmentErrorAlarmInhibit,
				omtp11tPlusOduTcm3BackwardIncomingAlignmentErrorAlarmInhibit,
				omtp11tPlusOduTcm4BackwardIncomingAlignmentErrorAlarmInhibit,
				omtp11tPlusOduTcm5BackwardIncomingAlignmentErrorAlarmInhibit,
				omtp11tPlusOduTcm6BackwardIncomingAlignmentErrorAlarmInhibit,
				omtp11tPlusOpuPayloadMismatchAlarmInhibit,
				omtp11tPlusOchLossOfPayloadAlarmInhibit,
				omtp11tPlusXfpInputPowerFailureAlarmSeverity,
				omtp11tPlusXfpOutputPowerFailureAlarmSeverity,
				omtp11tPlusXfpHighTemperatureAlarmSeverity,
				omtp11tPlusXfpLowTemperatureAlarmSeverity,
				omtp11tPlusXfpHighTemperatureWarningSeverity,
				omtp11tPlusXfpLowTemperatureWarningSeverity,
				omtp11tPlusXfpHighBiasCurrentAlarmSeverity,
				omtp11tPlusXfpLowBiasCurrentAlarmSeverity,
				omtp11tPlusXfpHighBiasCurrentWarningSeverity,
				omtp11tPlusXfpLowBiasCurrentWarningSeverity,
				omtp11tPlusXfpInputHighPowerAlarmSeverity,
				omtp11tPlusXfpInputLowPowerAlarmSeverity,
				omtp11tPlusXfpInputHighPowerWarningSeverity,
				omtp11tPlusXfpInputLowPowerWarningSeverity,
				omtp11tPlusXfpOutputHighPowerAlarmSeverity,
				omtp11tPlusXfpOutputLowPowerAlarmSeverity,
				omtp11tPlusXfpOutputHighPowerWarningSeverity,
				omtp11tPlusXfpOutputLowPowerWarningSeverity,
				omtp11tPlusXfpHighSupplyVoltageAlarmSeverity,
				omtp11tPlusXfpLowSupplyVoltageAlarmSeverity,
				omtp11tPlusXfpHighSupplyVoltageWarningSeverity,
				omtp11tPlusXfpLowSupplyVoltageWarningSeverity,
				omtp11tPlusXfpPresenceAbsenceNotificationSeverity,
				omtp11tPlusOtuLossOfSignalAlarmSeverity,
				omtp11tPlusOtuLossOfFrameAlarmSeverity,
				omtp11tPlusOtuOutOfFrameAlarmSeverity,
				omtp11tPlusOtuLossOfMultiFrameAlarmSeverity,
				omtp11tPlusOtuOutOfMultiFrameAlarmSeverity,
				omtp11tPlusOtuSignalFailAlarmSeverity,
				omtp11tPlusOtuSignalDegradeAlarmSeverity,
				omtp11tPlusOtuAlarmIndicationSignalAlarmSeverity,
				omtp11tPlusOtuIncomingAlignmentErrorAlarmSeverity,
				omtp11tPlusOtuTraceIdentifierMismatchAlarmSeverity,
				omtp11tPlusOtuBackwardIncomingAlignmentErrorAlarmSeverity,
				omtp11tPlusOtuBackwardDefectIndicationAlarmSeverity,
				omtp11tPlusOduSignalFailAlarmSeverity,
				omtp11tPlusOduSignalDegradeAlarmSeverity,
				omtp11tPlusOduAlarmIndicationSignalAlarmSeverity,
				omtp11tPlusOduTcm1IncomingAlignmentErrorAlarmSeverity,
				omtp11tPlusOduTcm2IncomingAlignmentErrorAlarmSeverity,
				omtp11tPlusOduTcm3IncomingAlignmentErrorAlarmSeverity,
				omtp11tPlusOduTcm4IncomingAlignmentErrorAlarmSeverity,
				omtp11tPlusOduTcm5IncomingAlignmentErrorAlarmSeverity,
				omtp11tPlusOduTcm6IncomingAlignmentErrorAlarmSeverity,
				omtp11tPlusOduTraceIdentifierMismatchAlarmSeverity,
				omtp11tPlusOduLockedDefectAlarmSeverity,
				omtp11tPlusOduOpenConnectionIndicationAlarmSeverity,
				omtp11tPlusOduBackwardDefectIndicationAlarmSeverity,
				omtp11tPlusOduTcm1BackwardIncomingAlignmentErrorAlarmSeverity,
				omtp11tPlusOduTcm2BackwardIncomingAlignmentErrorAlarmSeverity,
				omtp11tPlusOduTcm3BackwardIncomingAlignmentErrorAlarmSeverity,
				omtp11tPlusOduTcm4BackwardIncomingAlignmentErrorAlarmSeverity,
				omtp11tPlusOduTcm5BackwardIncomingAlignmentErrorAlarmSeverity,
				omtp11tPlusOduTcm6BackwardIncomingAlignmentErrorAlarmSeverity,
				omtp11tPlusOpuPayloadMismatchAlarmSeverity,
				omtp11tPlusOchLossOfPayloadAlarmSeverity,
				omtp11tPlusConfigurationTableRowStatus,
				omtp11tPlusXfpInputPowerFailureAlarm,
				omtp11tPlusXfpOutputPowerFailureAlarm,
				omtp11tPlusXfpHighTemperatureAlarm,
				omtp11tPlusXfpLowTemperatureAlarm,
				omtp11tPlusXfpHighTemperatureWarning,
				omtp11tPlusXfpLowTemperatureWarning,
				omtp11tPlusXfpHighBiasCurrentAlarm,
				omtp11tPlusXfpLowBiasCurrentAlarm,
				omtp11tPlusXfpHighBiasCurrentWarning,
				omtp11tPlusXfpLowBiasCurrentWarning,
				omtp11tPlusXfpInputHighPowerAlarm,
				omtp11tPlusXfpInputLowPowerAlarm,
				omtp11tPlusXfpInputHighPowerWarning,
				omtp11tPlusXfpInputLowPowerWarning,
				omtp11tPlusXfpOutputHighPowerAlarm,
				omtp11tPlusXfpOutputLowPowerAlarm,
				omtp11tPlusXfpOutputHighPowerWarning,
				omtp11tPlusXfpOutputLowPowerWarning,
				omtp11tPlusXfpHighSupplyVoltageAlarm,
				omtp11tPlusXfpLowSupplyVoltageAlarm,
				omtp11tPlusXfpHighSupplyVoltageWarning,
				omtp11tPlusXfpLowSupplyVoltageWarning,
				omtp11tPlusXfpPresenceAbsenceNotification,
				omtp11tPlusOtuLossOfSignalAlarm,
				omtp11tPlusOtuLossOfFrameAlarm,
				omtp11tPlusOtuOutOfFrameAlarm,
				omtp11tPlusOtuLossOfMultiFrameAlarm,
				omtp11tPlusOtuOutOfMultiFrameAlarm,
				omtp11tPlusOtuSignalFailAlarm,
				omtp11tPlusOtuSignalDegradeAlarm,
				omtp11tPlusOtuAlarmIndicationSignalAlarm,
				omtp11tPlusOtuIncomingAlignmentErrorAlarm,
				omtp11tPlusOtuTraceIdentifierMismatchAlarm,
				omtp11tPlusOtuBackwardIncomingAlignmentErrorAlarm,
				omtp11tPlusOtuBackwardDefectIndicationAlarm,
				omtp11tPlusOduSignalFailAlarm,
				omtp11tPlusOduSignalDegradeAlarm,
				omtp11tPlusOduAlarmIndicationSignalAlarm,
				omtp11tPlusOduTcm1IncomingAlignmentErrorAlarm,
				omtp11tPlusOduTcm2IncomingAlignmentErrorAlarm,
				omtp11tPlusOduTcm3IncomingAlignmentErrorAlarm,
				omtp11tPlusOduTcm4IncomingAlignmentErrorAlarm,
				omtp11tPlusOduTcm5IncomingAlignmentErrorAlarm,
				omtp11tPlusOduTcm6IncomingAlignmentErrorAlarm,
				omtp11tPlusOduTraceIdentifierMismatchAlarm,
				omtp11tPlusOduLockedDefectAlarm,
				omtp11tPlusOduOpenConnectionIndicationAlarm,
				omtp11tPlusOduBackwardDefectIndicationAlarm,
				omtp11tPlusOduTcm1BackwardIncomingAlignmentErrorAlarm,
				omtp11tPlusOduTcm2BackwardIncomingAlignmentErrorAlarm,
				omtp11tPlusOduTcm3BackwardIncomingAlignmentErrorAlarm,
				omtp11tPlusOduTcm4BackwardIncomingAlignmentErrorAlarm,
				omtp11tPlusOduTcm5BackwardIncomingAlignmentErrorAlarm,
				omtp11tPlusOduTcm6BackwardIncomingAlignmentErrorAlarm,
				omtp11tPlusOpuPayloadMismatchAlarm,
				omtp11tPlusOchLossOfPayloadAlarm,
				omtp11tPlusAlarmQueryTableRowStatus,
				omtp11tPlusXfpInputPower,
				omtp11tPlusXfpOutputPower,
				omtp11tPlusXfpBiasCurrent,
				omtp11tPlusXfpSupplyVoltage,
				omtp11tPlusXfpTemperature,
				omtp11tPlusOtnFecUncorrectedWords,
				omtp11tPlusOtnFecCorrectedBits,
				omtp11tPlusOtnFecZerosCorrectedBits,
				omtp11tPlusOtnFecOnesCorrectedBits,
				omtp11tPlusOtuBitInterleavedParityErrors,
				omtp11tPlusOtuIncomingAlignmentErrorSeconds,
				omtp11tPlusOtuBackwardErrorIndicationErrorCount,
				omtp11tPlusOtuBackwardIncomingAlignmentErrorSeconds,
				omtp11tPlusOtuErrorFreeSeconds,
				omtp11tPlusOtuErrorSeconds,
				omtp11tPlusOtuBackgroundBlockErrors,
				omtp11tPlusOtuSevereErrorSeconds,
				omtp11tPlusOtuUnavailableSeconds,
				omtp11tPlusOtuBackgroundBlockErrorRatio,
				omtp11tPlusOtuSevereErrorSecondsErrorRatio,
				omtp11tPlusOtuFarEndErrorFreeSeconds,
				omtp11tPlusOtuFarEndErrorSeconds,
				omtp11tPlusOtuFarEndBackgroundBlockErrors,
				omtp11tPlusOtuFarEndSevereErrorSeconds,
				omtp11tPlusOtuFarEndUnavailableSeconds,
				omtp11tPlusOtuFarEndBackgroundBlockErrorRatio,
				omtp11tPlusOtuFarEndSevereErrorSecondsErrorRatio,
				omtp11tPlusOtuErrorRatio,
				omtp11tPlusOtuBitErrorRate,
				omtp11tPlusOtuFramesReceived,
				omtp11tPlusOduBitInterleavedParityErrors,
				omtp11tPlusOduTcm1BitInterleavedParityErrors,
				omtp11tPlusOduTcm2BitInterleavedParityErrors,
				omtp11tPlusOduTcm3BitInterleavedParityErrors,
				omtp11tPlusOduTcm4BitInterleavedParityErrors,
				omtp11tPlusOduTcm5BitInterleavedParityErrors,
				omtp11tPlusOduTcm6BitInterleavedParityErrors,
				omtp11tPlusOduTcm1IncomingAlignmentErrorSeconds,
				omtp11tPlusOduBackwardErrorIndicationErrorCount,
				omtp11tPlusOduTcm1BackwardErrorIndicationErrorCount,
				omtp11tPlusOduTcm2BackwardErrorIndicationErrorCount,
				omtp11tPlusOduTcm3BackwardErrorIndicationErrorCount,
				omtp11tPlusOduTcm4BackwardErrorIndicationErrorCount,
				omtp11tPlusOduTcm5BackwardErrorIndicationErrorCount,
				omtp11tPlusOduTcm6BackwardErrorIndicationErrorCount,
				omtp11tPlusOduTcm1BackwardIncomingAlignmentErrorSeconds,
				omtp11tPlusOduDelayMeasurement,
				omtp11tPlusOduErrorFreeSeconds,
				omtp11tPlusOduErrorSeconds,
				omtp11tPlusOduBackgroundBlockErrors,
				omtp11tPlusOduSevereErrorSeconds,
				omtp11tPlusOduUnavailableSeconds,
				omtp11tPlusOduBackgroundBlockErrorRatio,
				omtp11tPlusOduSevereErrorSecondsErrorRatio,
				omtp11tPlusOduFarEndErrorFreeSeconds,
				omtp11tPlusOduFarEndErrorSeconds,
				omtp11tPlusOduFarEndBackgroundBlockErrors,
				omtp11tPlusOduFarEndSevereErrorSeconds,
				omtp11tPlusOduFarEndUnavailableSeconds,
				omtp11tPlusOduFarEndBackgroundBlockErrorRatio,
				omtp11tPlusOduFarEndSevereErrorSecondsErrorRatio,
				omtp11tPlusPerformanceTableRowStatus,
				omtp11tPlusDiagnosticTableRowStatus,
				omtp11tPlusAccessCortinaRegister,
				omtp11tPlusCollectCortinaRegisterDump,
				omtp11tPlusCollectCortinaModulebGpllRxLockStatus,
				omtp11tPlusCollectCortinaModulebGpllTxLockStatus,
				omtp11tPlusCollectCortinaModulebTxSerdesLockStatus,
				omtp11tPlusCollectCortinaModulebTxSerdesVcoTunedValue,
				omtp11tPlusCollectCortinaModulebXfiCupllLockStatus,
				omtp11tPlusCollectCortinaModulebAllClockLockStatus
		}
		STATUS  current
		DESCRIPTION
	    		"A collection of objects from RFC 1213 made current by this MIB module."
		::= { utlrnd 2 }

END

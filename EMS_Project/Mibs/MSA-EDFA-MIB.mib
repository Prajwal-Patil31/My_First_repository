--*****************************************************************************
--				UTL MSA EDFA MIB
--*****************************************************************************

MSA-EDFA-MIB DEFINITIONS ::= BEGIN
 
		IMPORTS
		RowStatus				FROM STANDARD-MIB

		DisplayString				FROM RFC1213-MIB       

		OBJECT-IDENTITY, 
		NOTIFICATION-TYPE, 
		MODULE-IDENTITY, 
		Integer32, 
		Unsigned32, 
		IpAddress, 
		TimeTicks				FROM SNMPv2-SMI

		OBJECT-TYPE				FROM RFC-1212

		MODULE-COMPLIANCE, 
		OBJECT-GROUP, 
		NOTIFICATION-GROUP			FROM SNMPv2-CONF
		
		node, 
		rack, 
		subRack, 
		slot 					FROM SCC-MIB

		enterprises 				FROM RFC1155-SMI		

	;

	utl   	MODULE-IDENTITY
		LAST-UPDATED    	"1807130630Z"
		ORGANIZATION    	"United Telecoms Limited, Bangalore-560048."
		CONTACT-INFO    	"Website: http://www.utlindia.com."                                           
		DESCRIPTION     	"MIB module for UTL DWDM."
		REVISION 	    	"1807130630Z"

		DESCRIPTION    	 	"MIB module for MSA EDFA Card."

		::= { enterprises 18036 }

	utlrnd  OBJECT-IDENTITY
		STATUS  current

		DESCRIPTION "UTL R and D."

		::= { utl 1 }

	dwdm 				OBJECT IDENTIFIER	::=   { utlrnd 1 }
	indus 				OBJECT IDENTIFIER	::=   { dwdm 1 }
	msaEdfa 			OBJECT IDENTIFIER 	::=   { indus 142 }

	msaEdfaCardGeneralDetails 	OBJECT IDENTIFIER 	::=   { msaEdfa 1 }
	msaEdfaConfiguration 		OBJECT IDENTIFIER 	::=   { msaEdfa 2 }
	msaEdfaAlarm 			OBJECT IDENTIFIER 	::=   { msaEdfa 3 }
	msaEdfaPerformance 		OBJECT IDENTIFIER 	::=   { msaEdfa 4 }

	msaEdfaAlarmQuery 		OBJECT IDENTIFIER 	::=   { msaEdfaAlarm 1 }
	msaEdfaAlarmNotification 	OBJECT IDENTIFIER 	::=   { msaEdfaAlarm 2 }
	
--*****************************************************************************
--			MSA EDFA CARD GENERAL DETAILS
--*****************************************************************************

	msaEdfaCardGeneralDetailsTable OBJECT-TYPE
		SYNTAX  	SEQUENCE OF MsaPaBaEdfaCardGeneralDetailsEntry
		MAX-ACCESS	not-accessible
		STATUS		current

		DESCRIPTION
		 " we can get MSA EDFA card general details "

		::= { msaEdfaCardGeneralDetails 1 }

	msaEdfaCardGeneralDetailsEntry OBJECT-TYPE
		SYNTAX  	MsaPaBaEdfaCardGeneralDetailsEntry
		MAX-ACCESS  	not-accessible
		STATUS  	current

		DESCRIPTION 
		 "Enter node rack, subrack, slot and msaEdfaInterface numbers"

		INDEX   { node, rack, subRack, slot, msaEdfaInterface }

		::= { msaEdfaCardGeneralDetailsTable 1 }

	MsaPaBaEdfaCardGeneralDetailsEntry ::=
		SEQUENCE {
				msaEdfaInterface					INTEGER,
				msaEdfaEepromCardId					INTEGER,
				msaEdfaEepromCardName					DisplayString,
				msaEdfaEepromPartCode					DisplayString,
				msaEdfaEepromCardSerialNumber				DisplayString,
				msaEdfaEepromHardwareExternalReleaseVersion		DisplayString,
				msaEdfaSoftwareExternalReleaseVersion			DisplayString,
				msaEdfaEepromHardwareInternalReleaseVersion		DisplayString,
				msaEdfaSoftwareInternalReleaseVersion			DisplayString,
				msaEdfaEepromCardUidNumber				DisplayString,
				msaEdfaEepromCardEUI48Number				DisplayString,
				msaEdfaEepromCardEUI64Number				DisplayString,
				msaEdfaEepromModuleType					DisplayString,
				msaEdfaInstallationDate					DisplayString,
				msaEdfaCommissionDate					DisplayString,
				msaEdfaCardRunningTime					DisplayString,
				msaEdfaCardRestartCount					INTEGER,

			   	msaPaEdfaModuleVendorName	                        DisplayString,
				msaPaEdfaModuleSerialNumber		                INTEGER,		
				msaPaEdfaModuleNumberOfChannelsSupported		INTEGER,
				msaPaEdfaModuleNumberOfPumpSupported                    INTEGER,			
				msaPaEdfaModuleMaxGainSupported				DisplayString,
				msaPaEdfaModuleSaturationOutputPowerSupported		DisplayString,
				msaPaEdfaModuleVoaPresenceStatus			INTEGER,				
				
				msaBaEdfaModuleVendorName	                        DisplayString,
				msaBaEdfaModuleSerialNumber			        INTEGER,	
				msaBaEdfaModuleNumberOfChannelsSupported	        INTEGER,		
				msaBaEdfaModuleNumberOfPumpSupported		        INTEGER,		
				msaBaEdfaModuleMaxGainSupported			        DisplayString,
				msaBaEdfaModuleSaturationOutputPowerSupported	        DisplayString,
				msaBaEdfaModuleVoaPresenceStatus                	INTEGER,				

				msaEdfaDirection					INTEGER,
				msaEdfaCardGeneralDetailsTableRowStatus			RowStatus
			}	
	
	msaEdfaInterface 	OBJECT-TYPE
		SYNTAX  	INTEGER
		MAX-ACCESS  	not-accessible
		STATUS  	current
		DESCRIPTION	
			"msa edfa interface number, should be 0 always"

		::= { msaEdfaCardGeneralDetailsEntry 1 }

	msaEdfaEepromCardId OBJECT-TYPE
		SYNTAX  	INTEGER
		MAX-ACCESS  	read-only
		STATUS  	current

		DESCRIPTION
		 " Tells the card ID of the MSA EDFA card, present in the EEPROM "

		::= { msaEdfaCardGeneralDetailsEntry 2 }

	msaEdfaEepromCardName OBJECT-TYPE
		SYNTAX  	DisplayString (SIZE (0..255))
		MAX-ACCESS  	read-only
		STATUS		current

		DESCRIPTION
		 " Tells the card name of the MSA EDFA card, present in the EEPROM "

		::= { msaEdfaCardGeneralDetailsEntry 3 }

	msaEdfaEepromPartCode OBJECT-TYPE
		SYNTAX  	DisplayString (SIZE (0..255))
		MAX-ACCESS  	read-only
		STATUS		current

		DESCRIPTION
		 " Tells the part code of the MSA EDFA card, present in the EEPROM "

		::= { msaEdfaCardGeneralDetailsEntry 4 }

	msaEdfaEepromCardSerialNumber OBJECT-TYPE
		SYNTAX  	DisplayString (SIZE (0..255))
		MAX-ACCESS  	read-write
		STATUS		current

		DESCRIPTION
		 " This property get / set the information about MSA EDFA 
		 Card's Serial Number.
		-----------------------------
		Values:
		eg: 123456
		-----------------------------"

		::= { msaEdfaCardGeneralDetailsEntry 5 }

	msaEdfaEepromHardwareExternalReleaseVersion OBJECT-TYPE
		SYNTAX  	DisplayString (SIZE (0..255))
		MAX-ACCESS  	read-only
		STATUS		current

		DESCRIPTION
		 " To get the Card's Hardware External Release Version. This detail 
		 will be displayed to the customer. This version will increment 
		 only if there are significant architectural changes in the product.
		-----------------------------
		Value:
		eg: 0.1
		-----------------------------"

		::= { msaEdfaCardGeneralDetailsEntry 6 }

	msaEdfaSoftwareExternalReleaseVersion OBJECT-TYPE
		SYNTAX  	DisplayString (SIZE (0..255))
		MAX-ACCESS  	read-only
		STATUS		current

		DESCRIPTION
		 " To get the Card's Software External Release Version.  This detail 
		 will be displayed to the customer. This version will increment 
		 only if there are significant architectural changes in the product.
		-----------------------------
		Value:
		eg: 0.1
		-----------------------------"

		::= { msaEdfaCardGeneralDetailsEntry 7 }

	msaEdfaEepromHardwareInternalReleaseVersion OBJECT-TYPE
		SYNTAX  	DisplayString (SIZE (0..255))
		MAX-ACCESS  	read-only
		STATUS		current

		DESCRIPTION
		 " To get the Card's Hardware Internal Release Version. This detail 
		 is used for development purposes only. It differs from the external 
		 hardware version.
		-----------------------------
		Value:
		eg: 4.1
		-----------------------------"

		::= { msaEdfaCardGeneralDetailsEntry 8 }

	msaEdfaSoftwareInternalReleaseVersion OBJECT-TYPE
		SYNTAX  	DisplayString (SIZE (0..255))
		MAX-ACCESS  	read-only
		STATUS		current

		DESCRIPTION
		 " To get the Card's Software Internal Release Version.  This detail 
		 is used for development purposes only. It differs from the external 
		 software version.
		-----------------------------
		Value:
		eg: 5.1
		-----------------------------"

		::= { msaEdfaCardGeneralDetailsEntry 9 }

	msaEdfaEepromCardUidNumber OBJECT-TYPE
		SYNTAX  	DisplayString (SIZE (0..255))
		MAX-ACCESS  	read-only
		STATUS		current

		DESCRIPTION
		 " Tells the Card Unique Identifier It is a 4 byte address used to 
		 uniquely identify a card.
		------------------------------
		Value:
	      	eg: 12345678
		-----------------------------"

		::= { msaEdfaCardGeneralDetailsEntry 10 }

	msaEdfaEepromCardEUI48Number OBJECT-TYPE
		SYNTAX  	DisplayString (SIZE (0..255))
		MAX-ACCESS  	read-only
		STATUS		current

		DESCRIPTION
		 " Tells the Card EUI-48 Number. It’s a 6 byte address used to 
		 uniquely identify a card.
		-----------------------------
		Value:
	      	eg: 0004A3123456
		-----------------------------"

		::= { msaEdfaCardGeneralDetailsEntry 11 }

	msaEdfaEepromCardEUI64Number OBJECT-TYPE
		SYNTAX  	DisplayString (SIZE (0..255))
		MAX-ACCESS  	read-only
		STATUS		current

		DESCRIPTION
		 " Tells the Card EUI-64 Number. It’s a 8 byte address
		used to uniquely identify a card.
		-----------------------------
		Value:
	      	eg: 0004A31234567890
		-----------------------------"

		::= { msaEdfaCardGeneralDetailsEntry 12 }	

	msaEdfaEepromModuleType OBJECT-TYPE
		SYNTAX  	DisplayString (SIZE (0..255))
		MAX-ACCESS  	read-only
		STATUS		current

		DESCRIPTION
		 " Tells the EDFA Module Type. It represents the EDFA
		module that is connected in card.
		-----------------------------
		Value:
	      	eg: pa_edfa or ba_edfa
		-----------------------------"

		::= { msaEdfaCardGeneralDetailsEntry 13 }

	msaEdfaInstallationDate OBJECT-TYPE
		SYNTAX  	DisplayString (SIZE (0..255))
		MAX-ACCESS  	read-write
		STATUS		current

		DESCRIPTION
		 " To get/set the card's installation date in dd/mm/yyyy format.
		-----------------------------
		Value:
	      	eg: 12/03/2016
		-----------------------------"

		::= { msaEdfaCardGeneralDetailsEntry 14 }

	msaEdfaCommissionDate OBJECT-TYPE
		SYNTAX  	DisplayString (SIZE (0..255))
		MAX-ACCESS  	read-write
		STATUS		current

		DESCRIPTION
		 " To get/set the card's commission date in  dd/mm/yyyy format.
		-----------------------------
		Value:
	      	eg: 20/03/2016
		-----------------------------"

		::= { msaEdfaCardGeneralDetailsEntry 15 }

	msaEdfaCardRunningTime OBJECT-TYPE
		SYNTAX  	DisplayString (SIZE (0..255))
		MAX-ACCESS  	read-only
		STATUS		current

		DESCRIPTION
		 " To get the duration of time for which the card is operational/running.
		-----------------------------
		Values:
	      	eg: 3d 2h 1m
		-----------------------------"

		::= { msaEdfaCardGeneralDetailsEntry 16 }

	msaEdfaCardRestartCount OBJECT-TYPE
		SYNTAX  	INTEGER
		MAX-ACCESS  	read-only
		STATUS		current

		DESCRIPTION
		 " To get the number of times the card has been soft reset. This value 
		 will get reset to 0 on factory reset.
		-----------------------------
		Values:
	      	eg: 10
		-----------------------------"

		::= { msaEdfaCardGeneralDetailsEntry 17 }	

	msaPaEdfaModuleVendorName OBJECT-TYPE
		SYNTAX  	DisplayString (SIZE (0..255))
		MAX-ACCESS  	read-only
		STATUS		current

		DESCRIPTION
		 " to get MSA PA EDFA card module vendor name.
		-----------------------------
		Values:
	      	eg: ACCELINK
		-----------------------------"

		::= { msaEdfaCardGeneralDetailsEntry 18 }

	msaPaEdfaModuleSerialNumber OBJECT-TYPE
		SYNTAX  	INTEGER
		MAX-ACCESS  	read-only
		STATUS		current

		DESCRIPTION
		 " to get MSA PA EDFA card module serial number.
		-----------------------------
		Values:
	      	eg: 12345
		-----------------------------"

		::= { msaEdfaCardGeneralDetailsEntry 19 }

	msaPaEdfaModuleNumberOfChannelsSupported OBJECT-TYPE
		SYNTAX  	INTEGER
		MAX-ACCESS  	read-only
		STATUS  	current

		DESCRIPTION
		 " to get MSA PA EDFA card supports how many number of channels.
		-----------------------------
		Values:
	      	eg: 30
		-----------------------------"

		::= { msaEdfaCardGeneralDetailsEntry 20 }

	msaPaEdfaModuleNumberOfPumpSupported OBJECT-TYPE
		SYNTAX  	INTEGER
		MAX-ACCESS  	read-only
		STATUS  	current

		DESCRIPTION
		 " to get MSA PA EDFA card supports how many number of pumps.
		-----------------------------
		Values:
	      	eg: 2
		-----------------------------"

		::= { msaEdfaCardGeneralDetailsEntry 21 }

	msaPaEdfaModuleMaxGainSupported OBJECT-TYPE
		SYNTAX  	DisplayString (SIZE (0..255))
		MAX-ACCESS  	read-only
		STATUS		current

		DESCRIPTION
		 " to get MSA PA EDFA card supports maximum gain supported.
		-----------------------------
		Values:
	      	eg: 25.0
		-----------------------------"

		::= { msaEdfaCardGeneralDetailsEntry 22 }

	msaPaEdfaModuleSaturationOutputPowerSupported OBJECT-TYPE
		SYNTAX  	DisplayString (SIZE (0..255))
		MAX-ACCESS  	read-only
		STATUS		current

		DESCRIPTION
		 " to get MSA PA EDFA card supports saturation power.
		-----------------------------
		Values:
	      	eg: 19.0
		-----------------------------"

		::= { msaEdfaCardGeneralDetailsEntry 23 }

	msaPaEdfaModuleVoaPresenceStatus	OBJECT-TYPE
		SYNTAX  	INTEGER
		MAX-ACCESS  read-only
		STATUS  	current
		DESCRIPTION	" to get MSA PA EDFA inbuilt voa presence status.
		-----------------------------
		Values:
		1 - VOA present 
		0 - VOA absent
		-----------------------------"
		::= { msaEdfaCardGeneralDetailsEntry 24 }

	msaBaEdfaModuleVendorName OBJECT-TYPE
		SYNTAX  	DisplayString (SIZE (0..255))
		MAX-ACCESS  	read-only
		STATUS		current

		DESCRIPTION
		 " to get MSA BA EDFA card module vendor name.
		-----------------------------
		Values:
	      	eg: ACCELINK
		-----------------------------"

		::= { msaEdfaCardGeneralDetailsEntry 25 }

	msaBaEdfaModuleSerialNumber OBJECT-TYPE
		SYNTAX  	INTEGER
		MAX-ACCESS  	read-only
		STATUS		current

		DESCRIPTION
		 " to get MSA BA EDFA card module serial number.
		-----------------------------
		Values:
	      	eg: 12345
		-----------------------------"

		::= { msaEdfaCardGeneralDetailsEntry 26 }

	msaBaEdfaModuleNumberOfChannelsSupported OBJECT-TYPE
		SYNTAX  	INTEGER
		MAX-ACCESS  	read-only
		STATUS  	current

		DESCRIPTION
		 " to get MSA BA EDFA card supports how many number of channels.
		-----------------------------
		Values:
	      	eg: 30
		-----------------------------"

		::= { msaEdfaCardGeneralDetailsEntry 27 }

	msaBaEdfaModuleNumberOfPumpSupported OBJECT-TYPE
		SYNTAX  	INTEGER
		MAX-ACCESS  	read-only
		STATUS  	current

		DESCRIPTION
		 " to get MSA BA EDFA card supports how many number of pumps.
		-----------------------------
		Values:
	      	eg: 2
		-----------------------------"

		::= { msaEdfaCardGeneralDetailsEntry 28 }

	msaBaEdfaModuleMaxGainSupported OBJECT-TYPE
		SYNTAX  	DisplayString (SIZE (0..255))
		MAX-ACCESS  	read-only
		STATUS		current

		DESCRIPTION
		 " to get MSA BA EDFA card supports maximum gain supported.
		-----------------------------
		Values:
	      	eg: 25.0
		-----------------------------"

		::= { msaEdfaCardGeneralDetailsEntry 29 }

	msaBaEdfaModuleSaturationOutputPowerSupported OBJECT-TYPE
		SYNTAX  	DisplayString (SIZE (0..255))
		MAX-ACCESS  	read-only
		STATUS		current

		DESCRIPTION
		 " to get MSA BA EDFA card supports saturation power.
		-----------------------------
		Values:
	      	eg: 19.0
		-----------------------------"

		::= { msaEdfaCardGeneralDetailsEntry 30 }

	msaBaEdfaModuleVoaPresenceStatus	OBJECT-TYPE
		SYNTAX  	INTEGER
		MAX-ACCESS  read-only
		STATUS  	current
		DESCRIPTION	" to get MSA BA EDFA inbuilt voa presence status.
		-----------------------------
		Values:
		1 - VOA present 
		0 - VOA absent
		-----------------------------"
		::= { msaEdfaCardGeneralDetailsEntry 31 }

	
	msaEdfaDirection	OBJECT-TYPE
		SYNTAX  	INTEGER
		MAX-ACCESS  	read-only
		STATUS  	current
		DESCRIPTION	
		" to get MSA EDFA card Direction.
		-----------------------------
		Values:
		1 - Direction 1
		2 - Direction 2
		3 - Direction 3
		4 - Direction 4
		-----------------------------"
		::= { msaEdfaCardGeneralDetailsEntry 32 }
		
	msaEdfaCardGeneralDetailsTableRowStatus OBJECT-TYPE
	      SYNTAX      RowStatus
	      MAX-ACCESS  read-write
	      STATUS      current
	      DESCRIPTION
		      "	This is MIB realted property,
			NOT to be considered as a card property"
	      ::= { msaEdfaCardGeneralDetailsEntry 33 }
		
--*****************************************************************************
--			MSA EDFA CONFIGURATION
--***************************************************************************** 

	msaEdfaConfigurationTable OBJECT-TYPE
		SYNTAX  	SEQUENCE OF MsaPaBaEdfaConfigurationEntry
		MAX-ACCESS  	not-accessible
		STATUS  	current

		DESCRIPTION
		 " we can get MSA EDFA configuration details "

		::= { msaEdfaConfiguration 1 }

		msaEdfaConfigurationEntry OBJECT-TYPE
		SYNTAX  	MsaPaBaEdfaConfigurationEntry
		MAX-ACCESS  	not-accessible
		STATUS  	current

		DESCRIPTION  
		 "Enter node rack, subrack, slot and msaEdfaInterface numbers"

		INDEX   { node, rack, subRack, slot, msaEdfaInterface }

		::= { msaEdfaConfigurationTable 1 }

	MsaPaBaEdfaConfigurationEntry ::= 
		SEQUENCE {

					
				msaEdfaCardSoftReset							INTEGER,
				msaEdfaCardDefaultFactoryReset						INTEGER,
				msaEdfaAlarmMonitoringStatus						INTEGER,
				msaEdfaSystemTimeAndRtcTime						DisplayString,
				msaEdfaSyncRtcWithNtpServer						DisplayString,
				msaEdfaSyncRtcWithSystemTime						INTEGER,
				msaEdfaSyncSystemTimeWithNtpServer					DisplayString,
				msaEdfaUpdateGivenTimeIntoRtc						DisplayString,
				msaEdfaUpdateGivenTimeIntoSystem					DisplayString,
				msaPaEdfaModulePumpLaserStatus						INTEGER,
				msaPaEdfaModuleAutomaticLaserShutdownStatusForStage1			INTEGER,
				msaPaEdfaModuleOperatingMode						DisplayString,
				msaPaEdfaModuleGainInAutomaticGainControlMode				DisplayString,
				msaPaEdfaModuleGainTilt	 						DisplayString,
				msaPaEdfaModuleOpticalOutputPowerInAutomaticPowerControlMode			DisplayString,
				msaPaEdfaModulePump1OperatingCurrentInAutomaticCurrentControlMode	DisplayString,
				msaPaEdfaModuleVariableOpticalAttenuatorAttenuation			DisplayString,
				msaPaEdfaModuleResetOpticalAmplifier					INTEGER,
				msaBaEdfaModulePumpLaserStatus						INTEGER,
				msaBaEdfaModuleAutomaticLaserShutdownStatusForStage1			INTEGER,
				msaBaEdfaModuleOperatingMode						DisplayString,
				msaBaEdfaModuleOpticalOutputPowerInAutomaticPowerControlMode			DisplayString,
				msaBaEdfaModulePump1OperatingCurrentInAutomaticCurrentControlMode	DisplayString,
				msaBaEdfaModuleVariableOpticalAttenuatorAttenuation			DisplayString,
				msaBaEdfaModuleResetOpticalAmplifier					INTEGER,
				msaPaEdfaOpticalInputPowerFailureAlarmThreshold				DisplayString,
				msaPaEdfaOpticalInputPowerFailureAlarmThresholdMinimumValue		DisplayString,
				msaPaEdfaOpticalInputPowerFailureAlarmThresholdMaximumValue		DisplayString,
				msaPaEdfaHighOpticalInputPowerAlarmThreshold				DisplayString,
				msaPaEdfaHighOpticalInputPowerAlarmThresholdMinimumValue		DisplayString,
				msaPaEdfaHighOpticalInputPowerAlarmThresholdMaximumValue		DisplayString,
				msaPaEdfaLowOpticalInputPowerAlarmThreshold				DisplayString,
				msaPaEdfaLowOpticalInputPowerAlarmThresholdMinimumValue			DisplayString,
				msaPaEdfaLowOpticalInputPowerAlarmThresholdMaximumValue			DisplayString,
				msaPaEdfaHighOpticalInputPowerWarningThreshold				DisplayString,
				msaPaEdfaHighOpticalInputPowerWarningThresholdMinimumValue		DisplayString,
				msaPaEdfaHighOpticalInputPowerWarningThresholdMaximumValue		DisplayString,
				msaPaEdfaLowOpticalInputPowerWarningThreshold				DisplayString,
				msaPaEdfaLowOpticalInputPowerWarningThresholdMinimumValue		DisplayString,
				msaPaEdfaLowOpticalInputPowerWarningThresholdMaximumValue		DisplayString,
				msaPaEdfaHighOpticalOutputPowerWarningThreshold				DisplayString,
				msaPaEdfaHighOpticalOutputPowerWarningThresholdMinimumValue		DisplayString,
				msaPaEdfaHighOpticalOutputPowerWarningThresholdMaximumValue		DisplayString,
				msaPaEdfaLowOpticalOutputPowerWarningThreshold				DisplayString,
				msaPaEdfaLowOpticalOutputPowerWarningThresholdMinimumValue		DisplayString,
				msaPaEdfaLowOpticalOutputPowerWarningThresholdMaximumValue		DisplayString,
				msaPaEdfaOpticalOutputPowerFailureAlarmThreshold			DisplayString,
				msaPaEdfaOpticalOutputPowerFailureAlarmThresholdMinimumValue		DisplayString,
				msaPaEdfaOpticalOutputPowerFailureAlarmThresholdMaximumValue		DisplayString,
				msaPaEdfaHighOpticalOutputPowerAlarmThreshold				DisplayString,
				msaPaEdfaHighOpticalOutputPowerAlarmThresholdMinimumValue		DisplayString,
				msaPaEdfaHighOpticalOutputPowerAlarmThresholdMaximumValue		DisplayString,
				msaPaEdfaLowOpticalOutputPowerAlarmThreshold				DisplayString,
				msaPaEdfaLowOpticalOutputPowerAlarmThresholdMinimumValue		DisplayString,
				msaPaEdfaLowOpticalOutputPowerAlarmThresholdMaximumValue		DisplayString,
				msaPaEdfaHighTemperatureAlarmThreshold					DisplayString,
				msaPaEdfaHighTemperatureAlarmThresholdMinimumValue			DisplayString,
				msaPaEdfaHighTemperatureAlarmThresholdMaximumValue			DisplayString,
				msaPaEdfaLowTemperatureAlarmThreshold					DisplayString,
				msaPaEdfaLowTemperatureAlarmThresholdMinimumValue			DisplayString,
				msaPaEdfaLowTemperatureAlarmThresholdMaximumValue			DisplayString,
				msaPaEdfaHighTemperatureWarningThreshold				DisplayString,
				msaPaEdfaHighTemperatureWarningThresholdMinimumValue			DisplayString,
				msaPaEdfaHighTemperatureWarningThresholdMaximumValue			DisplayString,
				msaPaEdfaLowTemperatureWarningThreshold					DisplayString,
				msaPaEdfaLowTemperatureWarningThresholdMinimumValue			DisplayString,
				msaPaEdfaLowTemperatureWarningThresholdMaximumValue			DisplayString,
				msaPaEdfaHighOperatingCurrentAlarmThreshold				DisplayString,
				msaPaEdfaHighOperatingCurrentAlarmThresholdMinimumValue			DisplayString,
				msaPaEdfaHighOperatingCurrentAlarmThresholdMaximumValue			DisplayString,
				msaPaEdfaLowOperatingCurrentAlarmThreshold				DisplayString,
				msaPaEdfaLowOperatingCurrentAlarmThresholdMinimumValue			DisplayString,
				msaPaEdfaLowOperatingCurrentAlarmThresholdMaximumValue			DisplayString,
				msaPaEdfaHighOperatingCurrentWarningThreshold				DisplayString,
				msaPaEdfaHighOperatingCurrentWarningThresholdMinimumValue		DisplayString,
				msaPaEdfaHighOperatingCurrentWarningThresholdMaximumValue		DisplayString,
				msaPaEdfaLowOperatingCurrentWarningThreshold				DisplayString,
				msaPaEdfaLowOperatingCurrentWarningThresholdMinimumValue		DisplayString,
				msaPaEdfaLowOperatingCurrentWarningThresholdMaximumValue		DisplayString,
				msaPaEdfaHighTECCurrentAlarmThreshold					DisplayString,
				msaPaEdfaHighTECCurrentAlarmThresholdMinimumValue			DisplayString,
				msaPaEdfaHighTECCurrentAlarmThresholdMaximumValue			DisplayString,
				msaPaEdfaLowTECCurrentAlarmThreshold					DisplayString,
				msaPaEdfaLowTECCurrentAlarmThresholdMinimumValue			DisplayString,
				msaPaEdfaLowTECCurrentAlarmThresholdMaximumValue			DisplayString,
				msaPaEdfaHighTECCurrentWarningThreshold					DisplayString,
				msaPaEdfaHighTECCurrentWarningThresholdMinimumValue			DisplayString,
				msaPaEdfaHighTECCurrentWarningThresholdMaximumValue			DisplayString,
				msaPaEdfaLowTECCurrentWarningThreshold					DisplayString,
				msaPaEdfaLowTECCurrentWarningThresholdMinimumValue			DisplayString,
				msaPaEdfaLowTECCurrentWarningThresholdMaximumValue			DisplayString,
				msaPaEdfaVoaHighInputPowerAlarmThreshold				DisplayString,
				msaPaEdfaVoaHighInputPowerAlarmThresholdMinimumValue			DisplayString,
				msaPaEdfaVoaHighInputPowerAlarmThresholdMaximumValue			DisplayString,
				msaPaEdfaVoaLowInputPowerAlarmThreshold					DisplayString,
				msaPaEdfaVoaLowInputPowerAlarmThresholdMinimumValue			DisplayString,
				msaPaEdfaVoaLowInputPowerAlarmThresholdMaximumValue			DisplayString,
				msaPaEdfaVoaHighInputPowerWarningThreshold				DisplayString,
				msaPaEdfaVoaHighInputPowerWarningThresholdMinimumValue			DisplayString,
				msaPaEdfaVoaHighInputPowerWarningThresholdMaximumValue			DisplayString,
				msaPaEdfaVoaLowInputPowerWarningThreshold				DisplayString,
				msaPaEdfaVoaLowInputPowerWarningThresholdMinimumValue			DisplayString,
				msaPaEdfaVoaLowInputPowerWarningThresholdMaximumValue			DisplayString,
				msaPaEdfaModuleInputOpticalPowerLowAlarmThreshold			DisplayString,
				msaPaEdfaModuleInputOpticalPowerLowAlarmThresholdMinimumValue		DisplayString,
				msaPaEdfaModuleInputOpticalPowerLowAlarmThresholdMaximumValue		DisplayString,
				msaPaEdfaModuleInputOpticalPowerHighAlarmThreshold			DisplayString,
				msaPaEdfaModuleInputOpticalPowerHighAlarmThresholdMinimumValue		DisplayString,
				msaPaEdfaModuleInputOpticalPowerHighAlarmThresholdMaximumValue		DisplayString,
				msaPaEdfaModuleOutputOpticalPowerFailureAlarmThreshold			DisplayString,
				msaPaEdfaModuleOutputOpticalPowerFailureAlarmThresholdMinimumValue	DisplayString,
				msaPaEdfaModuleOutputOpticalPowerFailureAlarmThresholdMaximumValue	DisplayString,
				msaPaEdfaModuleInputAlarmThreshold					DisplayString,
				msaPaEdfaModuleInputAlarmThresholdMinimumValue				DisplayString,
				msaPaEdfaModuleInputAlarmThresholdMaximumValue				DisplayString,
				msaBaEdfaOpticalInputPowerFailureAlarmThreshold				DisplayString,
				msaBaEdfaOpticalInputPowerFailureAlarmThresholdMinimumValue		DisplayString,
				msaBaEdfaOpticalInputPowerFailureAlarmThresholdMaximumValue		DisplayString,
				msaBaEdfaHighOpticalInputPowerAlarmThreshold				DisplayString,
				msaBaEdfaHighOpticalInputPowerAlarmThresholdMinimumValue		DisplayString,
				msaBaEdfaHighOpticalInputPowerAlarmThresholdMaximumValue		DisplayString,
				msaBaEdfaLowOpticalInputPowerAlarmThreshold				DisplayString,
				msaBaEdfaLowOpticalInputPowerAlarmThresholdMinimumValue			DisplayString,
				msaBaEdfaLowOpticalInputPowerAlarmThresholdMaximumValue			DisplayString,
				msaBaEdfaHighOpticalInputPowerWarningThreshold				DisplayString,
				msaBaEdfaHighOpticalInputPowerWarningThresholdMinimumValue		DisplayString,
				msaBaEdfaHighOpticalInputPowerWarningThresholdMaximumValue		DisplayString,
				msaBaEdfaLowOpticalInputPowerWarningThreshold				DisplayString,
				msaBaEdfaLowOpticalInputPowerWarningThresholdMinimumValue		DisplayString,
				msaBaEdfaLowOpticalInputPowerWarningThresholdMaximumValue		DisplayString,
				msaBaEdfaHighOpticalOutputPowerWarningThreshold				DisplayString,
				msaBaEdfaHighOpticalOutputPowerWarningThresholdMinimumValue		DisplayString,
				msaBaEdfaHighOpticalOutputPowerWarningThresholdMaximumValue		DisplayString,
				msaBaEdfaLowOpticalOutputPowerWarningThreshold				DisplayString,
				msaBaEdfaLowOpticalOutputPowerWarningThresholdMinimumValue		DisplayString,
				msaBaEdfaLowOpticalOutputPowerWarningThresholdMaximumValue		DisplayString,
				msaBaEdfaOpticalOutputPowerFailureAlarmThreshold			DisplayString,
				msaBaEdfaOpticalOutputPowerFailureAlarmThresholdMinimumValue		DisplayString,
				msaBaEdfaOpticalOutputPowerFailureAlarmThresholdMaximumValue		DisplayString,
				msaBaEdfaHighOpticalOutputPowerAlarmThreshold				DisplayString,
				msaBaEdfaHighOpticalOutputPowerAlarmThresholdMinimumValue		DisplayString,
				msaBaEdfaHighOpticalOutputPowerAlarmThresholdMaximumValue		DisplayString,
				msaBaEdfaLowOpticalOutputPowerAlarmThreshold				DisplayString,
				msaBaEdfaLowOpticalOutputPowerAlarmThresholdMinimumValue		DisplayString,
				msaBaEdfaLowOpticalOutputPowerAlarmThresholdMaximumValue		DisplayString,
				msaBaEdfaHighTemperatureAlarmThreshold					DisplayString,
				msaBaEdfaHighTemperatureAlarmThresholdMinimumValue			DisplayString,
				msaBaEdfaHighTemperatureAlarmThresholdMaximumValue			DisplayString,
				msaBaEdfaLowTemperatureAlarmThreshold					DisplayString,
				msaBaEdfaLowTemperatureAlarmThresholdMinimumValue			DisplayString,
				msaBaEdfaLowTemperatureAlarmThresholdMaximumValue			DisplayString,
				msaBaEdfaHighTemperatureWarningThreshold				DisplayString,
				msaBaEdfaHighTemperatureWarningThresholdMinimumValue			DisplayString,
				msaBaEdfaHighTemperatureWarningThresholdMaximumValue			DisplayString,
				msaBaEdfaLowTemperatureWarningThreshold					DisplayString,
				msaBaEdfaLowTemperatureWarningThresholdMinimumValue			DisplayString,
				msaBaEdfaLowTemperatureWarningThresholdMaximumValue			DisplayString,
				msaBaEdfaHighOperatingCurrentAlarmThreshold				DisplayString,
				msaBaEdfaHighOperatingCurrentAlarmThresholdMinimumValue			DisplayString,
				msaBaEdfaHighOperatingCurrentAlarmThresholdMaximumValue			DisplayString,
				msaBaEdfaLowOperatingCurrentAlarmThreshold				DisplayString,
				msaBaEdfaLowOperatingCurrentAlarmThresholdMinimumValue			DisplayString,
				msaBaEdfaLowOperatingCurrentAlarmThresholdMaximumValue			DisplayString,
				msaBaEdfaHighOperatingCurrentWarningThreshold				DisplayString,
				msaBaEdfaHighOperatingCurrentWarningThresholdMinimumValue		DisplayString,
				msaBaEdfaHighOperatingCurrentWarningThresholdMaximumValue		DisplayString,
				msaBaEdfaLowOperatingCurrentWarningThreshold				DisplayString,
				msaBaEdfaLowOperatingCurrentWarningThresholdMinimumValue		DisplayString,
				msaBaEdfaLowOperatingCurrentWarningThresholdMaximumValue		DisplayString,
				msaBaEdfaHighTECCurrentAlarmThreshold					DisplayString,
				msaBaEdfaHighTECCurrentAlarmThresholdMinimumValue			DisplayString,
				msaBaEdfaHighTECCurrentAlarmThresholdMaximumValue			DisplayString,
				msaBaEdfaLowTECCurrentAlarmThreshold					DisplayString,
				msaBaEdfaLowTECCurrentAlarmThresholdMinimumValue			DisplayString,
				msaBaEdfaLowTECCurrentAlarmThresholdMaximumValue			DisplayString,
				msaBaEdfaHighTECCurrentWarningThreshold					DisplayString,
				msaBaEdfaHighTECCurrentWarningThresholdMinimumValue			DisplayString,
				msaBaEdfaHighTECCurrentWarningThresholdMaximumValue			DisplayString,
				msaBaEdfaLowTECCurrentWarningThreshold					DisplayString,
				msaBaEdfaLowTECCurrentWarningThresholdMinimumValue			DisplayString,
				msaBaEdfaLowTECCurrentWarningThresholdMaximumValue			DisplayString,
				msaBaEdfaVoaHighInputPowerAlarmThreshold				DisplayString,
				msaBaEdfaVoaHighInputPowerAlarmThresholdMinimumValue			DisplayString,
				msaBaEdfaVoaHighInputPowerAlarmThresholdMaximumValue			DisplayString,
				msaBaEdfaVoaLowInputPowerAlarmThreshold					DisplayString,
				msaBaEdfaVoaLowInputPowerAlarmThresholdMinimumValue			DisplayString,
				msaBaEdfaVoaLowInputPowerAlarmThresholdMaximumValue			DisplayString,
				msaBaEdfaVoaHighInputPowerWarningThreshold				DisplayString,
				msaBaEdfaVoaHighInputPowerWarningThresholdMinimumValue			DisplayString,
				msaBaEdfaVoaHighInputPowerWarningThresholdMaximumValue			DisplayString,
				msaBaEdfaVoaLowInputPowerWarningThreshold				DisplayString,
				msaBaEdfaVoaLowInputPowerWarningThresholdMinimumValue			DisplayString,
				msaBaEdfaVoaLowInputPowerWarningThresholdMaximumValue			DisplayString,
				msaBaEdfaModuleInputOpticalPowerLowAlarmThreshold			DisplayString,
				msaBaEdfaModuleInputOpticalPowerLowAlarmThresholdMinimumValue		DisplayString,
				msaBaEdfaModuleInputOpticalPowerLowAlarmThresholdMaximumValue		DisplayString,
				msaBaEdfaModuleInputOpticalPowerHighAlarmThreshold			DisplayString,
				msaBaEdfaModuleInputOpticalPowerHighAlarmThresholdMinimumValue		DisplayString,
				msaBaEdfaModuleInputOpticalPowerHighAlarmThresholdMaximumValue		DisplayString,
				msaBaEdfaModuleOutputOpticalPowerFailureAlarmThreshold			DisplayString,
				msaBaEdfaModuleOutputOpticalPowerFailureAlarmThresholdMinimumValue	DisplayString,
				msaBaEdfaModuleOutputOpticalPowerFailureAlarmThresholdMaximumValue	DisplayString,
				msaBaEdfaModuleInputAlarmThreshold					DisplayString,
				msaBaEdfaModuleInputAlarmThresholdMinimumValue				DisplayString,
				msaBaEdfaModuleInputAlarmThresholdMaximumValue				DisplayString,
				msaEdfaCardSoftwareUpgrade						DisplayString,
				msaPaEdfaOpticalInputPowerFailureAlarmInhibit				INTEGER,
				msaPaEdfaOpticalOutputPowerFailureAlarmInhibit				INTEGER,
				msaPaEdfaLowOpticalInputPowerAlarmInhibit				INTEGER,
				msaPaEdfaHighOpticalInputPowerAlarmInhibit				INTEGER,
				msaPaEdfaLowOpticalOutputPowerAlarmInhibit				INTEGER,
				msaPaEdfaHighOpticalOutputPowerAlarmInhibit				INTEGER,
				msaPaEdfaLowTemperatureAlarmInhibit					INTEGER,
				msaPaEdfaHighTemperatureAlarmInhibit					INTEGER,
				msaPaEdfaLowOperatingCurrentAlarmInhibit				INTEGER,
				msaPaEdfaHighOperatingCurrentAlarmInhibit				INTEGER,
				msaPaEdfaLowTECCurrentAlarmInhibit					INTEGER,
				msaPaEdfaHighTECCurrentAlarmInhibit					INTEGER,
				msaPaEdfaLowVoaInputPowerAlarmInhibit					INTEGER,
				msaPaEdfaHighVoaInputPowerAlarmInhibit					INTEGER,
				msaPaEdfaInputOutOfRangeAlarmInhibit					INTEGER,
				msaPaEdfaOutputOutOfRangeAlarmInhibit					INTEGER,
				msaPaEdfaModuleCommunicationAlarmInhibit				INTEGER,
				msaPaEdfaOpticalInputPowerFailureWarningInhibit				INTEGER,
				msaPaEdfaOpticalOutputPowerFailureWarningInhibit			INTEGER,
				msaPaEdfaLowOpticalInputPowerWarningInhibit				INTEGER,
				msaPaEdfaHighOpticalInputPowerWarningInhibit				INTEGER,
				msaPaEdfaLowOpticalOutputPowerWarningInhibit				INTEGER,
				msaPaEdfaHighOpticalOutputPowerWarningInhibit				INTEGER,
				msaPaEdfaLowTemperatureWarningInhibit					INTEGER,
				msaPaEdfaHighTemperatureWarningInhibit					INTEGER,
				msaPaEdfaLowOperatingCurrentWarningInhibit				INTEGER,
				msaPaEdfaHighOperatingCurrentWarningInhibit				INTEGER,
				msaPaEdfaLowTECCurrentWarningInhibit					INTEGER,
				msaPaEdfaHighTECCurrentWarningInhibit					INTEGER,
				msaPaEdfaLowVoaInputPowerWarningInhibit					INTEGER,
				msaPaEdfaHighVoaInputPowerWarningInhibit				INTEGER,
				msaPaEdfaInputOutOfRangeWarningInhibit					INTEGER,
				msaPaEdfaOutputOutOfRangeWarningInhibit					INTEGER,
				msaPaEdfaModuleCommunicationWarningInhibit				INTEGER,
				msaBaEdfaOpticalInputPowerFailureAlarmInhibit				INTEGER,
				msaBaEdfaOpticalOutputPowerFailureAlarmInhibit				INTEGER,
				msaBaEdfaLowOpticalInputPowerAlarmInhibit				INTEGER,
				msaBaEdfaHighOpticalInputPowerAlarmInhibit				INTEGER,
				msaBaEdfaLowOpticalOutputPowerAlarmInhibit				INTEGER,
				msaBaEdfaHighOpticalOutputPowerAlarmInhibit				INTEGER,
				msaBaEdfaLowTemperatureAlarmInhibit					INTEGER,
				msaBaEdfaHighTemperatureAlarmInhibit					INTEGER,
				msaBaEdfaLowOperatingCurrentAlarmInhibit				INTEGER,
				msaBaEdfaHighOperatingCurrentAlarmInhibit				INTEGER,
				msaBaEdfaLowTECCurrentAlarmInhibit					INTEGER,
				msaBaEdfaHighTECCurrentAlarmInhibit					INTEGER,
				msaBaEdfaLowVoaInputPowerAlarmInhibit					INTEGER,
				msaBaEdfaHighVoaInputPowerAlarmInhibit					INTEGER,
				msaBaEdfaInputOutOfRangeAlarmInhibit					INTEGER,
				msaBaEdfaOutputOutOfRangeAlarmInhibit					INTEGER,
				msaBaEdfaModuleCommunicationAlarmInhibit				INTEGER,
				msaBaEdfaOpticalInputPowerFailureWarningInhibit				INTEGER,
				msaBaEdfaOpticalOutputPowerFailureWarningInhibit			INTEGER,
				msaBaEdfaLowOpticalInputPowerWarningInhibit				INTEGER,
				msaBaEdfaHighOpticalInputPowerWarningInhibit				INTEGER,
				msaBaEdfaLowOpticalOutputPowerWarningInhibit				INTEGER,
				msaBaEdfaHighOpticalOutputPowerWarningInhibit				INTEGER,
				msaBaEdfaLowTemperatureWarningInhibit					INTEGER,
				msaBaEdfaHighTemperatureWarningInhibit					INTEGER,
				msaBaEdfaLowOperatingCurrentWarningInhibit				INTEGER,
				msaBaEdfaHighOperatingCurrentWarningInhibit				INTEGER,
				msaBaEdfaLowTECCurrentWarningInhibit					INTEGER,
				msaBaEdfaHighTECCurrentWarningInhibit					INTEGER,
				msaBaEdfaLowVoaInputPowerWarningInhibit					INTEGER,
				msaBaEdfaHighVoaInputPowerWarningInhibit				INTEGER,
				msaBaEdfaInputOutOfRangeWarningInhibit					INTEGER,
				msaBaEdfaOutputOutOfRangeWarningInhibit					INTEGER,
				msaBaEdfaModuleCommunicationWarningInhibit				INTEGER,
				msaPaEdfaOpticalInputPowerFailureAlarmSeverity				DisplayString,
				msaPaEdfaOpticalOutputPowerFailureAlarmSeverity				DisplayString,
				msaPaEdfaLowOpticalInputPowerAlarmSeverity				DisplayString,
				msaPaEdfaHighOpticalInputPowerAlarmSeverity				DisplayString,
				msaPaEdfaLowOpticalOutputPowerAlarmSeverity				DisplayString,
				msaPaEdfaHighOpticalOutputPowerAlarmSeverity				DisplayString,
				msaPaEdfaLowTemperatureAlarmSeverity					DisplayString,
				msaPaEdfaHighTemperatureAlarmSeverity					DisplayString,
				msaPaEdfaLowOperatingCurrentAlarmSeverity				DisplayString,
				msaPaEdfaHighOperatingCurrentAlarmSeverity				DisplayString,
				msaPaEdfaLowTECCurrentAlarmSeverity					DisplayString,
				msaPaEdfaHighTECCurrentAlarmSeverity					DisplayString,
				msaPaEdfaLowVoaInputPowerAlarmSeverity					DisplayString,
				msaPaEdfaHighVoaInputPowerAlarmSeverity					DisplayString,
				msaPaEdfaInputOutOfRangeAlarmSeverity					DisplayString,
				msaPaEdfaOutputOutOfRangeAlarmSeverity					DisplayString,
				msaPaEdfaModuleCommunicationAlarmSeverity				DisplayString,
				msaPaEdfaOpticalInputPowerFailureWarningSeverity			DisplayString,
				msaPaEdfaOpticalOutputPowerFailureWarningSeverity			DisplayString,
				msaPaEdfaLowOpticalInputPowerWarningSeverity				DisplayString,
				msaPaEdfaHighOpticalInputPowerWarningSeverity				DisplayString,
				msaPaEdfaLowOpticalOutputPowerWarningSeverity				DisplayString,
				msaPaEdfaHighOpticalOutputPowerWarningSeverity				DisplayString,
				msaPaEdfaLowTemperatureWarningSeverity					DisplayString,
				msaPaEdfaHighTemperatureWarningSeverity					DisplayString,
				msaPaEdfaLowOperatingCurrentWarningSeverity				DisplayString,
				msaPaEdfaHighOperatingCurrentWarningSeverity				DisplayString,
				msaPaEdfaLowTECCurrentWarningSeverity					DisplayString,
				msaPaEdfaHighTECCurrentWarningSeverity					DisplayString,
				msaPaEdfaLowVoaInputPowerWarningSeverity				DisplayString,
				msaPaEdfaHighVoaInputPowerWarningSeverity				DisplayString,
				msaPaEdfaInputOutOfRangeWarningSeverity					DisplayString,
				msaPaEdfaOutputOutOfRangeWarningSeverity				DisplayString,
				msaPaEdfaModuleCommunicationWarningSeverity				DisplayString,
				msaBaEdfaOpticalInputPowerFailureAlarmSeverity				DisplayString,
				msaBaEdfaOpticalOutputPowerFailureAlarmSeverity				DisplayString,
				msaBaEdfaLowOpticalInputPowerAlarmSeverity				DisplayString,
				msaBaEdfaHighOpticalInputPowerAlarmSeverity				DisplayString,
				msaBaEdfaLowOpticalOutputPowerAlarmSeverity				DisplayString,
				msaBaEdfaHighOpticalOutputPowerAlarmSeverity				DisplayString,
				msaBaEdfaLowTemperatureAlarmSeverity					DisplayString,
				msaBaEdfaHighTemperatureAlarmSeverity					DisplayString,
				msaBaEdfaLowOperatingCurrentAlarmSeverity				DisplayString,
				msaBaEdfaHighOperatingCurrentAlarmSeverity				DisplayString,
				msaBaEdfaLowTECCurrentAlarmSeverity					DisplayString,
				msaBaEdfaHighTECCurrentAlarmSeverity					DisplayString,
				msaBaEdfaLowVoaInputPowerAlarmSeverity					DisplayString,
				msaBaEdfaHighVoaInputPowerAlarmSeverity					DisplayString,
				msaBaEdfaInputOutOfRangeAlarmSeverity					DisplayString,
				msaBaEdfaOutputOutOfRangeAlarmSeverity					DisplayString,
				msaBaEdfaModuleCommunicationAlarmSeverity				DisplayString,
				msaBaEdfaOpticalInputPowerFailureWarningSeverity			DisplayString,
				msaBaEdfaOpticalOutputPowerFailureWarningSeverity			DisplayString,
				msaBaEdfaLowOpticalInputPowerWarningSeverity				DisplayString,
				msaBaEdfaHighOpticalInputPowerWarningSeverity				DisplayString,
				msaBaEdfaLowOpticalOutputPowerWarningSeverity				DisplayString,
				msaBaEdfaHighOpticalOutputPowerWarningSeverity				DisplayString,
				msaBaEdfaLowTemperatureWarningSeverity					DisplayString,
				msaBaEdfaHighTemperatureWarningSeverity					DisplayString,
				msaBaEdfaLowOperatingCurrentWarningSeverity				DisplayString,
				msaBaEdfaHighOperatingCurrentWarningSeverity				DisplayString,
				msaBaEdfaLowTECCurrentWarningSeverity					DisplayString,
				msaBaEdfaHighTECCurrentWarningSeverity					DisplayString,
				msaBaEdfaLowVoaInputPowerWarningSeverity				DisplayString,
				msaBaEdfaHighVoaInputPowerWarningSeverity				DisplayString,
				msaBaEdfaInputOutOfRangeWarningSeverity					DisplayString,
				msaBaEdfaOutputOutOfRangeWarningSeverity				DisplayString,
				msaBaEdfaModuleCommunicationWarningSeverity				DisplayString,
				msaEdfaConfigurationTableRowStatus					RowStatus
			}
		
	msaEdfaCardSoftReset OBJECT-TYPE
		SYNTAX  	INTEGER
		MAX-ACCESS  	read-write
		STATUS  	current

		DESCRIPTION
		"Valid only as a SET command.
		Reboots the Card, Reconfigures the Card 
		i.e All Configuration Parameter	like Laser State,
		thresholds, operating mode & gain will be restored to 
		previous state.
		-----------------------------
		Values:
		Dont care, any value
		eg: 0
		-----------------------------"

		::= { msaEdfaConfigurationEntry 1 }		
	
	msaEdfaCardDefaultFactoryReset OBJECT-TYPE
		SYNTAX  	INTEGER
		MAX-ACCESS  	read-write
		STATUS  	current

		DESCRIPTION
		"Valid only as a SET command.
		Sets the Card To Factory Default State
		i.e All Configuration Parameter	like Laser State,
		thresholds, operating mode & gain will be set to 
		default state. "

		::= { msaEdfaConfigurationEntry 2 }

	msaEdfaAlarmMonitoringStatus OBJECT-TYPE
		SYNTAX  	INTEGER
		MAX-ACCESS  	read-write
		STATUS  	current

		DESCRIPTION
		"This property sets or gets the card's Alarm
		monitoring state. Disabling card alarm monitoring 
		will not provide any alarms and performances
		information to the user.
		-----------------------------
		Values:
		1 - Card Alarm Monitoring is enabled
		0 - Card Alarm Monitoring is disabled
		-----------------------------"

		::= { msaEdfaConfigurationEntry 3 }

  	msaEdfaSystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { msaEdfaConfigurationEntry 5 }
  		
  	msaEdfaSyncRtcWithNtpServer	 OBJECT-TYPE
		SYNTAX  		DisplayString
  		MAX-ACCESS  		read-write
  		STATUS  		current
  		DESCRIPTION	 	"When we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 10.254.254.254
							
						If we don't want to provide NTP server address, then no
						need to pass any value. 
						---------------------------"
  						
  		::= { msaEdfaConfigurationEntry 6 }
  		
  	msaEdfaSyncRtcWithSystemTime	 OBJECT-TYPE
		SYNTAX  		INTEGER
  		MAX-ACCESS  	read-write
  		STATUS  		current
  		DESCRIPTION	 	" when we want to manually sync the time value
  						present in RTC with the time value in linux kernel
  						we can use this OID. With this set operation, 
  						the time available with linux kernel will be updated
  						into RTC. The value should be :
  						1"
  						
  		::= { msaEdfaConfigurationEntry 7 }

	msaEdfaSyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that particular server. 
					If we are not providing NTP server IP address 
					then the system will be synced with the NTP server 
					which is already been registered with card. 
					If both are absent then error message will be returned
					-----------------------------
						Interface : 0
					-----------------------------
						If we want to provide NTP server IP address then
						Value should be a valid IP address as shown below
						: 10.254.254.254
						
						If we don't want to provide NTP server address then no
						need to pass any value. 
					---------------------------"
  						
  		::= { msaEdfaConfigurationEntry 8 }

  	msaEdfaUpdateGivenTimeIntoRtc	 OBJECT-TYPE
		SYNTAX  		DisplayString
  		MAX-ACCESS  		read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD HH:MM:SS
						
						Example: 2019-03-31 15:20:44
						---------------------------"
						
  		::= { msaEdfaConfigurationEntry 9 }

  		  		
  	msaEdfaUpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2019-03-31 15:20:44
						---------------------------"
						
  		::= { msaEdfaConfigurationEntry 10 }
  		  		
	msaPaEdfaModulePumpLaserStatus OBJECT-TYPE
		SYNTAX  	INTEGER
		MAX-ACCESS  	read-write
		STATUS  	current

		DESCRIPTION
		 " to set/get MSA PA EDFA card pump laser status.
		-----------------------------
		Values:
		1 - Laser ON
		0 - Laser OFF
		-----------------------------"

		::= { msaEdfaConfigurationEntry 11 }

	msaPaEdfaModuleAutomaticLaserShutdownStatusForStage1 OBJECT-TYPE
		SYNTAX  	INTEGER
		MAX-ACCESS  	read-write
		STATUS  	current

		DESCRIPTION
		 " to set/get MSA PA EDFA card automatic laser shutdown status 
		-----------------------------
		Values:
		1 - Automatic laser shutdown function ON
		0 - Automatic laser shutdown function OFF
		-----------------------------"

		::= { msaEdfaConfigurationEntry 12 }

	msaPaEdfaModuleOperatingMode	OBJECT-TYPE
		SYNTAX  	DisplayString (SIZE (0..255))
		MAX-ACCESS  	read-write
		STATUS  	current

		DESCRIPTION
		 "To set/get MSA PA EDFA card module operating mode.
		-----------------------------
		Values:
		APC - Automatic power control mode
		AGC - Automatic gain control mode
		ACC - Automatic current control mode
		-----------------------------"

		::= { msaEdfaConfigurationEntry 13 }
      
	msaPaEdfaModuleGainInAutomaticGainControlMode OBJECT-TYPE
		SYNTAX  	DisplayString (SIZE (0..255))
		MAX-ACCESS  	read-write
		STATUS  	current

		DESCRIPTION
		 " to set/get MSA PA EDFA card module gain in automatic gain control mode 
		-----------------------------
		Values:
		eg. : 15.5
		-----------------------------"

		::= { msaEdfaConfigurationEntry 14 }
  
      	msaPaEdfaModuleGainTilt OBJECT-TYPE
		SYNTAX  	DisplayString (SIZE (0..255))
		MAX-ACCESS  	read-write
		STATUS  	current

		DESCRIPTION
		 " to set/get MSA PA EDFA card gain tilt.
		-----------------------------
		Values:
		eg. : 15.5
		-----------------------------"

		::= { msaEdfaConfigurationEntry 15 } 
		   
	msaPaEdfaModuleOpticalOutputPowerInAutomaticPowerControlMode OBJECT-TYPE
		SYNTAX  	DisplayString (SIZE (0..255))
		MAX-ACCESS  	read-write
		STATUS  	current

		DESCRIPTION
		 " to set/get MSA PA EDFA card module output power in automatic power control mode.
		-----------------------------
		Values:
		eg. : 15.5
		-----------------------------"

		::= { msaEdfaConfigurationEntry 16 }		
    
	msaPaEdfaModulePump1OperatingCurrentInAutomaticCurrentControlMode OBJECT-TYPE
		SYNTAX  	DisplayString (SIZE (0..255))
		MAX-ACCESS  	read-write
		STATUS  	current

		DESCRIPTION
		 " to set/get MSA PA EDFA card pump 1 operating current in automatic current control mode.
		-----------------------------
		Values:
		eg. : 15.5
		-----------------------------"

		::= { msaEdfaConfigurationEntry 17 }
      
	msaPaEdfaModuleVariableOpticalAttenuatorAttenuation OBJECT-TYPE
		SYNTAX  	DisplayString (SIZE (0..255))
		MAX-ACCESS  	read-write
		STATUS  	current

		DESCRIPTION
		 " to set/get MSA PA EDFA card variable optical attenuator attenuation.
		-----------------------------
		Values:
		eg. : 15.5
		-----------------------------"

		::= { msaEdfaConfigurationEntry 18 }	  		 

      	msaPaEdfaModuleResetOpticalAmplifier OBJECT-TYPE
		SYNTAX  	INTEGER
		MAX-ACCESS  	read-write
		STATUS  	current

		DESCRIPTION
		 " to reset MSA PA EDFA Optical Amplifier Module.
		-----------------------------
		Value: 1
		-----------------------------"

		::= { msaEdfaConfigurationEntry 19 } 

	msaBaEdfaModulePumpLaserStatus OBJECT-TYPE
		SYNTAX  	INTEGER
		MAX-ACCESS  	read-write
		STATUS  	current

		DESCRIPTION
		 " to set/get MSA PA EDFA card pump 1 laser status.
		-----------------------------
		Values:
		1 - Laser ON
		0 - Laser OFF
		-----------------------------"

		::= { msaEdfaConfigurationEntry 20 }

	msaBaEdfaModuleAutomaticLaserShutdownStatusForStage1 OBJECT-TYPE
		SYNTAX  	INTEGER
		MAX-ACCESS  	read-write
		STATUS  	current

		DESCRIPTION
		 " to set/get MSA PA EDFA card automatic laser shutdown status 
		-----------------------------
		Values:
		1 - Automatic laser shutdown function ON
		0 - Automatic laser shutdown function OFF
		-----------------------------"

		::= { msaEdfaConfigurationEntry 21 }

	msaBaEdfaModuleOperatingMode	OBJECT-TYPE
		SYNTAX  	DisplayString (SIZE (0..255))
		MAX-ACCESS  	read-write
		STATUS  	current

		DESCRIPTION
		 "To set/get MSA PA EDFA card module operating mode.
		-----------------------------
		Values:
		APC - Automatic power control mode
		AGC - Automatic gain control mode
		ACC - Automatic current control mode
		-----------------------------"

		::= { msaEdfaConfigurationEntry 22 }
      
	msaBaEdfaModuleOpticalOutputPowerInAutomaticPowerControlMode OBJECT-TYPE
		SYNTAX  	DisplayString (SIZE (0..255))
		MAX-ACCESS  	read-write
		STATUS  	current

		DESCRIPTION
		 " to set/get MSA PA EDFA card module output power in automatic power control mode.
		-----------------------------
		Values:
		eg. : 15.5
		-----------------------------"

		::= { msaEdfaConfigurationEntry 23 }		
    
	msaBaEdfaModulePump1OperatingCurrentInAutomaticCurrentControlMode OBJECT-TYPE
		SYNTAX  	DisplayString (SIZE (0..255))
		MAX-ACCESS  	read-write
		STATUS  	current

		DESCRIPTION
		 " to set/get MSA PA EDFA card pump 1 operating current in automatic current control mode.
		-----------------------------
		Values:
		eg. : 15.5
		-----------------------------"

		::= { msaEdfaConfigurationEntry 24 }
      
	msaBaEdfaModuleVariableOpticalAttenuatorAttenuation OBJECT-TYPE
		SYNTAX  	DisplayString (SIZE (0..255))
		MAX-ACCESS  	read-write
		STATUS  	current

		DESCRIPTION
		 " to set/get MSA PA EDFA card variable optical attenuator attenuation.
		-----------------------------
		Values:
		eg. : 15.5
		-----------------------------"

		::= { msaEdfaConfigurationEntry 25 }

	msaBaEdfaModuleResetOpticalAmplifier OBJECT-TYPE
		SYNTAX  	INTEGER
		MAX-ACCESS  	read-write
		STATUS  	current

		DESCRIPTION
		 " to reset MSA PA EDFA Optical Amplifier Module.
		-----------------------------
		Values: 1
		-----------------------------"

		::= { msaEdfaConfigurationEntry 26 } 

	msaPaEdfaOpticalInputPowerFailureAlarmThreshold OBJECT-TYPE
		SYNTAX			DisplayString
		MAX-ACCESS		read-write
		STATUS			current

		DESCRIPTION
		 "To set/get PA EDFA card optical input power failure alarm threshold.
		-----------------------------
		Values:
		eg. : -21.0
		-----------------------------"

		::= { msaEdfaConfigurationEntry 27 }

	msaPaEdfaOpticalInputPowerFailureAlarmThresholdMinimumValue OBJECT-TYPE
		SYNTAX			DisplayString
		MAX-ACCESS		read-write
		STATUS			current

		DESCRIPTION
		 "To set/get PA EDFA card optical input power failure alarm threshold minimum value.
		-----------------------------
		Values:
		eg. : -21.0
		-----------------------------"

		::= { msaEdfaConfigurationEntry 28 }


	msaPaEdfaOpticalInputPowerFailureAlarmThresholdMaximumValue OBJECT-TYPE
		SYNTAX			DisplayString
		MAX-ACCESS		read-write
		STATUS			current

		DESCRIPTION
		 "To set/get PA EDFA card optical input power failure alarm threshold maximum value.
		-----------------------------
		Values:
		eg. : -21.0
		-----------------------------"

		::= { msaEdfaConfigurationEntry 29 }

	msaPaEdfaHighOpticalInputPowerAlarmThreshold OBJECT-TYPE
		SYNTAX			DisplayString
		MAX-ACCESS		read-write
		STATUS			current

		DESCRIPTION
		 "To set/get PA EDFA card optical high input power alarm threshold.
		-----------------------------
		Values:
		eg. : 5.0
		-----------------------------"

		::= { msaEdfaConfigurationEntry 30 }

	msaPaEdfaHighOpticalInputPowerAlarmThresholdMinimumValue OBJECT-TYPE
		SYNTAX			DisplayString
		MAX-ACCESS		read-write
		STATUS			current

		DESCRIPTION
		 "To set/get PA EDFA card optical high input power alarm threshold minimum value.
		-----------------------------
		Values:
		eg. : 5.0
		-----------------------------"

		::= { msaEdfaConfigurationEntry 31 }

	msaPaEdfaHighOpticalInputPowerAlarmThresholdMaximumValue OBJECT-TYPE
		SYNTAX			DisplayString
		MAX-ACCESS		read-write
		STATUS			current

		DESCRIPTION
		 "To set/get PA EDFA card optical high input power alarm threshold maximum value.
		-----------------------------
		Values:
		eg. : 5.0
		-----------------------------"

		::= { msaEdfaConfigurationEntry 32 }

	msaPaEdfaLowOpticalInputPowerAlarmThreshold OBJECT-TYPE
		SYNTAX			DisplayString
		MAX-ACCESS		read-write
		STATUS			current

		DESCRIPTION
		 "To set/get PA EDFA card optical low input power alarm threshold.
		-----------------------------
		Values:
		eg. : -35.0
		-----------------------------"

		::= { msaEdfaConfigurationEntry 33 }

	msaPaEdfaLowOpticalInputPowerAlarmThresholdMinimumValue OBJECT-TYPE
		SYNTAX			DisplayString
		MAX-ACCESS		read-write
		STATUS			current

		DESCRIPTION
		 "To set/get PA EDFA card optical Low input power alarm threshold minimum value.
		-----------------------------
		Values:
		eg. : 5.0
		-----------------------------"

		::= { msaEdfaConfigurationEntry 34 }

	msaPaEdfaLowOpticalInputPowerAlarmThresholdMaximumValue OBJECT-TYPE
		SYNTAX			DisplayString
		MAX-ACCESS		read-write
		STATUS			current

		DESCRIPTION
		 "To set/get PA EDFA card optical Low input power alarm threshold maximum value.
		-----------------------------
		Values:
		eg. : 5.0
		-----------------------------"

		::= { msaEdfaConfigurationEntry 35 }

	msaPaEdfaHighOpticalInputPowerWarningThreshold OBJECT-TYPE
		SYNTAX			DisplayString
		MAX-ACCESS		read-write
		STATUS			current

		DESCRIPTION
		 "To set/get PA EDFA card optical high input power warning threshold.
		-----------------------------
		Values:
		eg. : 3.0
		-----------------------------"

		::= { msaEdfaConfigurationEntry 36 }

	msaPaEdfaHighOpticalInputPowerWarningThresholdMinimumValue OBJECT-TYPE
		SYNTAX			DisplayString
		MAX-ACCESS		read-write
		STATUS			current

		DESCRIPTION
		 "To set/get PA EDFA card optical high input power warning threshold Minimum Value.
		-----------------------------
		Values:
		eg. : 3.0
		-----------------------------"

		::= { msaEdfaConfigurationEntry 37 }

	msaPaEdfaHighOpticalInputPowerWarningThresholdMaximumValue OBJECT-TYPE
		SYNTAX			DisplayString
		MAX-ACCESS		read-write
		STATUS			current

		DESCRIPTION
		 "To set/get PA EDFA card optical high input power warning threshold Maximum Value.
		-----------------------------
		Values:
		eg. : 3.0
		-----------------------------"

		::= { msaEdfaConfigurationEntry 38 }

	msaPaEdfaLowOpticalInputPowerWarningThreshold OBJECT-TYPE
		SYNTAX			DisplayString
		MAX-ACCESS		read-write
		STATUS			current

		DESCRIPTION
		 "To set/get PA EDFA card optical high input power warning threshold.
		-----------------------------
		Values:
		eg. : 3.0
		-----------------------------"

		::= { msaEdfaConfigurationEntry 39 }

	msaPaEdfaLowOpticalInputPowerWarningThresholdMinimumValue OBJECT-TYPE
		SYNTAX			DisplayString
		MAX-ACCESS		read-write
		STATUS			current

		DESCRIPTION
		 "To set/get PA EDFA card optical low input power warning threshold Minimum Value.
		-----------------------------
		Values:
		eg. : 3.0
		-----------------------------"

		::= { msaEdfaConfigurationEntry 40 }

	msaPaEdfaLowOpticalInputPowerWarningThresholdMaximumValue OBJECT-TYPE
		SYNTAX			DisplayString
		MAX-ACCESS		read-write
		STATUS			current

		DESCRIPTION
		 "To set/get PA EDFA card optical low input power warning threshold Maximum Value.
		-----------------------------
		Values:
		eg. : 3.0
		-----------------------------"

		::= { msaEdfaConfigurationEntry 41 }

	msaPaEdfaHighOpticalOutputPowerWarningThreshold OBJECT-TYPE
		SYNTAX			DisplayString
		MAX-ACCESS		read-write
		STATUS			current

		DESCRIPTION
		 "To set/get PA EDFA card optical high output power warning threshold.
		-----------------------------
		Values:
		eg. : 3.0
		-----------------------------"

		::= { msaEdfaConfigurationEntry 42 }

	msaPaEdfaHighOpticalOutputPowerWarningThresholdMinimumValue OBJECT-TYPE
		SYNTAX			DisplayString
		MAX-ACCESS		read-write
		STATUS			current

		DESCRIPTION
		 "To set/get PA EDFA card optical high output power warning threshold Minimum Value.
		-----------------------------
		Values:
		eg. : 3.0
		-----------------------------"

		::= { msaEdfaConfigurationEntry 43 }

	msaPaEdfaHighOpticalOutputPowerWarningThresholdMaximumValue OBJECT-TYPE
		SYNTAX			DisplayString
		MAX-ACCESS		read-write
		STATUS			current

		DESCRIPTION
		 "To set/get PA EDFA card optical high output power warning threshold Maximum Value.
		-----------------------------
		Values:
		eg. : 3.0
		-----------------------------"

		::= { msaEdfaConfigurationEntry 44 }

	msaPaEdfaLowOpticalOutputPowerWarningThreshold OBJECT-TYPE
		SYNTAX			DisplayString
		MAX-ACCESS		read-write
		STATUS			current

		DESCRIPTION
		 "To set/get PA EDFA card optical high output power warning threshold.
		-----------------------------
		Values:
		eg. : 3.0
		-----------------------------"

		::= { msaEdfaConfigurationEntry 45 }

	msaPaEdfaLowOpticalOutputPowerWarningThresholdMinimumValue OBJECT-TYPE
		SYNTAX			DisplayString
		MAX-ACCESS		read-write
		STATUS			current

		DESCRIPTION
		 "To set/get PA EDFA card optical high output power warning threshold Minimum Value.
		-----------------------------
		Values:
		eg. : 3.0
		-----------------------------"

		::= { msaEdfaConfigurationEntry 46 }

	msaPaEdfaLowOpticalOutputPowerWarningThresholdMaximumValue OBJECT-TYPE
		SYNTAX			DisplayString
		MAX-ACCESS		read-write
		STATUS			current

		DESCRIPTION
		 "To set/get PA EDFA card optical high output power warning threshold Maximum Value.
		-----------------------------
		Values:
		eg. : 3.0
		-----------------------------"

		::= { msaEdfaConfigurationEntry 47 }

	msaPaEdfaOpticalOutputPowerFailureAlarmThreshold OBJECT-TYPE
		SYNTAX			DisplayString
		MAX-ACCESS		read-write
		STATUS			current

		DESCRIPTION
		 "To set/get PA EDFA card optical output power failure alarm threshold.
		-----------------------------
		Values:
		eg. : -35.0
		-----------------------------"

		::= { msaEdfaConfigurationEntry 48 }

	msaPaEdfaOpticalOutputPowerFailureAlarmThresholdMinimumValue OBJECT-TYPE
		SYNTAX			DisplayString
		MAX-ACCESS		read-write
		STATUS			current

		DESCRIPTION
		 "To set/get PA EDFA card optical Output power failure alarm threshold minimum value.
		-----------------------------
		Values:
		eg. : -21.0
		-----------------------------"

		::= { msaEdfaConfigurationEntry 49 }


	msaPaEdfaOpticalOutputPowerFailureAlarmThresholdMaximumValue OBJECT-TYPE
		SYNTAX			DisplayString
		MAX-ACCESS		read-write
		STATUS			current

		DESCRIPTION
		 "To set/get PA EDFA card optical Output power failure alarm threshold maximum value.
		-----------------------------
		Values:
		eg. : -21.0
		-----------------------------"

		::= { msaEdfaConfigurationEntry 50 }

	msaPaEdfaHighOpticalOutputPowerAlarmThreshold OBJECT-TYPE
		SYNTAX			DisplayString
		MAX-ACCESS		read-write
		STATUS			current

		DESCRIPTION
		 "To set/get PA EDFA card optical high output power alarm threshold.
		-----------------------------
		Values:
		eg. : 7.0
		-----------------------------"

		::= { msaEdfaConfigurationEntry 51 }

	msaPaEdfaHighOpticalOutputPowerAlarmThresholdMinimumValue OBJECT-TYPE
		SYNTAX			DisplayString
		MAX-ACCESS		read-write
		STATUS			current

		DESCRIPTION
		 "To set/get PA EDFA card optical high output power alarm threshold Minimum Value.
		-----------------------------
		Values:
		eg. : 7.0
		-----------------------------"

		::= { msaEdfaConfigurationEntry 52 }

	msaPaEdfaHighOpticalOutputPowerAlarmThresholdMaximumValue OBJECT-TYPE
		SYNTAX			DisplayString
		MAX-ACCESS		read-write
		STATUS			current

		DESCRIPTION
		 "To set/get PA EDFA card optical high output power alarm threshold Maximum Value.
		-----------------------------
		Values:
		eg. : 7.0
		-----------------------------"

		::= { msaEdfaConfigurationEntry 53 }

	msaPaEdfaLowOpticalOutputPowerAlarmThreshold OBJECT-TYPE
		SYNTAX			DisplayString
		MAX-ACCESS		read-write
		STATUS			current

		DESCRIPTION
		 "To set/get PA EDFA card optical low output power alarm threshold.
		-----------------------------
		Values:
		eg. : -1.0
		-----------------------------"

		::= { msaEdfaConfigurationEntry 54 }

	msaPaEdfaLowOpticalOutputPowerAlarmThresholdMinimumValue OBJECT-TYPE
		SYNTAX			DisplayString
		MAX-ACCESS		read-write
		STATUS			current

		DESCRIPTION
		 "To set/get PA EDFA card optical low output power alarm threshold Minimum VAlue.
		-----------------------------
		Values:
		eg. : -1.0
		-----------------------------"

		::= { msaEdfaConfigurationEntry 55 }

	msaPaEdfaLowOpticalOutputPowerAlarmThresholdMaximumValue OBJECT-TYPE
		SYNTAX			DisplayString
		MAX-ACCESS		read-write
		STATUS			current

		DESCRIPTION
		 "To set/get PA EDFA card optical low output power alarm threshold Maximum Value.
		-----------------------------
		Values:
		eg. : -1.0
		-----------------------------"

		::= { msaEdfaConfigurationEntry 56 }

	msaPaEdfaHighTemperatureAlarmThreshold OBJECT-TYPE
		SYNTAX			DisplayString
		MAX-ACCESS		read-write
		STATUS			current

		DESCRIPTION
		 "To set/get PA EDFA card high temperature alarm threshold.
		-----------------------------
		Values:
		eg. : 50.0
		-----------------------------"

		::= { msaEdfaConfigurationEntry 57 }

	msaPaEdfaHighTemperatureAlarmThresholdMinimumValue OBJECT-TYPE
		SYNTAX			DisplayString
		MAX-ACCESS		read-write
		STATUS			current

		DESCRIPTION
		 "To set/get PA EDFA card high temperature alarm threshold Minimum Value.
		-----------------------------
		Values:
		eg. : 50.0
		-----------------------------"

		::= { msaEdfaConfigurationEntry 58 }

	msaPaEdfaHighTemperatureAlarmThresholdMaximumValue OBJECT-TYPE
		SYNTAX			DisplayString
		MAX-ACCESS		read-write
		STATUS			current

		DESCRIPTION
		 "To set/get PA EDFA card high temperature alarm threshold Maximum Value.
		-----------------------------
		Values:
		eg. : 50.0
		-----------------------------"

		::= { msaEdfaConfigurationEntry 59 }

	msaPaEdfaLowTemperatureAlarmThreshold OBJECT-TYPE
		SYNTAX			DisplayString
		MAX-ACCESS		read-write
		STATUS			current

		DESCRIPTION
		 "To set/get PA EDFA card low temperature alarm threshold.
		-----------------------------
		Values:
		eg. : -2.0
		-----------------------------"

		::= { msaEdfaConfigurationEntry 60 }

	msaPaEdfaLowTemperatureAlarmThresholdMinimumValue OBJECT-TYPE
		SYNTAX			DisplayString
		MAX-ACCESS		read-write
		STATUS			current

		DESCRIPTION
		 "To set/get PA EDFA card Low temperature alarm threshold Minimum Value.
		-----------------------------
		Values:
		eg. : 50.0
		-----------------------------"

		::= { msaEdfaConfigurationEntry 61 }

	msaPaEdfaLowTemperatureAlarmThresholdMaximumValue OBJECT-TYPE
		SYNTAX			DisplayString
		MAX-ACCESS		read-write
		STATUS			current

		DESCRIPTION
		 "To set/get PA EDFA card Low temperature alarm threshold Maximum Value.
		-----------------------------
		Values:
		eg. : 50.0
		-----------------------------"

		::= { msaEdfaConfigurationEntry 62 }

	msaPaEdfaHighTemperatureWarningThreshold OBJECT-TYPE
		SYNTAX			DisplayString
		MAX-ACCESS		read-write
		STATUS			current

		DESCRIPTION
		 "To set/get PA EDFA card high temperature warning threshold.
		-----------------------------
		Values:
		eg. : 45.0
		-----------------------------"

		::= { msaEdfaConfigurationEntry 63 }

	msaPaEdfaHighTemperatureWarningThresholdMinimumValue OBJECT-TYPE
		SYNTAX			DisplayString
		MAX-ACCESS		read-write
		STATUS			current

		DESCRIPTION
		 "To set/get PA EDFA card high temperature Warning threshold Minimum Value.
		-----------------------------
		Values:
		eg. : 50.0
		-----------------------------"

		::= { msaEdfaConfigurationEntry 64 }

	msaPaEdfaHighTemperatureWarningThresholdMaximumValue OBJECT-TYPE
		SYNTAX			DisplayString
		MAX-ACCESS		read-write
		STATUS			current

		DESCRIPTION
		 "To set/get PA EDFA card high temperature Warning threshold Maximum Value.
		-----------------------------
		Values:
		eg. : 50.0
		-----------------------------"

		::= { msaEdfaConfigurationEntry 65 }

	msaPaEdfaLowTemperatureWarningThreshold OBJECT-TYPE
		SYNTAX			DisplayString
		MAX-ACCESS		read-write
		STATUS			current

		DESCRIPTION
		 "To set/get PA EDFA card low temperature warning threshold.
		-----------------------------
		Values:
		eg. : 5.0
		-----------------------------"

		::= { msaEdfaConfigurationEntry 66 }

	msaPaEdfaLowTemperatureWarningThresholdMinimumValue OBJECT-TYPE
		SYNTAX			DisplayString
		MAX-ACCESS		read-write
		STATUS			current

		DESCRIPTION
		 "To set/get PA EDFA card Low temperature Warning threshold Minimum Value.
		-----------------------------
		Values:
		eg. : 50.0
		-----------------------------"

		::= { msaEdfaConfigurationEntry 67 }

	msaPaEdfaLowTemperatureWarningThresholdMaximumValue OBJECT-TYPE
		SYNTAX			DisplayString
		MAX-ACCESS		read-write
		STATUS			current

		DESCRIPTION
		 "To set/get PA EDFA card Low temperature Warning threshold Maximum Value.
		-----------------------------
		Values:
		eg. : 50.0
		-----------------------------"

		::= { msaEdfaConfigurationEntry 68 }

	msaPaEdfaHighOperatingCurrentAlarmThreshold OBJECT-TYPE
		SYNTAX			DisplayString
		MAX-ACCESS		read-write
		STATUS			current

		DESCRIPTION
		 "To set/get PA EDFA card high operating current alarm threshold.
		-----------------------------
		Values:
		eg. : 700.0
		-----------------------------"

		::= { msaEdfaConfigurationEntry 69 }

	msaPaEdfaHighOperatingCurrentAlarmThresholdMinimumValue OBJECT-TYPE
		SYNTAX			DisplayString
		MAX-ACCESS		read-write
		STATUS			current

		DESCRIPTION
		 "To set/get PA EDFA card high operating current alarm threshold Minimum Value.
		-----------------------------
		Values:
		eg. : 700.0
		-----------------------------"

		::= { msaEdfaConfigurationEntry 70 }

	msaPaEdfaHighOperatingCurrentAlarmThresholdMaximumValue OBJECT-TYPE
		SYNTAX			DisplayString
		MAX-ACCESS		read-write
		STATUS			current

		DESCRIPTION
		 "To set/get PA EDFA card high operating current alarm threshold Maximum Value.
		-----------------------------
		Values:
		eg. : 700.0
		-----------------------------"

		::= { msaEdfaConfigurationEntry 71 }

	msaPaEdfaLowOperatingCurrentAlarmThreshold OBJECT-TYPE
		SYNTAX			DisplayString
		MAX-ACCESS		read-write
		STATUS			current

		DESCRIPTION
		 "To set/get PA EDFA card low operating current alarm threshold.
		-----------------------------
		Values:
		eg. : 300.0
		-----------------------------"

		::= { msaEdfaConfigurationEntry 72 }

	msaPaEdfaLowOperatingCurrentAlarmThresholdMinimumValue OBJECT-TYPE
		SYNTAX			DisplayString
		MAX-ACCESS		read-write
		STATUS			current

		DESCRIPTION
		 "To set/get PA EDFA card Low operating current alarm threshold Minimum Value.
		-----------------------------
		Values:
		eg. : 700.0
		-----------------------------"

		::= { msaEdfaConfigurationEntry 73 }

	msaPaEdfaLowOperatingCurrentAlarmThresholdMaximumValue OBJECT-TYPE
		SYNTAX			DisplayString
		MAX-ACCESS		read-write
		STATUS			current

		DESCRIPTION
		 "To set/get PA EDFA card Low operating current alarm threshold Maximum Value.
		-----------------------------
		Values:
		eg. : 700.0
		-----------------------------"

		::= { msaEdfaConfigurationEntry 74 }

	msaPaEdfaHighOperatingCurrentWarningThreshold OBJECT-TYPE
		SYNTAX			DisplayString
		MAX-ACCESS		read-write
		STATUS			current

		DESCRIPTION
		 "To set/get PA EDFA card high operating current warning threshold.
		-----------------------------
		Values:
		eg. : 690.0
		-----------------------------"

		::= { msaEdfaConfigurationEntry 75 }

	msaPaEdfaHighOperatingCurrentWarningThresholdMinimumValue OBJECT-TYPE
		SYNTAX			DisplayString
		MAX-ACCESS		read-write
		STATUS			current

		DESCRIPTION
		 "To set/get PA EDFA card high operating current Warning threshold Minimum Value.
		-----------------------------
		Values:
		eg. : 700.0
		-----------------------------"

		::= { msaEdfaConfigurationEntry 76 }

	msaPaEdfaHighOperatingCurrentWarningThresholdMaximumValue OBJECT-TYPE
		SYNTAX			DisplayString
		MAX-ACCESS		read-write
		STATUS			current

		DESCRIPTION
		 "To set/get PA EDFA card high operating current Warning threshold Maximum Value.
		-----------------------------
		Values:
		eg. : 700.0
		-----------------------------"

		::= { msaEdfaConfigurationEntry 77 }

	msaPaEdfaLowOperatingCurrentWarningThreshold OBJECT-TYPE
		SYNTAX			DisplayString
		MAX-ACCESS		read-write
		STATUS			current

		DESCRIPTION
		 "To set/get PA EDFA card low operating current warning threshold.
		-----------------------------
		Values:
		eg. : 310.0
		-----------------------------"

		::= { msaEdfaConfigurationEntry 78 }

	msaPaEdfaLowOperatingCurrentWarningThresholdMinimumValue OBJECT-TYPE
		SYNTAX			DisplayString
		MAX-ACCESS		read-write
		STATUS			current

		DESCRIPTION
		 "To set/get PA EDFA card Low operating current Warning threshold Minimum Value.
		-----------------------------
		Values:
		eg. : 700.0
		-----------------------------"

		::= { msaEdfaConfigurationEntry 79 }

	msaPaEdfaLowOperatingCurrentWarningThresholdMaximumValue OBJECT-TYPE
		SYNTAX			DisplayString
		MAX-ACCESS		read-write
		STATUS			current

		DESCRIPTION
		 "To set/get PA EDFA card Low operating current Warning threshold Maximum Value.
		-----------------------------
		Values:
		eg. : 700.0
		-----------------------------"

		::= { msaEdfaConfigurationEntry 80 }

	msaPaEdfaHighTECCurrentAlarmThreshold OBJECT-TYPE
		SYNTAX			DisplayString
		MAX-ACCESS		read-write
		STATUS			current

		DESCRIPTION
		 "To set/get PA EDFA card high TEC current alarm threshold.
		-----------------------------
		Values:
		eg. : 700.0
		-----------------------------"

		::= { msaEdfaConfigurationEntry 81 }

	msaPaEdfaHighTECCurrentAlarmThresholdMinimumValue OBJECT-TYPE
		SYNTAX			DisplayString
		MAX-ACCESS		read-write
		STATUS			current

		DESCRIPTION
		 "To set/get PA EDFA card high TEC current alarm threshold Minimum Value.
		-----------------------------
		Values:
		eg. : 700.0
		-----------------------------"

		::= { msaEdfaConfigurationEntry 82 }

	msaPaEdfaHighTECCurrentAlarmThresholdMaximumValue OBJECT-TYPE
		SYNTAX			DisplayString
		MAX-ACCESS		read-write
		STATUS			current

		DESCRIPTION
		 "To set/get PA EDFA card high TEC current alarm threshold Maximum Value.
		-----------------------------
		Values:
		eg. : 700.0
		-----------------------------"

		::= { msaEdfaConfigurationEntry 83 }

	msaPaEdfaLowTECCurrentAlarmThreshold OBJECT-TYPE
		SYNTAX			DisplayString
		MAX-ACCESS		read-write
		STATUS			current

		DESCRIPTION
		 "To set/get PA EDFA card low TEC current alarm threshold.
		-----------------------------
		Values:
		eg. : 300.0
		-----------------------------"

		::= { msaEdfaConfigurationEntry 84 }

	msaPaEdfaLowTECCurrentAlarmThresholdMinimumValue OBJECT-TYPE
		SYNTAX			DisplayString
		MAX-ACCESS		read-write
		STATUS			current

		DESCRIPTION
		 "To set/get PA EDFA card low TEC current alarm threshold Minimum Value.
		-----------------------------
		Values:
		eg. : 300.0
		-----------------------------"

		::= { msaEdfaConfigurationEntry 85 }

	msaPaEdfaLowTECCurrentAlarmThresholdMaximumValue OBJECT-TYPE
		SYNTAX			DisplayString
		MAX-ACCESS		read-write
		STATUS			current

		DESCRIPTION
		 "To set/get PA EDFA card low TEC current alarm threshold Maximum Value.
		-----------------------------
		Values:
		eg. : 300.0
		-----------------------------"

		::= { msaEdfaConfigurationEntry 86 }

	msaPaEdfaHighTECCurrentWarningThreshold OBJECT-TYPE
		SYNTAX			DisplayString
		MAX-ACCESS		read-write
		STATUS			current

		DESCRIPTION
		 "To set/get PA EDFA card high TEC current warning threshold.
		-----------------------------
		Values:
		eg. : 700.0
		-----------------------------"

		::= { msaEdfaConfigurationEntry 87 }

	msaPaEdfaHighTECCurrentWarningThresholdMinimumValue OBJECT-TYPE
		SYNTAX			DisplayString
		MAX-ACCESS		read-write
		STATUS			current

		DESCRIPTION
		 "To set/get PA EDFA card high TEC current warning threshold Minimum Value.
		-----------------------------
		Values:
		eg. : 700.0
		-----------------------------"

		::= { msaEdfaConfigurationEntry 88 }

	msaPaEdfaHighTECCurrentWarningThresholdMaximumValue OBJECT-TYPE
		SYNTAX			DisplayString
		MAX-ACCESS		read-write
		STATUS			current

		DESCRIPTION
		 "To set/get PA EDFA card high TEC current warning threshold Maximum Value.
		-----------------------------
		Values:
		eg. : 700.0
		-----------------------------"

		::= { msaEdfaConfigurationEntry 89 }

	msaPaEdfaLowTECCurrentWarningThreshold OBJECT-TYPE
		SYNTAX			DisplayString
		MAX-ACCESS		read-write
		STATUS			current

		DESCRIPTION
		 "To set/get PA EDFA card low TEC current warning threshold.
		-----------------------------
		Values:
		eg. : 300.0
		-----------------------------"

		::= { msaEdfaConfigurationEntry 90 }

	msaPaEdfaLowTECCurrentWarningThresholdMinimumValue OBJECT-TYPE
		SYNTAX			DisplayString
		MAX-ACCESS		read-write
		STATUS			current

		DESCRIPTION
		 "To set/get PA EDFA card low TEC current warning threshold minimum Value.
		-----------------------------
		Values:
		eg. : 300.0
		-----------------------------"

		::= { msaEdfaConfigurationEntry 91 }

	msaPaEdfaLowTECCurrentWarningThresholdMaximumValue OBJECT-TYPE
		SYNTAX			DisplayString
		MAX-ACCESS		read-write
		STATUS			current

		DESCRIPTION
		 "To set/get PA EDFA card low TEC current warning threshold Maximum Value.
		-----------------------------
		Values:
		eg. : 300.0
		-----------------------------"

		::= { msaEdfaConfigurationEntry 92 }

	msaPaEdfaVoaHighInputPowerAlarmThreshold OBJECT-TYPE
		SYNTAX			DisplayString
		MAX-ACCESS		read-write
		STATUS			current

		DESCRIPTION
		 "To set/get PA EDFA VOA high Input Power alarm threshold.
		-----------------------------
		Values:
		eg. : 7.0
		-----------------------------"

		::= { msaEdfaConfigurationEntry 93 }

	msaPaEdfaVoaHighInputPowerAlarmThresholdMinimumValue OBJECT-TYPE
		SYNTAX			DisplayString
		MAX-ACCESS		read-write
		STATUS			current

		DESCRIPTION
		 "To set/get PA EDFA VOA high Input Power alarm threshold Minimum Value.
		-----------------------------
		Values:
		eg. : 7.0
		-----------------------------"

		::= { msaEdfaConfigurationEntry 94 }

	msaPaEdfaVoaHighInputPowerAlarmThresholdMaximumValue OBJECT-TYPE
		SYNTAX			DisplayString
		MAX-ACCESS		read-write
		STATUS			current

		DESCRIPTION
		 "To set/get PA EDFA VOA high Input Power alarm threshold Maximum Value.
		-----------------------------
		Values:
		eg. : 7.0
		-----------------------------"

		::= { msaEdfaConfigurationEntry 95 }

	msaPaEdfaVoaLowInputPowerAlarmThreshold OBJECT-TYPE
		SYNTAX			DisplayString
		MAX-ACCESS		read-write
		STATUS			current

		DESCRIPTION
		 "To set/get PA EDFA VOA low Input Power alarm threshold.
		-----------------------------
		Values:
		eg. : -25.0
		-----------------------------"

		::= { msaEdfaConfigurationEntry 96 }

	msaPaEdfaVoaLowInputPowerAlarmThresholdMinimumValue OBJECT-TYPE
		SYNTAX			DisplayString
		MAX-ACCESS		read-write
		STATUS			current

		DESCRIPTION
		 "To set/get PA EDFA VOA low Input Power alarm threshold Minimum Value.
		-----------------------------
		Values:
		eg. : -25.0
		-----------------------------"

		::= { msaEdfaConfigurationEntry 97 }

	msaPaEdfaVoaLowInputPowerAlarmThresholdMaximumValue OBJECT-TYPE
		SYNTAX			DisplayString
		MAX-ACCESS		read-write
		STATUS			current

		DESCRIPTION
		 "To set/get PA EDFA VOA low Input Power alarm threshold Maximum Value.
		-----------------------------
		Values:
		eg. : -25.0
		-----------------------------"

		::= { msaEdfaConfigurationEntry 98 }

	msaPaEdfaVoaHighInputPowerWarningThreshold OBJECT-TYPE
		SYNTAX			DisplayString
		MAX-ACCESS		read-write
		STATUS			current

		DESCRIPTION
		 "To set/get PA EDFA VOA high Input Power warning threshold.
		-----------------------------
		Values:
		eg. : 6.0
		-----------------------------"

		::= { msaEdfaConfigurationEntry 99 }

	msaPaEdfaVoaHighInputPowerWarningThresholdMinimumValue OBJECT-TYPE
		SYNTAX			DisplayString
		MAX-ACCESS		read-write
		STATUS			current

		DESCRIPTION
		 "To set/get PA EDFA VOA high Input Power warning threshold Minimum Value.
		-----------------------------
		Values:
		eg. : 6.0
		-----------------------------"

		::= { msaEdfaConfigurationEntry 100 }

	msaPaEdfaVoaHighInputPowerWarningThresholdMaximumValue OBJECT-TYPE
		SYNTAX			DisplayString
		MAX-ACCESS		read-write
		STATUS			current

		DESCRIPTION
		 "To set/get PA EDFA VOA high Input Power warning threshold Maximum Value.
		-----------------------------
		Values:
		eg. : 6.0
		-----------------------------"

		::= { msaEdfaConfigurationEntry 101 }

	msaPaEdfaVoaLowInputPowerWarningThreshold OBJECT-TYPE
		SYNTAX			DisplayString
		MAX-ACCESS		read-write
		STATUS			current

		DESCRIPTION
		 "To set/get PA EDFA VOA low Input Power warning threshold.
		-----------------------------
		Values:
		eg. : -22.0
		-----------------------------"

		::= { msaEdfaConfigurationEntry 102 }

	msaPaEdfaVoaLowInputPowerWarningThresholdMinimumValue OBJECT-TYPE
		SYNTAX			DisplayString
		MAX-ACCESS		read-write
		STATUS			current

		DESCRIPTION
		 "To set/get PA EDFA VOA low Input Power warning threshold Minimum Value.
		-----------------------------
		Values:
		eg. : -22.0
		-----------------------------"

		::= { msaEdfaConfigurationEntry 103 }

	msaPaEdfaVoaLowInputPowerWarningThresholdMaximumValue OBJECT-TYPE
		SYNTAX			DisplayString
		MAX-ACCESS		read-write
		STATUS			current

		DESCRIPTION
		 "To set/get PA EDFA VOA low Input Power warning threshold Maximum Value.
		-----------------------------
		Values:
		eg. : -22.0
		-----------------------------"

		::= { msaEdfaConfigurationEntry 104 }

	msaPaEdfaModuleInputOpticalPowerLowAlarmThreshold OBJECT-TYPE
		SYNTAX			DisplayString
		MAX-ACCESS		read-only
		STATUS			current

		DESCRIPTION
		 "To get PA EDFA Module Input Optical Power Low Alarm Threshold.
		-----------------------------
		Values:
		eg. : 1
		-----------------------------"

		::= { msaEdfaConfigurationEntry 105 }

	msaPaEdfaModuleInputOpticalPowerLowAlarmThresholdMinimumValue OBJECT-TYPE
		SYNTAX			DisplayString
		MAX-ACCESS		read-only
		STATUS			current

		DESCRIPTION
		 "To get PA EDFA Module Input Optical Power Low Alarm Threshold Minimum Value.
		-----------------------------
		Values:
		eg. : 1
		-----------------------------"

		::= { msaEdfaConfigurationEntry 106 }

	msaPaEdfaModuleInputOpticalPowerLowAlarmThresholdMaximumValue OBJECT-TYPE
		SYNTAX			DisplayString
		MAX-ACCESS		read-only
		STATUS			current

		DESCRIPTION
		 "To get PA EDFA Module Input Optical Power Low Alarm Threshold Maximum Value.
		-----------------------------
		Values:
		eg. : 1
		-----------------------------"

		::= { msaEdfaConfigurationEntry 107 }

	msaPaEdfaModuleInputOpticalPowerHighAlarmThreshold OBJECT-TYPE
		SYNTAX			DisplayString
		MAX-ACCESS		read-write
		STATUS			current

		DESCRIPTION
		 "To set/get PA EDFA High Input Power Alarm threshold.
		-----------------------------
		Values:
		eg. : 1.0
		-----------------------------"

		::= { msaEdfaConfigurationEntry 108 }

	msaPaEdfaModuleInputOpticalPowerHighAlarmThresholdMinimumValue OBJECT-TYPE
		SYNTAX			DisplayString
		MAX-ACCESS		read-write
		STATUS			current

		DESCRIPTION
		 "To set/get PA EDFA High Input Power Alarm threshold.
		-----------------------------
		Values:
		eg. : 1.0
		-----------------------------"

		::= { msaEdfaConfigurationEntry 109 }

	msaPaEdfaModuleInputOpticalPowerHighAlarmThresholdMaximumValue OBJECT-TYPE
		SYNTAX			DisplayString
		MAX-ACCESS		read-write
		STATUS			current

		DESCRIPTION
		 "To set/get PA EDFA High Input Power Alarm threshold.
		-----------------------------
		Values:
		eg. : 1.0
		-----------------------------"

		::= { msaEdfaConfigurationEntry 110 }

	msaPaEdfaModuleOutputOpticalPowerFailureAlarmThreshold OBJECT-TYPE
		SYNTAX			DisplayString
		MAX-ACCESS		read-write
		STATUS			current

		DESCRIPTION
		 "To get PA EDFA Output Optical Power Failure alarm threshold.
		-----------------------------
		Values:
		eg. : 1
		-----------------------------"

		::= { msaEdfaConfigurationEntry 111 }

	msaPaEdfaModuleOutputOpticalPowerFailureAlarmThresholdMinimumValue OBJECT-TYPE
		SYNTAX			DisplayString
		MAX-ACCESS		read-write
		STATUS			current

		DESCRIPTION
		 "To get PA EDFA Output Optical Power Failure alarm threshold Minimum Value.
		-----------------------------
		Values:
		eg. : 1
		-----------------------------"

		::= { msaEdfaConfigurationEntry 112 }

	msaPaEdfaModuleOutputOpticalPowerFailureAlarmThresholdMaximumValue OBJECT-TYPE
		SYNTAX			DisplayString
		MAX-ACCESS		read-write
		STATUS			current

		DESCRIPTION
		 "To get PA EDFA Output Optical Power Failure alarm threshold Maximum Value.
		-----------------------------
		Values:
		eg. : 1
		-----------------------------"

		::= { msaEdfaConfigurationEntry 113 }

	msaPaEdfaModuleInputAlarmThreshold OBJECT-TYPE
		SYNTAX			DisplayString
		MAX-ACCESS		read-write
		STATUS			current

		DESCRIPTION
		 "To get PA EDFA Input alarm threshold.
		-----------------------------
		Values:
		eg. : 1
		-----------------------------"

		::= { msaEdfaConfigurationEntry 114 }

	msaPaEdfaModuleInputAlarmThresholdMinimumValue OBJECT-TYPE
		SYNTAX			DisplayString
		MAX-ACCESS		read-write
		STATUS			current

		DESCRIPTION
		 "To get PA EDFA Input alarm threshold minimum Value Minimum Value.
		-----------------------------
		Values:
		eg. : 1
		-----------------------------"

		::= { msaEdfaConfigurationEntry 115 }

	msaPaEdfaModuleInputAlarmThresholdMaximumValue OBJECT-TYPE
		SYNTAX			DisplayString
		MAX-ACCESS		read-write
		STATUS			current

		DESCRIPTION
		 "To get PA EDFA Input alarm threshold maximum value Maximum Value.
		-----------------------------
		Values:
		eg. : 1
		-----------------------------"

		::= { msaEdfaConfigurationEntry 116 }

	msaBaEdfaOpticalInputPowerFailureAlarmThreshold OBJECT-TYPE
		SYNTAX			DisplayString
		MAX-ACCESS		read-write
		STATUS			current

		DESCRIPTION
		 "To set/get BA EDFA card optical input power failure alarm threshold.
		-----------------------------
		Values:
		eg. : -21.0
		-----------------------------"

		::= { msaEdfaConfigurationEntry 117 }

	msaBaEdfaOpticalInputPowerFailureAlarmThresholdMinimumValue OBJECT-TYPE
		SYNTAX			DisplayString
		MAX-ACCESS		read-write
		STATUS			current

		DESCRIPTION
		 "To set/get BA EDFA card optical input power failure alarm threshold Minimum Value.
		-----------------------------
		Values:
		eg. : -21.0
		-----------------------------"

		::= { msaEdfaConfigurationEntry 118 }

	msaBaEdfaOpticalInputPowerFailureAlarmThresholdMaximumValue OBJECT-TYPE
		SYNTAX			DisplayString
		MAX-ACCESS		read-write
		STATUS			current

		DESCRIPTION
		 "To set/get BA EDFA card optical input power failure alarm threshold Maximum Value.
		-----------------------------
		Values:
		eg. : -21.0
		-----------------------------"

		::= { msaEdfaConfigurationEntry 119 }

	msaBaEdfaHighOpticalInputPowerAlarmThreshold OBJECT-TYPE
		SYNTAX			DisplayString
		MAX-ACCESS		read-write
		STATUS			current

		DESCRIPTION
		 "To set/get BA EDFA card optical high input power alarm threshold.
		-----------------------------
		Values:
		eg. : 5.0
		-----------------------------"

		::= { msaEdfaConfigurationEntry 120 }

	msaBaEdfaHighOpticalInputPowerAlarmThresholdMinimumValue OBJECT-TYPE
		SYNTAX			DisplayString
		MAX-ACCESS		read-write
		STATUS			current

		DESCRIPTION
		 "To set/get BA EDFA card optical high input power alarm threshold Minimum Value.
		-----------------------------
		Values:
		eg. : 5.0
		-----------------------------"

		::= { msaEdfaConfigurationEntry 121 }

	msaBaEdfaHighOpticalInputPowerAlarmThresholdMaximumValue OBJECT-TYPE
		SYNTAX			DisplayString
		MAX-ACCESS		read-write
		STATUS			current

		DESCRIPTION
		 "To set/get BA EDFA card optical high input power alarm threshold Maximum Value.
		-----------------------------
		Values:
		eg. : 5.0
		-----------------------------"

		::= { msaEdfaConfigurationEntry 122 }

	msaBaEdfaLowOpticalInputPowerAlarmThreshold OBJECT-TYPE
		SYNTAX			DisplayString
		MAX-ACCESS		read-write
		STATUS			current

		DESCRIPTION
		 "To set/get BA EDFA card optical low input power alarm threshold.
		-----------------------------
		Values:
		eg. : -35.0
		-----------------------------"

		::= { msaEdfaConfigurationEntry 123 }

	msaBaEdfaLowOpticalInputPowerAlarmThresholdMinimumValue OBJECT-TYPE
		SYNTAX			DisplayString
		MAX-ACCESS		read-write
		STATUS			current

		DESCRIPTION
		 "To set/get BA EDFA card optical low input power alarm threshold Minimum Value.
		-----------------------------
		Values:
		eg. : -35.0
		-----------------------------"

		::= { msaEdfaConfigurationEntry 124 }

	msaBaEdfaLowOpticalInputPowerAlarmThresholdMaximumValue OBJECT-TYPE
		SYNTAX			DisplayString
		MAX-ACCESS		read-write
		STATUS			current

		DESCRIPTION
		 "To set/get BA EDFA card optical low input power alarm threshold Maximum Value.
		-----------------------------
		Values:
		eg. : -35.0
		-----------------------------"

		::= { msaEdfaConfigurationEntry 125 }

	msaBaEdfaHighOpticalInputPowerWarningThreshold OBJECT-TYPE
		SYNTAX			DisplayString
		MAX-ACCESS		read-write
		STATUS			current

		DESCRIPTION
		 "To set/get BA EDFA card optical high input power warning threshold.
		-----------------------------
		Values:
		eg. : 3.0
		-----------------------------"

		::= { msaEdfaConfigurationEntry 126 }

	msaBaEdfaHighOpticalInputPowerWarningThresholdMinimumValue OBJECT-TYPE
		SYNTAX			DisplayString
		MAX-ACCESS		read-write
		STATUS			current

		DESCRIPTION
		 "To set/get BA EDFA card optical high input power warning threshold Minimum Value.
		-----------------------------
		Values:
		eg. : 3.0
		-----------------------------"

		::= { msaEdfaConfigurationEntry 127 }

	msaBaEdfaHighOpticalInputPowerWarningThresholdMaximumValue OBJECT-TYPE
		SYNTAX			DisplayString
		MAX-ACCESS		read-write
		STATUS			current

		DESCRIPTION
		 "To set/get BA EDFA card optical high input power warning threshold Maximum Value.
		-----------------------------
		Values:
		eg. : 3.0
		-----------------------------"

		::= { msaEdfaConfigurationEntry 128 }

	msaBaEdfaLowOpticalInputPowerWarningThreshold OBJECT-TYPE
		SYNTAX			DisplayString
		MAX-ACCESS		read-write
		STATUS			current

		DESCRIPTION
		 "To set/get BA EDFA card optical high input power warning threshold.
		-----------------------------
		Values:
		eg. : 3.0
		-----------------------------"

		::= { msaEdfaConfigurationEntry 129 }

	msaBaEdfaLowOpticalInputPowerWarningThresholdMinimumValue OBJECT-TYPE
		SYNTAX			DisplayString
		MAX-ACCESS		read-write
		STATUS			current

		DESCRIPTION
		 "To set/get BA EDFA card optical high input power warning threshold Minimum Value.
		-----------------------------
		Values:
		eg. : 3.0
		-----------------------------"

		::= { msaEdfaConfigurationEntry 130 }

	msaBaEdfaLowOpticalInputPowerWarningThresholdMaximumValue OBJECT-TYPE
		SYNTAX			DisplayString
		MAX-ACCESS		read-write
		STATUS			current

		DESCRIPTION
		 "To set/get BA EDFA card optical high input power warning threshold MAximum Value.
		-----------------------------
		Values:
		eg. : 3.0
		-----------------------------"

		::= { msaEdfaConfigurationEntry 131 }

	msaBaEdfaHighOpticalOutputPowerWarningThreshold OBJECT-TYPE
		SYNTAX			DisplayString
		MAX-ACCESS		read-write
		STATUS			current

		DESCRIPTION
		 "To set/get BA EDFA card optical high output power warning threshold.
		-----------------------------
		Values:
		eg. : 3.0
		-----------------------------"

		::= { msaEdfaConfigurationEntry 132 }

	msaBaEdfaHighOpticalOutputPowerWarningThresholdMinimumValue OBJECT-TYPE
		SYNTAX			DisplayString
		MAX-ACCESS		read-write
		STATUS			current

		DESCRIPTION
		 "To set/get BA EDFA card optical high output power warning threshold Minimum Value.
		-----------------------------
		Values:
		eg. : 3.0
		-----------------------------"

		::= { msaEdfaConfigurationEntry 133 }

	msaBaEdfaHighOpticalOutputPowerWarningThresholdMaximumValue OBJECT-TYPE
		SYNTAX			DisplayString
		MAX-ACCESS		read-write
		STATUS			current

		DESCRIPTION
		 "To set/get BA EDFA card optical high output power warning threshold MAximum Value.
		-----------------------------
		Values:
		eg. : 3.0
		-----------------------------"

		::= { msaEdfaConfigurationEntry 134 }

	msaBaEdfaLowOpticalOutputPowerWarningThreshold OBJECT-TYPE
		SYNTAX			DisplayString
		MAX-ACCESS		read-write
		STATUS			current

		DESCRIPTION
		 "To set/get BA EDFA card optical high output power warning threshold.
		-----------------------------
		Values:
		eg. : 3.0
		-----------------------------"

		::= { msaEdfaConfigurationEntry 135 }

	msaBaEdfaLowOpticalOutputPowerWarningThresholdMinimumValue OBJECT-TYPE
		SYNTAX			DisplayString
		MAX-ACCESS		read-write
		STATUS			current

		DESCRIPTION
		 "To set/get BA EDFA card optical high output power warning threshold Minimum Value.
		-----------------------------
		Values:
		eg. : 3.0
		-----------------------------"

		::= { msaEdfaConfigurationEntry 136 }

	msaBaEdfaLowOpticalOutputPowerWarningThresholdMaximumValue OBJECT-TYPE
		SYNTAX			DisplayString
		MAX-ACCESS		read-write
		STATUS			current

		DESCRIPTION
		 "To set/get BA EDFA card optical high output power warning threshold Maximum Value.
		-----------------------------
		Values:
		eg. : 3.0
		-----------------------------"

		::= { msaEdfaConfigurationEntry 137 }

	msaBaEdfaOpticalOutputPowerFailureAlarmThreshold OBJECT-TYPE
		SYNTAX			DisplayString
		MAX-ACCESS		read-write
		STATUS			current

		DESCRIPTION
		 "To set/get BA EDFA card optical output power failure alarm threshold.
		-----------------------------
		Values:
		eg. : -35.0
		-----------------------------"

		::= { msaEdfaConfigurationEntry 138 }

	msaBaEdfaOpticalOutputPowerFailureAlarmThresholdMinimumValue OBJECT-TYPE
		SYNTAX			DisplayString
		MAX-ACCESS		read-write
		STATUS			current

		DESCRIPTION
		 "To set/get BA EDFA card optical output power failure alarm threshold minimum Value.
		-----------------------------
		Values:
		eg. : -35.0
		-----------------------------"

		::= { msaEdfaConfigurationEntry 139 }

	msaBaEdfaOpticalOutputPowerFailureAlarmThresholdMaximumValue OBJECT-TYPE
		SYNTAX			DisplayString
		MAX-ACCESS		read-write
		STATUS			current

		DESCRIPTION
		 "To set/get BA EDFA card optical output power failure alarm threshold Maximum Value.
		-----------------------------
		Values:
		eg. : -35.0
		-----------------------------"

		::= { msaEdfaConfigurationEntry 140 }

	msaBaEdfaHighOpticalOutputPowerAlarmThreshold OBJECT-TYPE
		SYNTAX			DisplayString
		MAX-ACCESS		read-write
		STATUS			current

		DESCRIPTION
		 "To set/get BA EDFA card optical high output power alarm threshold.
		-----------------------------
		Values:
		eg. : 7.0
		-----------------------------"

		::= { msaEdfaConfigurationEntry 141 }

	msaBaEdfaHighOpticalOutputPowerAlarmThresholdMinimumValue OBJECT-TYPE
		SYNTAX			DisplayString
		MAX-ACCESS		read-write
		STATUS			current

		DESCRIPTION
		 "To set/get BA EDFA card optical high output power alarm threshold minimum Value.
		-----------------------------
		Values:
		eg. : 7.0
		-----------------------------"

		::= { msaEdfaConfigurationEntry 142 }

	msaBaEdfaHighOpticalOutputPowerAlarmThresholdMaximumValue OBJECT-TYPE
		SYNTAX			DisplayString
		MAX-ACCESS		read-write
		STATUS			current

		DESCRIPTION
		 "To set/get BA EDFA card optical high output power alarm threshold Maximum Value.
		-----------------------------
		Values:
		eg. : 7.0
		-----------------------------"

		::= { msaEdfaConfigurationEntry 143 }

	msaBaEdfaLowOpticalOutputPowerAlarmThreshold OBJECT-TYPE
		SYNTAX			DisplayString
		MAX-ACCESS		read-write
		STATUS			current

		DESCRIPTION
		 "To set/get BA EDFA card optical low output power alarm threshold.
		-----------------------------
		Values:
		eg. : -1.0
		-----------------------------"

		::= { msaEdfaConfigurationEntry 144 }

	msaBaEdfaLowOpticalOutputPowerAlarmThresholdMinimumValue OBJECT-TYPE
		SYNTAX			DisplayString
		MAX-ACCESS		read-write
		STATUS			current

		DESCRIPTION
		 "To set/get BA EDFA card optical low output power alarm threshold minimum Value.
		-----------------------------
		Values:
		eg. : -1.0
		-----------------------------"

		::= { msaEdfaConfigurationEntry 145 }

	msaBaEdfaLowOpticalOutputPowerAlarmThresholdMaximumValue OBJECT-TYPE
		SYNTAX			DisplayString
		MAX-ACCESS		read-write
		STATUS			current

		DESCRIPTION
		 "To set/get BA EDFA card optical low output power alarm threshold maximum Value.
		-----------------------------
		Values:
		eg. : -1.0
		-----------------------------"

		::= { msaEdfaConfigurationEntry 146 }

	msaBaEdfaHighTemperatureAlarmThreshold OBJECT-TYPE
		SYNTAX			DisplayString
		MAX-ACCESS		read-write
		STATUS			current

		DESCRIPTION
		 "To set/get BA EDFA card high temperature alarm threshold.
		-----------------------------
		Values:
		eg. : 50.0
		-----------------------------"

		::= { msaEdfaConfigurationEntry 147 }

	msaBaEdfaHighTemperatureAlarmThresholdMinimumValue OBJECT-TYPE
		SYNTAX			DisplayString
		MAX-ACCESS		read-write
		STATUS			current

		DESCRIPTION
		 "To set/get BA EDFA card high temperature alarm threshold Minimum VAlue.
		-----------------------------
		Values:
		eg. : 50.0
		-----------------------------"

		::= { msaEdfaConfigurationEntry 148 }

	msaBaEdfaHighTemperatureAlarmThresholdMaximumValue OBJECT-TYPE
		SYNTAX			DisplayString
		MAX-ACCESS		read-write
		STATUS			current

		DESCRIPTION
		 "To set/get BA EDFA card high temperature alarm threshold Maximum Value.
		-----------------------------
		Values:
		eg. : 50.0
		-----------------------------"

		::= { msaEdfaConfigurationEntry 149 }

	msaBaEdfaLowTemperatureAlarmThreshold OBJECT-TYPE
		SYNTAX			DisplayString
		MAX-ACCESS		read-write
		STATUS			current

		DESCRIPTION
		 "To set/get BA EDFA card low temperature alarm threshold.
		-----------------------------
		Values:
		eg. : -2.0
		-----------------------------"

		::= { msaEdfaConfigurationEntry 150 }

	msaBaEdfaLowTemperatureAlarmThresholdMinimumValue OBJECT-TYPE
		SYNTAX			DisplayString
		MAX-ACCESS		read-write
		STATUS			current

		DESCRIPTION
		 "To set/get BA EDFA card low temperature alarm threshold Minimum Value.
		-----------------------------
		Values:
		eg. : -2.0
		-----------------------------"

		::= { msaEdfaConfigurationEntry 151 }

	msaBaEdfaLowTemperatureAlarmThresholdMaximumValue OBJECT-TYPE
		SYNTAX			DisplayString
		MAX-ACCESS		read-write
		STATUS			current

		DESCRIPTION
		 "To set/get BA EDFA card low temperature alarm threshold Maximum Value.
		-----------------------------
		Values:
		eg. : -2.0
		-----------------------------"

		::= { msaEdfaConfigurationEntry 152 }

	msaBaEdfaHighTemperatureWarningThreshold OBJECT-TYPE
		SYNTAX			DisplayString
		MAX-ACCESS		read-write
		STATUS			current

		DESCRIPTION
		 "To set/get BA EDFA card high temperature warning threshold.
		-----------------------------
		Values:
		eg. : 45.0
		-----------------------------"

		::= { msaEdfaConfigurationEntry 153 }

	msaBaEdfaHighTemperatureWarningThresholdMinimumValue OBJECT-TYPE
		SYNTAX			DisplayString
		MAX-ACCESS		read-write
		STATUS			current

		DESCRIPTION
		 "To set/get BA EDFA card high temperature warning threshold minimum Value.
		-----------------------------
		Values:
		eg. : 45.0
		-----------------------------"

		::= { msaEdfaConfigurationEntry 154 }

	msaBaEdfaHighTemperatureWarningThresholdMaximumValue OBJECT-TYPE
		SYNTAX			DisplayString
		MAX-ACCESS		read-write
		STATUS			current

		DESCRIPTION
		 "To set/get BA EDFA card high temperature warning threshold maximum Value.
		-----------------------------
		Values:
		eg. : 45.0
		-----------------------------"

		::= { msaEdfaConfigurationEntry 155 }

	msaBaEdfaLowTemperatureWarningThreshold OBJECT-TYPE
		SYNTAX			DisplayString
		MAX-ACCESS		read-write
		STATUS			current

		DESCRIPTION
		 "To set/get BA EDFA card low temperature warning threshold.
		-----------------------------
		Values:
		eg. : 5.0
		-----------------------------"

		::= { msaEdfaConfigurationEntry 156 }

	msaBaEdfaLowTemperatureWarningThresholdMinimumValue OBJECT-TYPE
		SYNTAX			DisplayString
		MAX-ACCESS		read-write
		STATUS			current

		DESCRIPTION
		 "To set/get BA EDFA card low temperature warning threshold minimum Value.
		-----------------------------
		Values:
		eg. : 5.0
		-----------------------------"

		::= { msaEdfaConfigurationEntry 157 }

	msaBaEdfaLowTemperatureWarningThresholdMaximumValue OBJECT-TYPE
		SYNTAX			DisplayString
		MAX-ACCESS		read-write
		STATUS			current

		DESCRIPTION
		 "To set/get BA EDFA card low temperature warning threshold Maximum Value.
		-----------------------------
		Values:
		eg. : 5.0
		-----------------------------"

		::= { msaEdfaConfigurationEntry 158 }

	msaBaEdfaHighOperatingCurrentAlarmThreshold OBJECT-TYPE
		SYNTAX			DisplayString
		MAX-ACCESS		read-write
		STATUS			current

		DESCRIPTION
		 "To set/get BA EDFA card high operating current alarm threshold.
		-----------------------------
		Values:
		eg. : 700.0
		-----------------------------"

		::= { msaEdfaConfigurationEntry 159 }

	msaBaEdfaHighOperatingCurrentAlarmThresholdMinimumValue OBJECT-TYPE
		SYNTAX			DisplayString
		MAX-ACCESS		read-write
		STATUS			current

		DESCRIPTION
		 "To set/get BA EDFA card high operating current alarm threshold Minimum Value.
		-----------------------------
		Values:
		eg. : 700.0
		-----------------------------"

		::= { msaEdfaConfigurationEntry 160 }

	msaBaEdfaHighOperatingCurrentAlarmThresholdMaximumValue OBJECT-TYPE
		SYNTAX			DisplayString
		MAX-ACCESS		read-write
		STATUS			current

		DESCRIPTION
		 "To set/get BA EDFA card high operating current alarm threshold Maximum Value.
		-----------------------------
		Values:
		eg. : 700.0
		-----------------------------"

		::= { msaEdfaConfigurationEntry 161 }

	msaBaEdfaLowOperatingCurrentAlarmThreshold OBJECT-TYPE
		SYNTAX			DisplayString
		MAX-ACCESS		read-write
		STATUS			current

		DESCRIPTION
		 "To set/get BA EDFA card low operating current alarm threshold.
		-----------------------------
		Values:
		eg. : 300.0
		-----------------------------"

		::= { msaEdfaConfigurationEntry 162 }

	msaBaEdfaLowOperatingCurrentAlarmThresholdMinimumValue OBJECT-TYPE
		SYNTAX			DisplayString
		MAX-ACCESS		read-write
		STATUS			current

		DESCRIPTION
		 "To set/get BA EDFA card low operating current alarm threshold Minimum Value.
		-----------------------------
		Values:
		eg. : 300.0
		-----------------------------"

		::= { msaEdfaConfigurationEntry 163 }

	msaBaEdfaLowOperatingCurrentAlarmThresholdMaximumValue OBJECT-TYPE
		SYNTAX			DisplayString
		MAX-ACCESS		read-write
		STATUS			current

		DESCRIPTION
		 "To set/get BA EDFA card low operating current alarm threshold Maximum Value.
		-----------------------------
		Values:
		eg. : 300.0
		-----------------------------"

		::= { msaEdfaConfigurationEntry 164 }

	msaBaEdfaHighOperatingCurrentWarningThreshold OBJECT-TYPE
		SYNTAX			DisplayString
		MAX-ACCESS		read-write
		STATUS			current

		DESCRIPTION
		 "To set/get BA EDFA card high operating current warning threshold.
		-----------------------------
		Values:
		eg. : 690.0
		-----------------------------"

		::= { msaEdfaConfigurationEntry 165 }

	msaBaEdfaHighOperatingCurrentWarningThresholdMinimumValue OBJECT-TYPE
		SYNTAX			DisplayString
		MAX-ACCESS		read-write
		STATUS			current

		DESCRIPTION
		 "To set/get BA EDFA card high operating current warning threshold Minimum Value.
		-----------------------------
		Values:
		eg. : 690.0
		-----------------------------"

		::= { msaEdfaConfigurationEntry 166 }

	msaBaEdfaHighOperatingCurrentWarningThresholdMaximumValue OBJECT-TYPE
		SYNTAX			DisplayString
		MAX-ACCESS		read-write
		STATUS			current

		DESCRIPTION
		 "To set/get BA EDFA card high operating current warning threshold Maximum Value.
		-----------------------------
		Values:
		eg. : 690.0
		-----------------------------"

		::= { msaEdfaConfigurationEntry 167 }

	msaBaEdfaLowOperatingCurrentWarningThreshold OBJECT-TYPE
		SYNTAX			DisplayString
		MAX-ACCESS		read-write
		STATUS			current

		DESCRIPTION
		 "To set/get BA EDFA card low operating current warning threshold.
		-----------------------------
		Values:
		eg. : 310.0
		-----------------------------"

		::= { msaEdfaConfigurationEntry 168 }

	msaBaEdfaLowOperatingCurrentWarningThresholdMinimumValue OBJECT-TYPE
		SYNTAX			DisplayString
		MAX-ACCESS		read-write
		STATUS			current

		DESCRIPTION
		 "To set/get BA EDFA card low operating current warning threshold Minimum Value.
		-----------------------------
		Values:
		eg. : 310.0
		-----------------------------"

		::= { msaEdfaConfigurationEntry 169 }

	msaBaEdfaLowOperatingCurrentWarningThresholdMaximumValue OBJECT-TYPE
		SYNTAX			DisplayString
		MAX-ACCESS		read-write
		STATUS			current

		DESCRIPTION
		 "To set/get BA EDFA card low operating current warning threshold Maximum Value.
		-----------------------------
		Values:
		eg. : 310.0
		-----------------------------"

		::= { msaEdfaConfigurationEntry 170 }

	msaBaEdfaHighTECCurrentAlarmThreshold OBJECT-TYPE
		SYNTAX			DisplayString
		MAX-ACCESS		read-write
		STATUS			current

		DESCRIPTION
		 "To set/get BA EDFA card high TEC current alarm threshold.
		-----------------------------
		Values:
		eg. : 700.0
		-----------------------------"

		::= { msaEdfaConfigurationEntry 171 }

	msaBaEdfaHighTECCurrentAlarmThresholdMinimumValue OBJECT-TYPE
		SYNTAX			DisplayString
		MAX-ACCESS		read-write
		STATUS			current

		DESCRIPTION
		 "To set/get BA EDFA card high TEC current alarm threshold Minimum Value.
		-----------------------------
		Values:
		eg. : 700.0
		-----------------------------"

		::= { msaEdfaConfigurationEntry 172 }

	msaBaEdfaHighTECCurrentAlarmThresholdMaximumValue OBJECT-TYPE
		SYNTAX			DisplayString
		MAX-ACCESS		read-write
		STATUS			current

		DESCRIPTION
		 "To set/get BA EDFA card high TEC current alarm threshold Maximum Value.
		-----------------------------
		Values:
		eg. : 700.0
		-----------------------------"

		::= { msaEdfaConfigurationEntry 173 }

	msaBaEdfaLowTECCurrentAlarmThreshold OBJECT-TYPE
		SYNTAX			DisplayString
		MAX-ACCESS		read-write
		STATUS			current

		DESCRIPTION
		 "To set/get BA EDFA card low TEC current alarm threshold.
		-----------------------------
		Values:
		eg. : 300.0
		-----------------------------"

		::= { msaEdfaConfigurationEntry 174 }

	msaBaEdfaLowTECCurrentAlarmThresholdMinimumValue OBJECT-TYPE
		SYNTAX			DisplayString
		MAX-ACCESS		read-write
		STATUS			current

		DESCRIPTION
		 "To set/get BA EDFA card low TEC current alarm threshold Minimum Value.
		-----------------------------
		Values:
		eg. : 300.0
		-----------------------------"

		::= { msaEdfaConfigurationEntry 175 }

	msaBaEdfaLowTECCurrentAlarmThresholdMaximumValue OBJECT-TYPE
		SYNTAX			DisplayString
		MAX-ACCESS		read-write
		STATUS			current

		DESCRIPTION
		 "To set/get BA EDFA card low TEC current alarm threshold Maximum Value.
		-----------------------------
		Values:
		eg. : 300.0
		-----------------------------"

		::= { msaEdfaConfigurationEntry 176 }

	msaBaEdfaHighTECCurrentWarningThreshold OBJECT-TYPE
		SYNTAX			DisplayString
		MAX-ACCESS		read-write
		STATUS			current

		DESCRIPTION
		 "To set/get BA EDFA card high TEC current warning threshold.
		-----------------------------
		Values:
		eg. : 700.0
		-----------------------------"

		::= { msaEdfaConfigurationEntry 177 }

	msaBaEdfaHighTECCurrentWarningThresholdMinimumValue OBJECT-TYPE
		SYNTAX			DisplayString
		MAX-ACCESS		read-write
		STATUS			current

		DESCRIPTION
		 "To set/get BA EDFA card high TEC current warning threshold Minimum Value.
		-----------------------------
		Values:
		eg. : 700.0
		-----------------------------"

		::= { msaEdfaConfigurationEntry 178 }

	msaBaEdfaHighTECCurrentWarningThresholdMaximumValue OBJECT-TYPE
		SYNTAX			DisplayString
		MAX-ACCESS		read-write
		STATUS			current

		DESCRIPTION
		 "To set/get BA EDFA card high TEC current warning threshold MAximum Value.
		-----------------------------
		Values:
		eg. : 700.0
		-----------------------------"

		::= { msaEdfaConfigurationEntry 179 }

	msaBaEdfaLowTECCurrentWarningThreshold OBJECT-TYPE
		SYNTAX			DisplayString
		MAX-ACCESS		read-write
		STATUS			current

		DESCRIPTION
		 "To set/get BA EDFA card low TEC current warning threshold.
		-----------------------------
		Values:
		eg. : 300.0
		-----------------------------"

		::= { msaEdfaConfigurationEntry 180 }

	msaBaEdfaLowTECCurrentWarningThresholdMinimumValue OBJECT-TYPE
		SYNTAX			DisplayString
		MAX-ACCESS		read-write
		STATUS			current

		DESCRIPTION
		 "To set/get BA EDFA card low TEC current warning threshold minimum Value.
		-----------------------------
		Values:
		eg. : 300.0
		-----------------------------"

		::= { msaEdfaConfigurationEntry 181 }

	msaBaEdfaLowTECCurrentWarningThresholdMaximumValue OBJECT-TYPE
		SYNTAX			DisplayString
		MAX-ACCESS		read-write
		STATUS			current

		DESCRIPTION
		 "To set/get BA EDFA card low TEC current warning threshold Maximum Value.
		-----------------------------
		Values:
		eg. : 300.0
		-----------------------------"

		::= { msaEdfaConfigurationEntry 182 }

	msaBaEdfaVoaHighInputPowerAlarmThreshold OBJECT-TYPE
		SYNTAX			DisplayString
		MAX-ACCESS		read-write
		STATUS			current

		DESCRIPTION
		 "To set/get BA EDFA VOA high Input Power alarm threshold.
		-----------------------------
		Values:
		eg. : 7.0
		-----------------------------"

		::= { msaEdfaConfigurationEntry 183 }

	msaBaEdfaVoaHighInputPowerAlarmThresholdMinimumValue OBJECT-TYPE
		SYNTAX			DisplayString
		MAX-ACCESS		read-write
		STATUS			current

		DESCRIPTION
		 "To set/get BA EDFA VOA high Input Power alarm threshold Minimum VAlue.
		-----------------------------
		Values:
		eg. : 7.0
		-----------------------------"

		::= { msaEdfaConfigurationEntry 184 }

	msaBaEdfaVoaHighInputPowerAlarmThresholdMaximumValue OBJECT-TYPE
		SYNTAX			DisplayString
		MAX-ACCESS		read-write
		STATUS			current

		DESCRIPTION
		 "To set/get BA EDFA VOA high Input Power alarm threshold Maximum Value.
		-----------------------------
		Values:
		eg. : 7.0
		-----------------------------"

		::= { msaEdfaConfigurationEntry 185 }

	msaBaEdfaVoaLowInputPowerAlarmThreshold OBJECT-TYPE
		SYNTAX			DisplayString
		MAX-ACCESS		read-write
		STATUS			current

		DESCRIPTION
		 "To set/get BA EDFA VOA low Input Power alarm threshold.
		-----------------------------
		Values:
		eg. : -25.0
		-----------------------------"

		::= { msaEdfaConfigurationEntry 186 }

	msaBaEdfaVoaLowInputPowerAlarmThresholdMinimumValue OBJECT-TYPE
		SYNTAX			DisplayString
		MAX-ACCESS		read-write
		STATUS			current

		DESCRIPTION
		 "To set/get BA EDFA VOA low Input Power alarm threshold Minimum Value.
		-----------------------------
		Values:
		eg. : -25.0
		-----------------------------"

		::= { msaEdfaConfigurationEntry 187 }

	msaBaEdfaVoaLowInputPowerAlarmThresholdMaximumValue OBJECT-TYPE
		SYNTAX			DisplayString
		MAX-ACCESS		read-write
		STATUS			current

		DESCRIPTION
		 "To set/get BA EDFA VOA low Input Power alarm threshold Maximum Value.
		-----------------------------
		Values:
		eg. : -25.0
		-----------------------------"

		::= { msaEdfaConfigurationEntry 188 }

	msaBaEdfaVoaHighInputPowerWarningThreshold OBJECT-TYPE
		SYNTAX			DisplayString
		MAX-ACCESS		read-write
		STATUS			current

		DESCRIPTION
		 "To set/get BA EDFA VOA high Input Power warning threshold.
		-----------------------------
		Values:
		eg. : 6.0
		-----------------------------"

		::= { msaEdfaConfigurationEntry 189 }

	msaBaEdfaVoaHighInputPowerWarningThresholdMinimumValue OBJECT-TYPE
		SYNTAX			DisplayString
		MAX-ACCESS		read-write
		STATUS			current

		DESCRIPTION
		 "To set/get BA EDFA VOA high Input Power warning threshold Minimum Value.
		-----------------------------
		Values:
		eg. : 6.0
		-----------------------------"

		::= { msaEdfaConfigurationEntry 190 }

	msaBaEdfaVoaHighInputPowerWarningThresholdMaximumValue OBJECT-TYPE
		SYNTAX			DisplayString
		MAX-ACCESS		read-write
		STATUS			current

		DESCRIPTION
		 "To set/get BA EDFA VOA high Input Power warning threshold Maximum Value.
		-----------------------------
		Values:
		eg. : 6.0
		-----------------------------"

		::= { msaEdfaConfigurationEntry 191 }

	msaBaEdfaVoaLowInputPowerWarningThreshold OBJECT-TYPE
		SYNTAX			DisplayString
		MAX-ACCESS		read-write
		STATUS			current

		DESCRIPTION
		 "To set/get BA EDFA VOA low Input Power warning threshold.
		-----------------------------
		Values:
		eg. : -22.0
		-----------------------------"

		::= { msaEdfaConfigurationEntry 192 }

	msaBaEdfaVoaLowInputPowerWarningThresholdMinimumValue OBJECT-TYPE
		SYNTAX			DisplayString
		MAX-ACCESS		read-write
		STATUS			current

		DESCRIPTION
		 "To set/get BA EDFA VOA low Input Power warning threshold Minimum Value.
		-----------------------------
		Values:
		eg. : -22.0
		-----------------------------"

		::= { msaEdfaConfigurationEntry 193 }

	msaBaEdfaVoaLowInputPowerWarningThresholdMaximumValue OBJECT-TYPE
		SYNTAX			DisplayString
		MAX-ACCESS		read-write
		STATUS			current

		DESCRIPTION
		 "To set/get BA EDFA VOA low Input Power warning threshold Maximum Value.
		-----------------------------
		Values:
		eg. : -22.0
		-----------------------------"

		::= { msaEdfaConfigurationEntry 194 }

	msaBaEdfaModuleInputOpticalPowerLowAlarmThreshold OBJECT-TYPE
		SYNTAX			DisplayString
		MAX-ACCESS		read-only
		STATUS			current

		DESCRIPTION
		 "To get BA EDFA Module Input Optical Power Low Alarm Threshold.
		-----------------------------
		Values:
		eg. : 1
		-----------------------------"

		::= { msaEdfaConfigurationEntry 195 }

	msaBaEdfaModuleInputOpticalPowerLowAlarmThresholdMinimumValue OBJECT-TYPE
		SYNTAX			DisplayString
		MAX-ACCESS		read-only
		STATUS			current

		DESCRIPTION
		 "To get BA EDFA Module Input Optical Power Low Alarm Threshold Minimum VAlue.
		-----------------------------
		Values:
		eg. : 1
		-----------------------------"

		::= { msaEdfaConfigurationEntry 196 }

	msaBaEdfaModuleInputOpticalPowerLowAlarmThresholdMaximumValue OBJECT-TYPE
		SYNTAX			DisplayString
		MAX-ACCESS		read-only
		STATUS			current

		DESCRIPTION
		 "To get BA EDFA Module Input Optical Power Low Alarm Threshold MAximum VAlue.
		-----------------------------
		Values:
		eg. : 1
		-----------------------------"

		::= { msaEdfaConfigurationEntry 197 }

	msaBaEdfaModuleInputOpticalPowerHighAlarmThreshold OBJECT-TYPE
		SYNTAX			DisplayString
		MAX-ACCESS		read-write
		STATUS			current

		DESCRIPTION
		 "To set/get BA EDFA High Input Power Alarm threshold.
		-----------------------------
		Values:
		eg. : 1.0
		-----------------------------"

		::= { msaEdfaConfigurationEntry 198 }

	msaBaEdfaModuleInputOpticalPowerHighAlarmThresholdMinimumValue OBJECT-TYPE
		SYNTAX			DisplayString
		MAX-ACCESS		read-write
		STATUS			current

		DESCRIPTION
		 "To set/get BA EDFA High Input Power Alarm threshold Minimum Value.
		-----------------------------
		Values:
		eg. : 1.0
		-----------------------------"

		::= { msaEdfaConfigurationEntry 199 }

	msaBaEdfaModuleInputOpticalPowerHighAlarmThresholdMaximumValue OBJECT-TYPE
		SYNTAX			DisplayString
		MAX-ACCESS		read-write
		STATUS			current

		DESCRIPTION
		 "To set/get BA EDFA High Input Power Alarm threshold Maximum VAlue.
		-----------------------------
		Values:
		eg. : 1.0
		-----------------------------"

		::= { msaEdfaConfigurationEntry 200 }

	msaBaEdfaModuleOutputOpticalPowerFailureAlarmThreshold OBJECT-TYPE
		SYNTAX			DisplayString
		MAX-ACCESS		read-write
		STATUS			current

		DESCRIPTION
		 "To get BA EDFA Output Optical Power Failure alarm threshold.
		-----------------------------
		Values:
		eg. : 1
		-----------------------------"

		::= { msaEdfaConfigurationEntry 201 }

	msaBaEdfaModuleOutputOpticalPowerFailureAlarmThresholdMinimumValue OBJECT-TYPE
		SYNTAX			DisplayString
		MAX-ACCESS		read-write
		STATUS			current

		DESCRIPTION
		 "To get BA EDFA Output Optical Power Failure alarm threshold Minimum Value.
		-----------------------------
		Values:
		eg. : 1
		-----------------------------"

		::= { msaEdfaConfigurationEntry 202 }

	msaBaEdfaModuleOutputOpticalPowerFailureAlarmThresholdMaximumValue OBJECT-TYPE
		SYNTAX			DisplayString
		MAX-ACCESS		read-write
		STATUS			current

		DESCRIPTION
		 "To get BA EDFA Output Optical Power Failure alarm threshold Maximum value.
		-----------------------------
		Values:
		eg. : 1
		-----------------------------"

		::= { msaEdfaConfigurationEntry 203 }

	msaBaEdfaModuleInputAlarmThreshold OBJECT-TYPE
		SYNTAX			DisplayString
		MAX-ACCESS		read-write
		STATUS			current

		DESCRIPTION
		 "To get BA EDFA Input alarm threshold.
		-----------------------------
		Values:
		eg. : 1
		-----------------------------"

		::= { msaEdfaConfigurationEntry 204 }

	msaBaEdfaModuleInputAlarmThresholdMinimumValue OBJECT-TYPE
		SYNTAX			DisplayString
		MAX-ACCESS		read-write
		STATUS			current

		DESCRIPTION
		 "To get BA EDFA Input alarm threshold Minimum Value.
		-----------------------------
		Values:
		eg. : 1
		-----------------------------"

		::= { msaEdfaConfigurationEntry 205 }

	msaBaEdfaModuleInputAlarmThresholdMaximumValue OBJECT-TYPE
		SYNTAX			DisplayString
		MAX-ACCESS		read-write
		STATUS			current

		DESCRIPTION
		 "To get BA EDFA Input alarm threshold MAximum VAlue.
		-----------------------------
		Values:
		eg. : 1
		-----------------------------"

		::= { msaEdfaConfigurationEntry 206 }

	msaEdfaCardSoftwareUpgrade OBJECT-TYPE
		SYNTAX 		DisplayString
		MAX-ACCESS 	read-write
		STATUS 		current
		DESCRIPTION
			"Valid only as SET command.
			This property upgrades the software of the MSA EDFA card
			It takes the path of the software release as
			a value,
			paEdfaPlusInterface: 0
			Values:
			eg: /home/root/rel-2.0.0.tar.gz
			-----------------------------"

		::= { msaEdfaConfigurationEntry 207 }

	msaPaEdfaOpticalInputPowerFailureAlarmInhibit OBJECT-TYPE
		SYNTAX  	INTEGER
		MAX-ACCESS  	read-write
		STATUS  	current

		DESCRIPTION
		"Inhibits msaPaEdfa Input Power Failure Alarm
		for the receiving port. Set and Get succeed upon
		valid inhibition status.
		-----------------------------
		Values:
		0 or 1
		eg: 0
		-----------------------------"

		::= { msaEdfaConfigurationEntry 208 }	

	msaPaEdfaOpticalOutputPowerFailureAlarmInhibit OBJECT-TYPE
		SYNTAX  	INTEGER
		MAX-ACCESS  	read-write
		STATUS  	current

		DESCRIPTION
		"Inhibits msaPaEdfa Output Power Failure Alarm
		for the receiving port. Set and Get succeed upon
		valid inhibition status.
		-----------------------------
		Values:
		0 or 1
		eg: 0
		-----------------------------"

		::= { msaEdfaConfigurationEntry 209 }

	msaPaEdfaLowOpticalInputPowerAlarmInhibit OBJECT-TYPE
		SYNTAX  	INTEGER
		MAX-ACCESS  	read-write
		STATUS  	current

		DESCRIPTION
		"Inhibits msaPaEdfa Low Input Power Alarm
		for the receiving port. Set and Get succeed upon
		valid inhibition status.
		-----------------------------
		Values:
		0 or 1
		eg: 0
		-----------------------------"

		::= { msaEdfaConfigurationEntry 210 }	

	msaPaEdfaHighOpticalInputPowerAlarmInhibit OBJECT-TYPE
		SYNTAX  	INTEGER
		MAX-ACCESS  	read-write
		STATUS  	current

		DESCRIPTION
		"Inhibits msaPaEdfa High Input Power Alarm
		for the receiving port. Set and Get succeed upon
		valid inhibition status.
		-----------------------------
		Values:
		0 or 1
		eg: 0
		-----------------------------"

		::= { msaEdfaConfigurationEntry 211 }	

	msaPaEdfaLowOpticalOutputPowerAlarmInhibit OBJECT-TYPE
		SYNTAX  	INTEGER
		MAX-ACCESS  	read-write
		STATUS  	current

		DESCRIPTION
		"Inhibits msaPaEdfa Low Output Power Alarm
		for the receiving port. Set and Get succeed upon
		valid inhibition status.
		-----------------------------
		Values:
		0 or 1
		eg: 0
		-----------------------------"

		::= { msaEdfaConfigurationEntry 212 }	

	msaPaEdfaHighOpticalOutputPowerAlarmInhibit OBJECT-TYPE
		SYNTAX  	INTEGER
		MAX-ACCESS  	read-write
		STATUS  	current

		DESCRIPTION
		"Inhibits msaPaEdfa High Output Power Alarm
		for the receiving port. Set and Get succeed upon
		valid inhibition status.
		-----------------------------
		Values:
		0 or 1
		eg: 0
		-----------------------------"

		::= { msaEdfaConfigurationEntry 213 }	

	msaPaEdfaLowTemperatureAlarmInhibit OBJECT-TYPE
		SYNTAX  	INTEGER
		MAX-ACCESS  	read-write
		STATUS  	current

		DESCRIPTION
		"Inhibits msaPaEdfa Low Temperature Alarm
		for the receiving port. Set and Get succeed upon
		valid inhibition status.
		-----------------------------
		Values:
		0 or 1
		eg: 0
		-----------------------------"

		::= { msaEdfaConfigurationEntry 214 }	

	msaPaEdfaHighTemperatureAlarmInhibit OBJECT-TYPE
		SYNTAX  	INTEGER
		MAX-ACCESS  	read-write
		STATUS  	current

		DESCRIPTION
		"Inhibits msaPaEdfa High Temperature Alarm
		for the receiving port. Set and Get succeed upon
		valid inhibition status.
		-----------------------------
		Values:
		0 or 1
		eg: 0
		-----------------------------"

		::= { msaEdfaConfigurationEntry 215 }

	msaPaEdfaLowOperatingCurrentAlarmInhibit OBJECT-TYPE
		SYNTAX  	INTEGER
		MAX-ACCESS  	read-write
		STATUS  	current

		DESCRIPTION
		"Inhibits msaPaEdfa Low Operating Current Alarm
		for the receiving port. Set and Get succeed upon
		valid inhibition status.
		-----------------------------
		Values:
		0 or 1
		eg: 0
		-----------------------------"

		::= { msaEdfaConfigurationEntry 216 }	

	msaPaEdfaHighOperatingCurrentAlarmInhibit OBJECT-TYPE
		SYNTAX  	INTEGER
		MAX-ACCESS  	read-write
		STATUS  	current

		DESCRIPTION
		"Inhibits msaPaEdfa High Operating Current Alarm
		for the receiving port. Set and Get succeed upon
		valid inhibition status.
		-----------------------------
		Values:
		0 or 1
		eg: 0
		-----------------------------"

		::= { msaEdfaConfigurationEntry 217 }	

	msaPaEdfaLowTECCurrentAlarmInhibit OBJECT-TYPE
		SYNTAX  	INTEGER
		MAX-ACCESS  	read-write
		STATUS  	current

		DESCRIPTION
		"Inhibits msaPaEdfa Low TEC Current Alarm
		for the receiving port. Set and Get succeed upon
		valid inhibition status.
		-----------------------------
		Values:
		0 or 1
		eg: 0
		-----------------------------"

		::= { msaEdfaConfigurationEntry 218 }

	msaPaEdfaHighTECCurrentAlarmInhibit OBJECT-TYPE
		SYNTAX  	INTEGER
		MAX-ACCESS  	read-write
		STATUS  	current

		DESCRIPTION
		"Inhibits msaPaEdfa High TEC Current Alarm
		for the receiving port. Set and Get succeed upon
		valid inhibition status.
		-----------------------------
		Values:
		0 or 1
		eg: 0
		-----------------------------"

		::= { msaEdfaConfigurationEntry 219 }	

	msaPaEdfaLowVoaInputPowerAlarmInhibit OBJECT-TYPE
		SYNTAX  	INTEGER
		MAX-ACCESS  	read-write
		STATUS  	current

		DESCRIPTION
		"Inhibits msaPaEdfa Low Voa Input Power Alarm
		for the receiving port. Set and Get succeed upon
		valid inhibition status.
		-----------------------------
		Values:
		0 or 1
		eg: 0
		-----------------------------"

		::= { msaEdfaConfigurationEntry 220 }

	msaPaEdfaHighVoaInputPowerAlarmInhibit OBJECT-TYPE
		SYNTAX  	INTEGER
		MAX-ACCESS  	read-write
		STATUS  	current

		DESCRIPTION
		"Inhibits msaPaEdfa High Voa Input Power Alarm
		for the receiving port. Set and Get succeed upon
		valid inhibition status.
		-----------------------------
		Values:
		0 or 1
		eg: 0
		-----------------------------"

		::= { msaEdfaConfigurationEntry 221 }

	msaPaEdfaInputOutOfRangeAlarmInhibit OBJECT-TYPE
		SYNTAX  	INTEGER
		MAX-ACCESS  	read-write
		STATUS  	current

		DESCRIPTION
		"Inhibits msaPaEdfa Input Out Of Range Alarm
		for the receiving port. Set and Get succeed upon
		valid inhibition status.
		-----------------------------
		Values:
		0 or 1
		eg: 0
		-----------------------------"

		::= { msaEdfaConfigurationEntry 222 }

	msaPaEdfaOutputOutOfRangeAlarmInhibit OBJECT-TYPE
		SYNTAX  	INTEGER
		MAX-ACCESS  	read-write
		STATUS  	current

		DESCRIPTION
		"Inhibits msaPaEdfa Output Out Of Range Alarm
		for the receiving port. Set and Get succeed upon
		valid inhibition status.
		-----------------------------
		Values:
		0 or 1
		eg: 0
		-----------------------------"

		::= { msaEdfaConfigurationEntry 223 }

	msaPaEdfaModuleCommunicationAlarmInhibit OBJECT-TYPE
		SYNTAX  	INTEGER
		MAX-ACCESS  	read-write
		STATUS  	current

		DESCRIPTION
		"Inhibits msaPaEdfa Module Communication Alarm
		for the receiving port. Set and Get succeed upon
		valid inhibition status.
		-----------------------------
		Values:
		0 or 1
		eg: 0
		-----------------------------"

		::= { msaEdfaConfigurationEntry 224 }

	msaPaEdfaOpticalInputPowerFailureWarningInhibit OBJECT-TYPE
		SYNTAX  	INTEGER
		MAX-ACCESS  	read-write
		STATUS  	current

		DESCRIPTION
		"Inhibits msaPaEdfa Input Power Failure Warning
		for the receiving port. Set and Get succeed upon
		valid inhibition status.
		-----------------------------
		Values:
		0 or 1
		eg: 0
		-----------------------------"

		::= { msaEdfaConfigurationEntry 225 }	

	msaPaEdfaOpticalOutputPowerFailureWarningInhibit OBJECT-TYPE
		SYNTAX  	INTEGER
		MAX-ACCESS  	read-write
		STATUS  	current

		DESCRIPTION
		"Inhibits msaPaEdfa Output Power Failure Warning
		for the receiving port. Set and Get succeed upon
		valid inhibition status.
		-----------------------------
		Values:
		0 or 1
		eg: 0
		-----------------------------"

		::= { msaEdfaConfigurationEntry 226 }

	msaPaEdfaLowOpticalInputPowerWarningInhibit OBJECT-TYPE
		SYNTAX  	INTEGER
		MAX-ACCESS  	read-write
		STATUS  	current

		DESCRIPTION
		"Inhibits msaPaEdfa Low Input Power Warning
		for the receiving port. Set and Get succeed upon
		valid inhibition status.
		-----------------------------
		Values:
		0 or 1
		eg: 0
		-----------------------------"

		::= { msaEdfaConfigurationEntry 227 }	

	msaPaEdfaHighOpticalInputPowerWarningInhibit OBJECT-TYPE
		SYNTAX  	INTEGER
		MAX-ACCESS  	read-write
		STATUS  	current

		DESCRIPTION
		"Inhibits msaPaEdfa High Input Power Warning
		for the receiving port. Set and Get succeed upon
		valid inhibition status.
		-----------------------------
		Values:
		0 or 1
		eg: 0
		-----------------------------"

		::= { msaEdfaConfigurationEntry 228 }	

	msaPaEdfaLowOpticalOutputPowerWarningInhibit OBJECT-TYPE
		SYNTAX  	INTEGER
		MAX-ACCESS  	read-write
		STATUS  	current

		DESCRIPTION
		"Inhibits msaPaEdfa Low Output Power Warning
		for the receiving port. Set and Get succeed upon
		valid inhibition status.
		-----------------------------
		Values:
		0 or 1
		eg: 0
		-----------------------------"

		::= { msaEdfaConfigurationEntry 229 }	

	msaPaEdfaHighOpticalOutputPowerWarningInhibit OBJECT-TYPE
		SYNTAX  	INTEGER
		MAX-ACCESS  	read-write
		STATUS  	current

		DESCRIPTION
		"Inhibits msaPaEdfa High Output Power Warning
		for the receiving port. Set and Get succeed upon
		valid inhibition status.
		-----------------------------
		Values:
		0 or 1
		eg: 0
		-----------------------------"

		::= { msaEdfaConfigurationEntry 230 }	

	msaPaEdfaLowTemperatureWarningInhibit OBJECT-TYPE
		SYNTAX  	INTEGER
		MAX-ACCESS  	read-write
		STATUS  	current

		DESCRIPTION
		"Inhibits msaPaEdfa Low Temperature Warning
		for the receiving port. Set and Get succeed upon
		valid inhibition status.
		-----------------------------
		Values:
		0 or 1
		eg: 0
		-----------------------------"

		::= { msaEdfaConfigurationEntry 231 }	

	msaPaEdfaHighTemperatureWarningInhibit OBJECT-TYPE
		SYNTAX  	INTEGER
		MAX-ACCESS  	read-write
		STATUS  	current

		DESCRIPTION
		"Inhibits msaPaEdfa High Temperature Warning
		for the receiving port. Set and Get succeed upon
		valid inhibition status.
		-----------------------------
		Values:
		0 or 1
		eg: 0
		-----------------------------"

		::= { msaEdfaConfigurationEntry 232 }

	msaPaEdfaLowOperatingCurrentWarningInhibit OBJECT-TYPE
		SYNTAX  	INTEGER
		MAX-ACCESS  	read-write
		STATUS  	current

		DESCRIPTION
		"Inhibits msaPaEdfa Low Operating Current Warning
		for the receiving port. Set and Get succeed upon
		valid inhibition status.
		-----------------------------
		Values:
		0 or 1
		eg: 0
		-----------------------------"

		::= { msaEdfaConfigurationEntry 233 }	

	msaPaEdfaHighOperatingCurrentWarningInhibit OBJECT-TYPE
		SYNTAX  	INTEGER
		MAX-ACCESS  	read-write
		STATUS  	current

		DESCRIPTION
		"Inhibits msaPaEdfa High Operating Current Warning
		for the receiving port. Set and Get succeed upon
		valid inhibition status.
		-----------------------------
		Values:
		0 or 1
		eg: 0
		-----------------------------"

		::= { msaEdfaConfigurationEntry 234 }	

	msaPaEdfaLowTECCurrentWarningInhibit OBJECT-TYPE
		SYNTAX  	INTEGER
		MAX-ACCESS  	read-write
		STATUS  	current

		DESCRIPTION
		"Inhibits msaPaEdfa Low TEC Current Warning
		for the receiving port. Set and Get succeed upon
		valid inhibition status.
		-----------------------------
		Values:
		0 or 1
		eg: 0
		-----------------------------"

		::= { msaEdfaConfigurationEntry 235 }

	msaPaEdfaHighTECCurrentWarningInhibit OBJECT-TYPE
		SYNTAX  	INTEGER
		MAX-ACCESS  	read-write
		STATUS  	current

		DESCRIPTION
		"Inhibits msaPaEdfa High TEC Current Warning
		for the receiving port. Set and Get succeed upon
		valid inhibition status.
		-----------------------------
		Values:
		0 or 1
		eg: 0
		-----------------------------"

		::= { msaEdfaConfigurationEntry 236 }	

	msaPaEdfaLowVoaInputPowerWarningInhibit OBJECT-TYPE
		SYNTAX  	INTEGER
		MAX-ACCESS  	read-write
		STATUS  	current

		DESCRIPTION
		"Inhibits msaPaEdfa Low Voa Input Power Warning
		for the receiving port. Set and Get succeed upon
		valid inhibition status.
		-----------------------------
		Values:
		0 or 1
		eg: 0
		-----------------------------"

		::= { msaEdfaConfigurationEntry 237 }

	msaPaEdfaHighVoaInputPowerWarningInhibit OBJECT-TYPE
		SYNTAX  	INTEGER
		MAX-ACCESS  	read-write
		STATUS  	current

		DESCRIPTION
		"Inhibits msaPaEdfa High Voa Input Power Warning
		for the receiving port. Set and Get succeed upon
		valid inhibition status.
		-----------------------------
		Values:
		0 or 1
		eg: 0
		-----------------------------"

		::= { msaEdfaConfigurationEntry 238 }

	msaPaEdfaInputOutOfRangeWarningInhibit OBJECT-TYPE
		SYNTAX  	INTEGER
		MAX-ACCESS  	read-write
		STATUS  	current

		DESCRIPTION
		"Inhibits msaPaEdfa Input Out Of Range Warning
		for the receiving port. Set and Get succeed upon
		valid inhibition status.
		-----------------------------
		Values:
		0 or 1
		eg: 0
		-----------------------------"

		::= { msaEdfaConfigurationEntry 239 }

	msaPaEdfaOutputOutOfRangeWarningInhibit OBJECT-TYPE
		SYNTAX  	INTEGER
		MAX-ACCESS  	read-write
		STATUS  	current

		DESCRIPTION
		"Inhibits msaPaEdfa Output Out Of Range Warning
		for the receiving port. Set and Get succeed upon
		valid inhibition status.
		-----------------------------
		Values:
		0 or 1
		eg: 0
		-----------------------------"

		::= { msaEdfaConfigurationEntry 240 }

	msaPaEdfaModuleCommunicationWarningInhibit OBJECT-TYPE
		SYNTAX  	INTEGER
		MAX-ACCESS  	read-write
		STATUS  	current

		DESCRIPTION
		"Inhibits msaPaEdfa Module Communication Warning
		for the receiving port. Set and Get succeed upon
		valid inhibition status.
		-----------------------------
		Values:
		0 or 1
		eg: 0
		-----------------------------"

		::= { msaEdfaConfigurationEntry 241 }	

msaBaEdfaOpticalInputPowerFailureAlarmInhibit OBJECT-TYPE
		SYNTAX  	INTEGER
		MAX-ACCESS  	read-write
		STATUS  	current

		DESCRIPTION
		"Inhibits msaBaEdfa Input Power Failure Alarm
		for the receiving port. Set and Get succeed upon
		valid inhibition status.
		-----------------------------
		Values:
		0 or 1
		eg: 0
		-----------------------------"

		::= { msaEdfaConfigurationEntry 242 }	

	msaBaEdfaOpticalOutputPowerFailureAlarmInhibit OBJECT-TYPE
		SYNTAX  	INTEGER
		MAX-ACCESS  	read-write
		STATUS  	current

		DESCRIPTION
		"Inhibits msaBaEdfa Output Power Failure Alarm
		for the receiving port. Set and Get succeed upon
		valid inhibition status.
		-----------------------------
		Values:
		0 or 1
		eg: 0
		-----------------------------"

		::= { msaEdfaConfigurationEntry 243 }

	msaBaEdfaLowOpticalInputPowerAlarmInhibit OBJECT-TYPE
		SYNTAX  	INTEGER
		MAX-ACCESS  	read-write
		STATUS  	current

		DESCRIPTION
		"Inhibits msaBaEdfa Low Input Power Alarm
		for the receiving port. Set and Get succeed upon
		valid inhibition status.
		-----------------------------
		Values:
		0 or 1
		eg: 0
		-----------------------------"

		::= { msaEdfaConfigurationEntry 244 }	

	msaBaEdfaHighOpticalInputPowerAlarmInhibit OBJECT-TYPE
		SYNTAX  	INTEGER
		MAX-ACCESS  	read-write
		STATUS  	current

		DESCRIPTION
		"Inhibits msaBaEdfa High Input Power Alarm
		for the receiving port. Set and Get succeed upon
		valid inhibition status.
		-----------------------------
		Values:
		0 or 1
		eg: 0
		-----------------------------"

		::= { msaEdfaConfigurationEntry 245 }	

	msaBaEdfaLowOpticalOutputPowerAlarmInhibit OBJECT-TYPE
		SYNTAX  	INTEGER
		MAX-ACCESS  	read-write
		STATUS  	current

		DESCRIPTION
		"Inhibits msaBaEdfa Low Output Power Alarm
		for the receiving port. Set and Get succeed upon
		valid inhibition status.
		-----------------------------
		Values:
		0 or 1
		eg: 0
		-----------------------------"

		::= { msaEdfaConfigurationEntry 246 }	

	msaBaEdfaHighOpticalOutputPowerAlarmInhibit OBJECT-TYPE
		SYNTAX  	INTEGER
		MAX-ACCESS  	read-write
		STATUS  	current

		DESCRIPTION
		"Inhibits msaBaEdfa High Output Power Alarm
		for the receiving port. Set and Get succeed upon
		valid inhibition status.
		-----------------------------
		Values:
		0 or 1
		eg: 0
		-----------------------------"

		::= { msaEdfaConfigurationEntry 247 }	

	msaBaEdfaLowTemperatureAlarmInhibit OBJECT-TYPE
		SYNTAX  	INTEGER
		MAX-ACCESS  	read-write
		STATUS  	current

		DESCRIPTION
		"Inhibits msaBaEdfa Low Temperature Alarm
		for the receiving port. Set and Get succeed upon
		valid inhibition status.
		-----------------------------
		Values:
		0 or 1
		eg: 0
		-----------------------------"

		::= { msaEdfaConfigurationEntry 248 }	

	msaBaEdfaHighTemperatureAlarmInhibit OBJECT-TYPE
		SYNTAX  	INTEGER
		MAX-ACCESS  	read-write
		STATUS  	current

		DESCRIPTION
		"Inhibits msaBaEdfa High Temperature Alarm
		for the receiving port. Set and Get succeed upon
		valid inhibition status.
		-----------------------------
		Values:
		0 or 1
		eg: 0
		-----------------------------"

		::= { msaEdfaConfigurationEntry 249 }

	msaBaEdfaLowOperatingCurrentAlarmInhibit OBJECT-TYPE
		SYNTAX  	INTEGER
		MAX-ACCESS  	read-write
		STATUS  	current

		DESCRIPTION
		"Inhibits msaBaEdfa Low Operating Current Alarm
		for the receiving port. Set and Get succeed upon
		valid inhibition status.
		-----------------------------
		Values:
		0 or 1
		eg: 0
		-----------------------------"

		::= { msaEdfaConfigurationEntry 250 }	

	msaBaEdfaHighOperatingCurrentAlarmInhibit OBJECT-TYPE
		SYNTAX  	INTEGER
		MAX-ACCESS  	read-write
		STATUS  	current

		DESCRIPTION
		"Inhibits msaBaEdfa High Operating Current Alarm
		for the receiving port. Set and Get succeed upon
		valid inhibition status.
		-----------------------------
		Values:
		0 or 1
		eg: 0
		-----------------------------"

		::= { msaEdfaConfigurationEntry 251 }	

	msaBaEdfaLowTECCurrentAlarmInhibit OBJECT-TYPE
		SYNTAX  	INTEGER
		MAX-ACCESS  	read-write
		STATUS  	current

		DESCRIPTION
		"Inhibits msaBaEdfa Low TEC Current Alarm
		for the receiving port. Set and Get succeed upon
		valid inhibition status.
		-----------------------------
		Values:
		0 or 1
		eg: 0
		-----------------------------"

		::= { msaEdfaConfigurationEntry 252 }

	msaBaEdfaHighTECCurrentAlarmInhibit OBJECT-TYPE
		SYNTAX  	INTEGER
		MAX-ACCESS  	read-write
		STATUS  	current

		DESCRIPTION
		"Inhibits msaBaEdfa High TEC Current Alarm
		for the receiving port. Set and Get succeed upon
		valid inhibition status.
		-----------------------------
		Values:
		0 or 1
		eg: 0
		-----------------------------"

		::= { msaEdfaConfigurationEntry 253 }	

	msaBaEdfaLowVoaInputPowerAlarmInhibit OBJECT-TYPE
		SYNTAX  	INTEGER
		MAX-ACCESS  	read-write
		STATUS  	current

		DESCRIPTION
		"Inhibits msaBaEdfa Low Voa Input Power Alarm
		for the receiving port. Set and Get succeed upon
		valid inhibition status.
		-----------------------------
		Values:
		0 or 1
		eg: 0
		-----------------------------"

		::= { msaEdfaConfigurationEntry 254 }

	msaBaEdfaHighVoaInputPowerAlarmInhibit OBJECT-TYPE
		SYNTAX  	INTEGER
		MAX-ACCESS  	read-write
		STATUS  	current

		DESCRIPTION
		"Inhibits msaBaEdfa High Voa Input Power Alarm
		for the receiving port. Set and Get succeed upon
		valid inhibition status.
		-----------------------------
		Values:
		0 or 1
		eg: 0
		-----------------------------"

		::= { msaEdfaConfigurationEntry 255 }

	msaBaEdfaInputOutOfRangeAlarmInhibit OBJECT-TYPE
		SYNTAX  	INTEGER
		MAX-ACCESS  	read-write
		STATUS  	current

		DESCRIPTION
		"Inhibits msaBaEdfa Input Out Of Range Alarm
		for the receiving port. Set and Get succeed upon
		valid inhibition status.
		-----------------------------
		Values:
		0 or 1
		eg: 0
		-----------------------------"

		::= { msaEdfaConfigurationEntry 256 }

	msaBaEdfaOutputOutOfRangeAlarmInhibit OBJECT-TYPE
		SYNTAX  	INTEGER
		MAX-ACCESS  	read-write
		STATUS  	current

		DESCRIPTION
		"Inhibits msaBaEdfa Output Out Of Range Alarm
		for the receiving port. Set and Get succeed upon
		valid inhibition status.
		-----------------------------
		Values:
		0 or 1
		eg: 0
		-----------------------------"

		::= { msaEdfaConfigurationEntry 257 }

	msaBaEdfaModuleCommunicationAlarmInhibit OBJECT-TYPE
		SYNTAX  	INTEGER
		MAX-ACCESS  	read-write
		STATUS  	current

		DESCRIPTION
		"Inhibits msaBaEdfa Module Communication Alarm
		for the receiving port. Set and Get succeed upon
		valid inhibition status.
		-----------------------------
		Values:
		0 or 1
		eg: 0
		-----------------------------"

		::= { msaEdfaConfigurationEntry 258 }

	msaBaEdfaOpticalInputPowerFailureWarningInhibit OBJECT-TYPE
		SYNTAX  	INTEGER
		MAX-ACCESS  	read-write
		STATUS  	current

		DESCRIPTION
		"Inhibits msaBaEdfa Input Power Failure Warning
		for the receiving port. Set and Get succeed upon
		valid inhibition status.
		-----------------------------
		Values:
		0 or 1
		eg: 0
		-----------------------------"

		::= { msaEdfaConfigurationEntry 259 }	

	msaBaEdfaOpticalOutputPowerFailureWarningInhibit OBJECT-TYPE
		SYNTAX  	INTEGER
		MAX-ACCESS  	read-write
		STATUS  	current

		DESCRIPTION
		"Inhibits msaBaEdfa Output Power Failure Warning
		for the receiving port. Set and Get succeed upon
		valid inhibition status.
		-----------------------------
		Values:
		0 or 1
		eg: 0
		-----------------------------"

		::= { msaEdfaConfigurationEntry 260 }

	msaBaEdfaLowOpticalInputPowerWarningInhibit OBJECT-TYPE
		SYNTAX  	INTEGER
		MAX-ACCESS  	read-write
		STATUS  	current

		DESCRIPTION
		"Inhibits msaBaEdfa Low Input Power Warning
		for the receiving port. Set and Get succeed upon
		valid inhibition status.
		-----------------------------
		Values:
		0 or 1
		eg: 0
		-----------------------------"

		::= { msaEdfaConfigurationEntry 261 }	

	msaBaEdfaHighOpticalInputPowerWarningInhibit OBJECT-TYPE
		SYNTAX  	INTEGER
		MAX-ACCESS  	read-write
		STATUS  	current

		DESCRIPTION
		"Inhibits msaBaEdfa High Input Power Warning
		for the receiving port. Set and Get succeed upon
		valid inhibition status.
		-----------------------------
		Values:
		0 or 1
		eg: 0
		-----------------------------"

		::= { msaEdfaConfigurationEntry 262 }	

	msaBaEdfaLowOpticalOutputPowerWarningInhibit OBJECT-TYPE
		SYNTAX  	INTEGER
		MAX-ACCESS  	read-write
		STATUS  	current

		DESCRIPTION
		"Inhibits msaBaEdfa Low Output Power Warning
		for the receiving port. Set and Get succeed upon
		valid inhibition status.
		-----------------------------
		Values:
		0 or 1
		eg: 0
		-----------------------------"

		::= { msaEdfaConfigurationEntry 263 }	

	msaBaEdfaHighOpticalOutputPowerWarningInhibit OBJECT-TYPE
		SYNTAX  	INTEGER
		MAX-ACCESS  	read-write
		STATUS  	current

		DESCRIPTION
		"Inhibits msaBaEdfa High Output Power Warning
		for the receiving port. Set and Get succeed upon
		valid inhibition status.
		-----------------------------
		Values:
		0 or 1
		eg: 0
		-----------------------------"

		::= { msaEdfaConfigurationEntry 264 }	

	msaBaEdfaLowTemperatureWarningInhibit OBJECT-TYPE
		SYNTAX  	INTEGER
		MAX-ACCESS  	read-write
		STATUS  	current

		DESCRIPTION
		"Inhibits msaBaEdfa Low Temperature Warning
		for the receiving port. Set and Get succeed upon
		valid inhibition status.
		-----------------------------
		Values:
		0 or 1
		eg: 0
		-----------------------------"

		::= { msaEdfaConfigurationEntry 265 }	

	msaBaEdfaHighTemperatureWarningInhibit OBJECT-TYPE
		SYNTAX  	INTEGER
		MAX-ACCESS  	read-write
		STATUS  	current

		DESCRIPTION
		"Inhibits msaBaEdfa High Temperature Warning
		for the receiving port. Set and Get succeed upon
		valid inhibition status.
		-----------------------------
		Values:
		0 or 1
		eg: 0
		-----------------------------"

		::= { msaEdfaConfigurationEntry 266 }

	msaBaEdfaLowOperatingCurrentWarningInhibit OBJECT-TYPE
		SYNTAX  	INTEGER
		MAX-ACCESS  	read-write
		STATUS  	current

		DESCRIPTION
		"Inhibits msaBaEdfa Low Operating Current Warning
		for the receiving port. Set and Get succeed upon
		valid inhibition status.
		-----------------------------
		Values:
		0 or 1
		eg: 0
		-----------------------------"

		::= { msaEdfaConfigurationEntry 267 }	

	msaBaEdfaHighOperatingCurrentWarningInhibit OBJECT-TYPE
		SYNTAX  	INTEGER
		MAX-ACCESS  	read-write
		STATUS  	current

		DESCRIPTION
		"Inhibits msaBaEdfa High Operating Current Warning
		for the receiving port. Set and Get succeed upon
		valid inhibition status.
		-----------------------------
		Values:
		0 or 1
		eg: 0
		-----------------------------"

		::= { msaEdfaConfigurationEntry 268 }	

	msaBaEdfaLowTECCurrentWarningInhibit OBJECT-TYPE
		SYNTAX  	INTEGER
		MAX-ACCESS  	read-write
		STATUS  	current

		DESCRIPTION
		"Inhibits msaBaEdfa Low TEC Current Warning
		for the receiving port. Set and Get succeed upon
		valid inhibition status.
		-----------------------------
		Values:
		0 or 1
		eg: 0
		-----------------------------"

		::= { msaEdfaConfigurationEntry 269 }

	msaBaEdfaHighTECCurrentWarningInhibit OBJECT-TYPE
		SYNTAX  	INTEGER
		MAX-ACCESS  	read-write
		STATUS  	current

		DESCRIPTION
		"Inhibits msaBaEdfa High TEC Current Warning
		for the receiving port. Set and Get succeed upon
		valid inhibition status.
		-----------------------------
		Values:
		0 or 1
		eg: 0
		-----------------------------"

		::= { msaEdfaConfigurationEntry 270 }	

	msaBaEdfaLowVoaInputPowerWarningInhibit OBJECT-TYPE
		SYNTAX  	INTEGER
		MAX-ACCESS  	read-write
		STATUS  	current

		DESCRIPTION
		"Inhibits msaBaEdfa Low Voa Input Power Warning
		for the receiving port. Set and Get succeed upon
		valid inhibition status.
		-----------------------------
		Values:
		0 or 1
		eg: 0
		-----------------------------"

		::= { msaEdfaConfigurationEntry 271 }

	msaBaEdfaHighVoaInputPowerWarningInhibit OBJECT-TYPE
		SYNTAX  	INTEGER
		MAX-ACCESS  	read-write
		STATUS  	current

		DESCRIPTION
		"Inhibits msaBaEdfa High Voa Input Power Warning
		for the receiving port. Set and Get succeed upon
		valid inhibition status.
		-----------------------------
		Values:
		0 or 1
		eg: 0
		-----------------------------"

		::= { msaEdfaConfigurationEntry 272 }

	msaBaEdfaInputOutOfRangeWarningInhibit OBJECT-TYPE
		SYNTAX  	INTEGER
		MAX-ACCESS  	read-write
		STATUS  	current

		DESCRIPTION
		"Inhibits msaBaEdfa Input Out Of Range Warning
		for the receiving port. Set and Get succeed upon
		valid inhibition status.
		-----------------------------
		Values:
		0 or 1
		eg: 0
		-----------------------------"

		::= { msaEdfaConfigurationEntry 273 }

	msaBaEdfaOutputOutOfRangeWarningInhibit OBJECT-TYPE
		SYNTAX  	INTEGER
		MAX-ACCESS  	read-write
		STATUS  	current

		DESCRIPTION
		"Inhibits msaBaEdfa Output Out Of Range Warning
		for the receiving port. Set and Get succeed upon
		valid inhibition status.
		-----------------------------
		Values:
		0 or 1
		eg: 0
		-----------------------------"

		::= { msaEdfaConfigurationEntry 274 }

	msaBaEdfaModuleCommunicationWarningInhibit OBJECT-TYPE
		SYNTAX  	INTEGER
		MAX-ACCESS  	read-write
		STATUS  	current

		DESCRIPTION
		"Inhibits msaBaEdfa Module Communication Warning
		for the receiving port. Set and Get succeed upon
		valid inhibition status.
		-----------------------------
		Values:
		0 or 1
		eg: 0
		-----------------------------"

		::= { msaEdfaConfigurationEntry 275 }	

	msaPaEdfaOpticalInputPowerFailureAlarmSeverity OBJECT-TYPE
		SYNTAX  	DisplayString
		MAX-ACCESS  	read-write
		STATUS  	current

		DESCRIPTION
		"Severity msaPaEdfa Input Power Failure Alarm
		for the receiving port. Set and Get succeed upon
		valid Severity level.
		-----------------------------
		Values:
		critical major or minor
		eg: 0
		-----------------------------"

		::= { msaEdfaConfigurationEntry 276 }	

	msaPaEdfaOpticalOutputPowerFailureAlarmSeverity OBJECT-TYPE
		SYNTAX  	DisplayString
		MAX-ACCESS  	read-write
		STATUS  	current

		DESCRIPTION
		"Severity msaPaEdfa Output Power Failure Alarm
		for the receiving port. Set and Get succeed upon
		valid Severity level.
		-----------------------------
		Values:
		critical major or minor
		eg: 0
		-----------------------------"

		::= { msaEdfaConfigurationEntry 277 }

	msaPaEdfaLowOpticalInputPowerAlarmSeverity OBJECT-TYPE
		SYNTAX  	DisplayString
		MAX-ACCESS  	read-write
		STATUS  	current

		DESCRIPTION
		"Severity msaPaEdfa Low Input Power Alarm
		for the receiving port. Set and Get succeed upon
		valid Severity level.
		-----------------------------
		Values:
		critical major or minor
		eg: 0
		-----------------------------"

		::= { msaEdfaConfigurationEntry 278 }	

	msaPaEdfaHighOpticalInputPowerAlarmSeverity OBJECT-TYPE
		SYNTAX  	DisplayString
		MAX-ACCESS  	read-write
		STATUS  	current

		DESCRIPTION
		"Severity msaPaEdfa High Input Power Alarm
		for the receiving port. Set and Get succeed upon
		valid Severity level.
		-----------------------------
		Values:
		critical major or minor
		eg: 0
		-----------------------------"

		::= { msaEdfaConfigurationEntry 279 }	

	msaPaEdfaLowOpticalOutputPowerAlarmSeverity OBJECT-TYPE
		SYNTAX  	DisplayString
		MAX-ACCESS  	read-write
		STATUS  	current

		DESCRIPTION
		"Severity msaPaEdfa Low Output Power Alarm
		for the receiving port. Set and Get succeed upon
		valid Severity level.
		-----------------------------
		Values:
		critical major or minor
		eg: 0
		-----------------------------"

		::= { msaEdfaConfigurationEntry 280 }	

	msaPaEdfaHighOpticalOutputPowerAlarmSeverity OBJECT-TYPE
		SYNTAX  	DisplayString
		MAX-ACCESS  	read-write
		STATUS  	current

		DESCRIPTION
		"Severity msaPaEdfa High Output Power Alarm
		for the receiving port. Set and Get succeed upon
		valid Severity level.
		-----------------------------
		Values:
		critical major or minor
		eg: 0
		-----------------------------"

		::= { msaEdfaConfigurationEntry 281 }	

	msaPaEdfaLowTemperatureAlarmSeverity OBJECT-TYPE
		SYNTAX  	DisplayString
		MAX-ACCESS  	read-write
		STATUS  	current

		DESCRIPTION
		"Severity msaPaEdfa Low Temperature Alarm
		for the receiving port. Set and Get succeed upon
		valid Severity level.
		-----------------------------
		Values:
		critical major or minor
		eg: 0
		-----------------------------"

		::= { msaEdfaConfigurationEntry 282 }	

	msaPaEdfaHighTemperatureAlarmSeverity OBJECT-TYPE
		SYNTAX  	DisplayString
		MAX-ACCESS  	read-write
		STATUS  	current

		DESCRIPTION
		"Severity msaPaEdfa High Temperature Alarm
		for the receiving port. Set and Get succeed upon
		valid Severity level.
		-----------------------------
		Values:
		critical major or minor
		eg: 0
		-----------------------------"

		::= { msaEdfaConfigurationEntry 283 }

	msaPaEdfaLowOperatingCurrentAlarmSeverity OBJECT-TYPE
		SYNTAX  	DisplayString
		MAX-ACCESS  	read-write
		STATUS  	current

		DESCRIPTION
		"Severity msaPaEdfa Low Operating Current Alarm
		for the receiving port. Set and Get succeed upon
		valid Severity level.
		-----------------------------
		Values:
		critical major or minor
		eg: 0
		-----------------------------"

		::= { msaEdfaConfigurationEntry 284 }	

	msaPaEdfaHighOperatingCurrentAlarmSeverity OBJECT-TYPE
		SYNTAX  	DisplayString
		MAX-ACCESS  	read-write
		STATUS  	current

		DESCRIPTION
		"Severity msaPaEdfa High Operating Current Alarm
		for the receiving port. Set and Get succeed upon
		valid Severity level.
		-----------------------------
		Values:
		critical major or minor
		eg: 0
		-----------------------------"

		::= { msaEdfaConfigurationEntry 285 }	

	msaPaEdfaLowTECCurrentAlarmSeverity OBJECT-TYPE
		SYNTAX  	DisplayString
		MAX-ACCESS  	read-write
		STATUS  	current

		DESCRIPTION
		"Severity msaPaEdfa Low TEC Current Alarm
		for the receiving port. Set and Get succeed upon
		valid Severity level.
		-----------------------------
		Values:
		critical major or minor
		eg: 0
		-----------------------------"

		::= { msaEdfaConfigurationEntry 286 }

	msaPaEdfaHighTECCurrentAlarmSeverity OBJECT-TYPE
		SYNTAX  	DisplayString
		MAX-ACCESS  	read-write
		STATUS  	current

		DESCRIPTION
		"Severity msaPaEdfa High TEC Current Alarm
		for the receiving port. Set and Get succeed upon
		valid Severity level.
		-----------------------------
		Values:
		critical major or minor
		eg: 0
		-----------------------------"

		::= { msaEdfaConfigurationEntry 287 }	

	msaPaEdfaLowVoaInputPowerAlarmSeverity OBJECT-TYPE
		SYNTAX  	DisplayString
		MAX-ACCESS  	read-write
		STATUS  	current

		DESCRIPTION
		"Severity msaPaEdfa Low Voa Input Power Alarm
		for the receiving port. Set and Get succeed upon
		valid Severity level.
		-----------------------------
		Values:
		critical major or minor
		eg: 0
		-----------------------------"

		::= { msaEdfaConfigurationEntry 288 }

	msaPaEdfaHighVoaInputPowerAlarmSeverity OBJECT-TYPE
		SYNTAX  	DisplayString
		MAX-ACCESS  	read-write
		STATUS  	current

		DESCRIPTION
		"Severity msaPaEdfa High Voa Input Power Alarm
		for the receiving port. Set and Get succeed upon
		valid Severity level.
		-----------------------------
		Values:
		critical major or minor
		eg: 0
		-----------------------------"

		::= { msaEdfaConfigurationEntry 289 }

	msaPaEdfaInputOutOfRangeAlarmSeverity OBJECT-TYPE
		SYNTAX  	DisplayString
		MAX-ACCESS  	read-write
		STATUS  	current

		DESCRIPTION
		"Severity msaPaEdfa Input Out Of Range Alarm
		for the receiving port. Set and Get succeed upon
		valid Severity level.
		-----------------------------
		Values:
		critical major or minor
		eg: 0
		-----------------------------"

		::= { msaEdfaConfigurationEntry 290 }

	msaPaEdfaOutputOutOfRangeAlarmSeverity OBJECT-TYPE
		SYNTAX  	DisplayString
		MAX-ACCESS  	read-write
		STATUS  	current

		DESCRIPTION
		"Severity msaPaEdfa Output Out Of Range Alarm
		for the receiving port. Set and Get succeed upon
		valid Severity level.
		-----------------------------
		Values:
		critical major or minor
		eg: 0
		-----------------------------"

		::= { msaEdfaConfigurationEntry 291 }

	msaPaEdfaModuleCommunicationAlarmSeverity OBJECT-TYPE
		SYNTAX  	DisplayString
		MAX-ACCESS  	read-write
		STATUS  	current

		DESCRIPTION
		"Severity msaPaEdfa Module Communication Alarm
		for the receiving port. Set and Get succeed upon
		valid Severity level.
		-----------------------------
		Values:
		critical major or minor
		eg: 0
		-----------------------------"

		::= { msaEdfaConfigurationEntry 292 }

	msaPaEdfaOpticalInputPowerFailureWarningSeverity OBJECT-TYPE
		SYNTAX  	DisplayString
		MAX-ACCESS  	read-write
		STATUS  	current

		DESCRIPTION
		"Severity msaPaEdfa Input Power Failure Warning
		for the receiving port. Set and Get succeed upon
		valid Severity level.
		-----------------------------
		Values:
		critical major or minor
		eg: 0
		-----------------------------"

		::= { msaEdfaConfigurationEntry 293 }	

	msaPaEdfaOpticalOutputPowerFailureWarningSeverity OBJECT-TYPE
		SYNTAX  	DisplayString
		MAX-ACCESS  	read-write
		STATUS  	current

		DESCRIPTION
		"Severity msaPaEdfa Output Power Failure Warning
		for the receiving port. Set and Get succeed upon
		valid Severity level.
		-----------------------------
		Values:
		critical major or minor
		eg: 0
		-----------------------------"

		::= { msaEdfaConfigurationEntry 294 }

	msaPaEdfaLowOpticalInputPowerWarningSeverity OBJECT-TYPE
		SYNTAX  	DisplayString
		MAX-ACCESS  	read-write
		STATUS  	current

		DESCRIPTION
		"Severity msaPaEdfa Low Input Power Warning
		for the receiving port. Set and Get succeed upon
		valid Severity level.
		-----------------------------
		Values:
		critical major or minor
		eg: 0
		-----------------------------"

		::= { msaEdfaConfigurationEntry 295 }	

	msaPaEdfaHighOpticalInputPowerWarningSeverity OBJECT-TYPE
		SYNTAX  	DisplayString
		MAX-ACCESS  	read-write
		STATUS  	current

		DESCRIPTION
		"Severity msaPaEdfa High Input Power Warning
		for the receiving port. Set and Get succeed upon
		valid Severity level.
		-----------------------------
		Values:
		critical major or minor
		eg: 0
		-----------------------------"

		::= { msaEdfaConfigurationEntry 296 }	

	msaPaEdfaLowOpticalOutputPowerWarningSeverity OBJECT-TYPE
		SYNTAX  	DisplayString
		MAX-ACCESS  	read-write
		STATUS  	current

		DESCRIPTION
		"Severity msaPaEdfa Low Output Power Warning
		for the receiving port. Set and Get succeed upon
		valid Severity level.
		-----------------------------
		Values:
		critical major or minor
		eg: 0
		-----------------------------"

		::= { msaEdfaConfigurationEntry 297 }	

	msaPaEdfaHighOpticalOutputPowerWarningSeverity OBJECT-TYPE
		SYNTAX  	DisplayString
		MAX-ACCESS  	read-write
		STATUS  	current

		DESCRIPTION
		"Severity msaPaEdfa High Output Power Warning
		for the receiving port. Set and Get succeed upon
		valid Severity level.
		-----------------------------
		Values:
		critical major or minor
		eg: 0
		-----------------------------"

		::= { msaEdfaConfigurationEntry 298 }	

	msaPaEdfaLowTemperatureWarningSeverity OBJECT-TYPE
		SYNTAX  	DisplayString
		MAX-ACCESS  	read-write
		STATUS  	current

		DESCRIPTION
		"Severity msaPaEdfa Low Temperature Warning
		for the receiving port. Set and Get succeed upon
		valid Severity level.
		-----------------------------
		Values:
		critical major or minor
		eg: 0
		-----------------------------"

		::= { msaEdfaConfigurationEntry 299 }	

	msaPaEdfaHighTemperatureWarningSeverity OBJECT-TYPE
		SYNTAX  	DisplayString
		MAX-ACCESS  	read-write
		STATUS  	current

		DESCRIPTION
		"Severity msaPaEdfa High Temperature Warning
		for the receiving port. Set and Get succeed upon
		valid Severity level.
		-----------------------------
		Values:
		critical major or minor
		eg: 0
		-----------------------------"

		::= { msaEdfaConfigurationEntry 300 }

	msaPaEdfaLowOperatingCurrentWarningSeverity OBJECT-TYPE
		SYNTAX  	DisplayString
		MAX-ACCESS  	read-write
		STATUS  	current

		DESCRIPTION
		"Severity msaPaEdfa Low Operating Current Warning
		for the receiving port. Set and Get succeed upon
		valid Severity level.
		-----------------------------
		Values:
		critical major or minor
		eg: 0
		-----------------------------"

		::= { msaEdfaConfigurationEntry 301 }	

	msaPaEdfaHighOperatingCurrentWarningSeverity OBJECT-TYPE
		SYNTAX  	DisplayString
		MAX-ACCESS  	read-write
		STATUS  	current

		DESCRIPTION
		"Severity msaPaEdfa High Operating Current Warning
		for the receiving port. Set and Get succeed upon
		valid Severity level.
		-----------------------------
		Values:
		critical major or minor
		eg: 0
		-----------------------------"

		::= { msaEdfaConfigurationEntry 302 }	

	msaPaEdfaLowTECCurrentWarningSeverity OBJECT-TYPE
		SYNTAX  	DisplayString
		MAX-ACCESS  	read-write
		STATUS  	current

		DESCRIPTION
		"Severity msaPaEdfa Low TEC Current Warning
		for the receiving port. Set and Get succeed upon
		valid Severity level.
		-----------------------------
		Values:
		critical major or minor
		eg: 0
		-----------------------------"

		::= { msaEdfaConfigurationEntry 303 }

	msaPaEdfaHighTECCurrentWarningSeverity OBJECT-TYPE
		SYNTAX  	DisplayString
		MAX-ACCESS  	read-write
		STATUS  	current

		DESCRIPTION
		"Severity msaPaEdfa High TEC Current Warning
		for the receiving port. Set and Get succeed upon
		valid Severity level.
		-----------------------------
		Values:
		critical major or minor
		eg: 0
		-----------------------------"

		::= { msaEdfaConfigurationEntry 304 }	

	msaPaEdfaLowVoaInputPowerWarningSeverity OBJECT-TYPE
		SYNTAX  	DisplayString
		MAX-ACCESS  	read-write
		STATUS  	current

		DESCRIPTION
		"Severity msaPaEdfa Low Voa Input Power Warning
		for the receiving port. Set and Get succeed upon
		valid Severity level.
		-----------------------------
		Values:
		critical major or minor
		eg: 0
		-----------------------------"

		::= { msaEdfaConfigurationEntry 305 }

	msaPaEdfaHighVoaInputPowerWarningSeverity OBJECT-TYPE
		SYNTAX  	DisplayString
		MAX-ACCESS  	read-write
		STATUS  	current

		DESCRIPTION
		"Severity msaPaEdfa High Voa Input Power Warning
		for the receiving port. Set and Get succeed upon
		valid Severity level.
		-----------------------------
		Values:
		critical major or minor
		eg: 0
		-----------------------------"

		::= { msaEdfaConfigurationEntry 306 }

	msaPaEdfaInputOutOfRangeWarningSeverity OBJECT-TYPE
		SYNTAX  	DisplayString
		MAX-ACCESS  	read-write
		STATUS  	current

		DESCRIPTION
		"Severity msaPaEdfa Input Out Of Range Warning
		for the receiving port. Set and Get succeed upon
		valid Severity level.
		-----------------------------
		Values:
		critical major or minor
		eg: 0
		-----------------------------"

		::= { msaEdfaConfigurationEntry 307 }

	msaPaEdfaOutputOutOfRangeWarningSeverity OBJECT-TYPE
		SYNTAX  	DisplayString
		MAX-ACCESS  	read-write
		STATUS  	current

		DESCRIPTION
		"Severity msaPaEdfa Output Out Of Range Warning
		for the receiving port. Set and Get succeed upon
		valid Severity level.
		-----------------------------
		Values:
		critical major or minor
		eg: 0
		-----------------------------"

		::= { msaEdfaConfigurationEntry 308 }

	msaPaEdfaModuleCommunicationWarningSeverity OBJECT-TYPE
		SYNTAX  	DisplayString
		MAX-ACCESS  	read-write
		STATUS  	current

		DESCRIPTION
		"Severity msaPaEdfa Module Communication Warning
		for the receiving port. Set and Get succeed upon
		valid Severity level.
		-----------------------------
		Values:
		critical major or minor
		eg: 0
		-----------------------------"

		::= { msaEdfaConfigurationEntry 309 }	

	msaBaEdfaOpticalInputPowerFailureAlarmSeverity OBJECT-TYPE
		SYNTAX  	DisplayString
		MAX-ACCESS  	read-write
		STATUS  	current

		DESCRIPTION
		"Severity msaBaEdfa Input Power Failure Alarm
		for the receiving port. Set and Get succeed upon
		valid Severity level.
		-----------------------------
		Values:
		critical major or minor
		eg: 0
		-----------------------------"

		::= { msaEdfaConfigurationEntry 310 }	

	msaBaEdfaOpticalOutputPowerFailureAlarmSeverity OBJECT-TYPE
		SYNTAX  	DisplayString
		MAX-ACCESS  	read-write
		STATUS  	current

		DESCRIPTION
		"Severity msaBaEdfa Output Power Failure Alarm
		for the receiving port. Set and Get succeed upon
		valid Severity level.
		-----------------------------
		Values:
		critical major or minor
		eg: 0
		-----------------------------"

		::= { msaEdfaConfigurationEntry 311 }

	msaBaEdfaLowOpticalInputPowerAlarmSeverity OBJECT-TYPE
		SYNTAX  	DisplayString
		MAX-ACCESS  	read-write
		STATUS  	current

		DESCRIPTION
		"Severity msaBaEdfa Low Input Power Alarm
		for the receiving port. Set and Get succeed upon
		valid Severity level.
		-----------------------------
		Values:
		critical major or minor
		eg: 0
		-----------------------------"

		::= { msaEdfaConfigurationEntry 312 }	

	msaBaEdfaHighOpticalInputPowerAlarmSeverity OBJECT-TYPE
		SYNTAX  	DisplayString
		MAX-ACCESS  	read-write
		STATUS  	current

		DESCRIPTION
		"Severity msaBaEdfa High Input Power Alarm
		for the receiving port. Set and Get succeed upon
		valid Severity level.
		-----------------------------
		Values:
		critical major or minor
		eg: 0
		-----------------------------"

		::= { msaEdfaConfigurationEntry 313 }	

	msaBaEdfaLowOpticalOutputPowerAlarmSeverity OBJECT-TYPE
		SYNTAX  	DisplayString
		MAX-ACCESS  	read-write
		STATUS  	current

		DESCRIPTION
		"Severity msaBaEdfa Low Output Power Alarm
		for the receiving port. Set and Get succeed upon
		valid Severity level.
		-----------------------------
		Values:
		critical major or minor
		eg: 0
		-----------------------------"

		::= { msaEdfaConfigurationEntry 314 }	

	msaBaEdfaHighOpticalOutputPowerAlarmSeverity OBJECT-TYPE
		SYNTAX  	DisplayString
		MAX-ACCESS  	read-write
		STATUS  	current

		DESCRIPTION
		"Severity msaBaEdfa High Output Power Alarm
		for the receiving port. Set and Get succeed upon
		valid Severity level.
		-----------------------------
		Values:
		critical major or minor
		eg: 0
		-----------------------------"

		::= { msaEdfaConfigurationEntry 315 }	

	msaBaEdfaLowTemperatureAlarmSeverity OBJECT-TYPE
		SYNTAX  	DisplayString
		MAX-ACCESS  	read-write
		STATUS  	current

		DESCRIPTION
		"Severity msaBaEdfa Low Temperature Alarm
		for the receiving port. Set and Get succeed upon
		valid Severity level.
		-----------------------------
		Values:
		critical major or minor
		eg: 0
		-----------------------------"

		::= { msaEdfaConfigurationEntry 316 }	

	msaBaEdfaHighTemperatureAlarmSeverity OBJECT-TYPE
		SYNTAX  	DisplayString
		MAX-ACCESS  	read-write
		STATUS  	current

		DESCRIPTION
		"Severity msaBaEdfa High Temperature Alarm
		for the receiving port. Set and Get succeed upon
		valid Severity level.
		-----------------------------
		Values:
		critical major or minor
		eg: 0
		-----------------------------"

		::= { msaEdfaConfigurationEntry 317 }

	msaBaEdfaLowOperatingCurrentAlarmSeverity OBJECT-TYPE
		SYNTAX  	DisplayString
		MAX-ACCESS  	read-write
		STATUS  	current

		DESCRIPTION
		"Severity msaBaEdfa Low Operating Current Alarm
		for the receiving port. Set and Get succeed upon
		valid Severity level.
		-----------------------------
		Values:
		critical major or minor
		eg: 0
		-----------------------------"

		::= { msaEdfaConfigurationEntry 318 }	

	msaBaEdfaHighOperatingCurrentAlarmSeverity OBJECT-TYPE
		SYNTAX  	DisplayString
		MAX-ACCESS  	read-write
		STATUS  	current

		DESCRIPTION
		"Severity msaBaEdfa High Operating Current Alarm
		for the receiving port. Set and Get succeed upon
		valid Severity level.
		-----------------------------
		Values:
		critical major or minor
		eg: 0
		-----------------------------"

		::= { msaEdfaConfigurationEntry 319 }	

	msaBaEdfaLowTECCurrentAlarmSeverity OBJECT-TYPE
		SYNTAX  	DisplayString
		MAX-ACCESS  	read-write
		STATUS  	current

		DESCRIPTION
		"Severity msaBaEdfa Low TEC Current Alarm
		for the receiving port. Set and Get succeed upon
		valid Severity level.
		-----------------------------
		Values:
		critical major or minor
		eg: 0
		-----------------------------"

		::= { msaEdfaConfigurationEntry 320 }

	msaBaEdfaHighTECCurrentAlarmSeverity OBJECT-TYPE
		SYNTAX  	DisplayString
		MAX-ACCESS  	read-write
		STATUS  	current

		DESCRIPTION
		"Severity msaBaEdfa High TEC Current Alarm
		for the receiving port. Set and Get succeed upon
		valid Severity level.
		-----------------------------
		Values:
		critical major or minor
		eg: 0
		-----------------------------"

		::= { msaEdfaConfigurationEntry 321 }	

	msaBaEdfaLowVoaInputPowerAlarmSeverity OBJECT-TYPE
		SYNTAX  	DisplayString
		MAX-ACCESS  	read-write
		STATUS  	current

		DESCRIPTION
		"Severity msaBaEdfa Low Voa Input Power Alarm
		for the receiving port. Set and Get succeed upon
		valid Severity level.
		-----------------------------
		Values:
		critical major or minor
		eg: 0
		-----------------------------"

		::= { msaEdfaConfigurationEntry 323 }

	msaBaEdfaHighVoaInputPowerAlarmSeverity OBJECT-TYPE
		SYNTAX  	DisplayString
		MAX-ACCESS  	read-write
		STATUS  	current

		DESCRIPTION
		"Severity msaBaEdfa High Voa Input Power Alarm
		for the receiving port. Set and Get succeed upon
		valid Severity level.
		-----------------------------
		Values:
		critical major or minor
		eg: 0
		-----------------------------"

		::= { msaEdfaConfigurationEntry 324 }

	msaBaEdfaInputOutOfRangeAlarmSeverity OBJECT-TYPE
		SYNTAX  	DisplayString
		MAX-ACCESS  	read-write
		STATUS  	current

		DESCRIPTION
		"Severity msaBaEdfa Input Out Of Range Alarm
		for the receiving port. Set and Get succeed upon
		valid Severity level.
		-----------------------------
		Values:
		critical major or minor
		eg: 0
		-----------------------------"

		::= { msaEdfaConfigurationEntry 325 }

	msaBaEdfaOutputOutOfRangeAlarmSeverity OBJECT-TYPE
		SYNTAX  	DisplayString
		MAX-ACCESS  	read-write
		STATUS  	current

		DESCRIPTION
		"Severity msaBaEdfa Output Out Of Range Alarm
		for the receiving port. Set and Get succeed upon
		valid Severity level.
		-----------------------------
		Values:
		critical major or minor
		eg: 0
		-----------------------------"

		::= { msaEdfaConfigurationEntry 326 }

	msaBaEdfaModuleCommunicationAlarmSeverity OBJECT-TYPE
		SYNTAX  	DisplayString
		MAX-ACCESS  	read-write
		STATUS  	current

		DESCRIPTION
		"Severity msaBaEdfa Module Communication Alarm
		for the receiving port. Set and Get succeed upon
		valid Severity level.
		-----------------------------
		Values:
		critical major or minor
		eg: 0
		-----------------------------"

		::= { msaEdfaConfigurationEntry 327 }

	msaBaEdfaOpticalInputPowerFailureWarningSeverity OBJECT-TYPE
		SYNTAX  	DisplayString
		MAX-ACCESS  	read-write
		STATUS  	current

		DESCRIPTION
		"Severity msaBaEdfa Input Power Failure Warning
		for the receiving port. Set and Get succeed upon
		valid Severity level.
		-----------------------------
		Values:
		critical major or minor
		eg: 0
		-----------------------------"

		::= { msaEdfaConfigurationEntry 328 }	

	msaBaEdfaOpticalOutputPowerFailureWarningSeverity OBJECT-TYPE
		SYNTAX  	DisplayString
		MAX-ACCESS  	read-write
		STATUS  	current

		DESCRIPTION
		"Severity msaBaEdfa Output Power Failure Warning
		for the receiving port. Set and Get succeed upon
		valid Severity level.
		-----------------------------
		Values:
		critical major or minor
		eg: 0
		-----------------------------"

		::= { msaEdfaConfigurationEntry 329 }

	msaBaEdfaLowOpticalInputPowerWarningSeverity OBJECT-TYPE
		SYNTAX  	DisplayString
		MAX-ACCESS  	read-write
		STATUS  	current

		DESCRIPTION
		"Severity msaBaEdfa Low Input Power Warning
		for the receiving port. Set and Get succeed upon
		valid Severity level.
		-----------------------------
		Values:
		critical major or minor
		eg: 0
		-----------------------------"

		::= { msaEdfaConfigurationEntry 330 }	

	msaBaEdfaHighOpticalInputPowerWarningSeverity OBJECT-TYPE
		SYNTAX  	DisplayString
		MAX-ACCESS  	read-write
		STATUS  	current

		DESCRIPTION
		"Severity msaBaEdfa High Input Power Warning
		for the receiving port. Set and Get succeed upon
		valid Severity level.
		-----------------------------
		Values:
		critical major or minor
		eg: 0
		-----------------------------"

		::= { msaEdfaConfigurationEntry 331 }	

	msaBaEdfaLowOpticalOutputPowerWarningSeverity OBJECT-TYPE
		SYNTAX  	DisplayString
		MAX-ACCESS  	read-write
		STATUS  	current

		DESCRIPTION
		"Severity msaBaEdfa Low Output Power Warning
		for the receiving port. Set and Get succeed upon
		valid Severity level.
		-----------------------------
		Values:
		critical major or minor
		eg: 0
		-----------------------------"

		::= { msaEdfaConfigurationEntry 332 }	

	msaBaEdfaHighOpticalOutputPowerWarningSeverity OBJECT-TYPE
		SYNTAX  	DisplayString
		MAX-ACCESS  	read-write
		STATUS  	current

		DESCRIPTION
		"Severity msaBaEdfa High Output Power Warning
		for the receiving port. Set and Get succeed upon
		valid Severity level.
		-----------------------------
		Values:
		critical major or minor
		eg: 0
		-----------------------------"

		::= { msaEdfaConfigurationEntry 333 }	

	msaBaEdfaLowTemperatureWarningSeverity OBJECT-TYPE
		SYNTAX  	DisplayString
		MAX-ACCESS  	read-write
		STATUS  	current

		DESCRIPTION
		"Severity msaBaEdfa Low Temperature Warning
		for the receiving port. Set and Get succeed upon
		valid Severity level.
		-----------------------------
		Values:
		critical major or minor
		eg: 0
		-----------------------------"

		::= { msaEdfaConfigurationEntry 334 }	

	msaBaEdfaHighTemperatureWarningSeverity OBJECT-TYPE
		SYNTAX  	DisplayString
		MAX-ACCESS  	read-write
		STATUS  	current

		DESCRIPTION
		"Severity msaBaEdfa High Temperature Warning
		for the receiving port. Set and Get succeed upon
		valid Severity level.
		-----------------------------
		Values:
		critical major or minor
		eg: 0
		-----------------------------"

		::= { msaEdfaConfigurationEntry 335 }

	msaBaEdfaLowOperatingCurrentWarningSeverity OBJECT-TYPE
		SYNTAX  	DisplayString
		MAX-ACCESS  	read-write
		STATUS  	current

		DESCRIPTION
		"Severity msaBaEdfa Low Operating Current Warning
		for the receiving port. Set and Get succeed upon
		valid Severity level.
		-----------------------------
		Values:
		critical major or minor
		eg: 0
		-----------------------------"

		::= { msaEdfaConfigurationEntry 336 }	

	msaBaEdfaHighOperatingCurrentWarningSeverity OBJECT-TYPE
		SYNTAX  	DisplayString
		MAX-ACCESS  	read-write
		STATUS  	current

		DESCRIPTION
		"Severity msaBaEdfa High Operating Current Warning
		for the receiving port. Set and Get succeed upon
		valid Severity level.
		-----------------------------
		Values:
		critical major or minor
		eg: 0
		-----------------------------"

		::= { msaEdfaConfigurationEntry 337 }	

	msaBaEdfaLowTECCurrentWarningSeverity OBJECT-TYPE
		SYNTAX  	DisplayString
		MAX-ACCESS  	read-write
		STATUS  	current

		DESCRIPTION
		"Severity msaBaEdfa Low TEC Current Warning
		for the receiving port. Set and Get succeed upon
		valid Severity level.
		-----------------------------
		Values:
		critical major or minor
		eg: 0
		-----------------------------"

		::= { msaEdfaConfigurationEntry 338 }

	msaBaEdfaHighTECCurrentWarningSeverity OBJECT-TYPE
		SYNTAX  	DisplayString
		MAX-ACCESS  	read-write
		STATUS  	current

		DESCRIPTION
		"Severity msaBaEdfa High TEC Current Warning
		for the receiving port. Set and Get succeed upon
		valid Severity level.
		-----------------------------
		Values:
		critical major or minor
		eg: 0
		-----------------------------"

		::= { msaEdfaConfigurationEntry 339 }	

	msaBaEdfaLowVoaInputPowerWarningSeverity OBJECT-TYPE
		SYNTAX  	DisplayString
		MAX-ACCESS  	read-write
		STATUS  	current

		DESCRIPTION
		"Severity msaBaEdfa Low Voa Input Power Warning
		for the receiving port. Set and Get succeed upon
		valid Severity level.
		-----------------------------
		Values:
		critical major or minor
		eg: 0
		-----------------------------"

		::= { msaEdfaConfigurationEntry 340 }

	msaBaEdfaHighVoaInputPowerWarningSeverity OBJECT-TYPE
		SYNTAX  	DisplayString
		MAX-ACCESS  	read-write
		STATUS  	current

		DESCRIPTION
		"Severity msaBaEdfa High Voa Input Power Warning
		for the receiving port. Set and Get succeed upon
		valid Severity level.
		-----------------------------
		Values:
		critical major or minor
		eg: 0
		-----------------------------"

		::= { msaEdfaConfigurationEntry 341 }

	msaBaEdfaInputOutOfRangeWarningSeverity OBJECT-TYPE
		SYNTAX  	DisplayString
		MAX-ACCESS  	read-write
		STATUS  	current

		DESCRIPTION
		"Severity msaBaEdfa Input Out Of Range Warning
		for the receiving port. Set and Get succeed upon
		valid Severity level.
		-----------------------------
		Values:
		critical major or minor
		eg: 0
		-----------------------------"

		::= { msaEdfaConfigurationEntry 342 }

	msaBaEdfaOutputOutOfRangeWarningSeverity OBJECT-TYPE
		SYNTAX  	DisplayString
		MAX-ACCESS  	read-write
		STATUS  	current

		DESCRIPTION
		"Severity msaBaEdfa Output Out Of Range Warning
		for the receiving port. Set and Get succeed upon
		valid Severity level.
		-----------------------------
		Values:
		critical major or minor
		eg: 0
		-----------------------------"

		::= { msaEdfaConfigurationEntry 343 }

	msaBaEdfaModuleCommunicationWarningSeverity OBJECT-TYPE
		SYNTAX  	DisplayString
		MAX-ACCESS  	read-write
		STATUS  	current

		DESCRIPTION
		"Severity msaBaEdfa Module Communication Warning
		for the receiving port. Set and Get succeed upon
		valid Severity level.
		-----------------------------
		Values:
		critical major or minor
		eg: 0
		-----------------------------"

		::= { msaEdfaConfigurationEntry 344 }	
	
	msaEdfaConfigurationTableRowStatus OBJECT-TYPE
		SYNTAX      RowStatus
		MAX-ACCESS  read-write
		STATUS      current
		DESCRIPTION
		 "This is MIB related property, NOT to be considered as a card property"

		::= { msaEdfaConfigurationEntry 345 }

--*****************************************************************************
--				MSA EDFA PERFORMANCE
--***************************************************************************** 

	msaEdfaPerformanceTable OBJECT-TYPE
		SYNTAX  	SEQUENCE OF MsaEdfaPerformanceEntry
		MAX-ACCESS  	not-accessible
		STATUS  	current

		DESCRIPTION
		 "we can get MSA EDFA card performance details "

		::= { msaEdfaPerformance 1 }
	      
	msaEdfaPerformanceEntry OBJECT-TYPE
		SYNTAX  	MsaEdfaPerformanceEntry
		MAX-ACCESS  	not-accessible
		STATUS  	current

		DESCRIPTION 
		 "Enter node rack, subrack, slot and msaEdfaInterface numbers"

		INDEX   { node, rack, subRack, slot, msaEdfaInterface }

		::= { msaEdfaPerformanceTable 1 }
	
	MsaEdfaPerformanceEntry ::= 
		SEQUENCE {
				msaPaEdfaModuleOpticalInputPower				DisplayString,
				msaPaEdfaModuleOpticalOutputPower				DisplayString,
				msaPaEdfaModuleTemperature						DisplayString,
				msaPaEdfaModulePump1TecCurrent					DisplayString,
				msaPaEdfaModuleVoaInputPower					DisplayString,
				msaPaEdfaModuleVoaOutputPower					DisplayString,
				msaPaEdfaModuleAmplifiedSpontaneousEmissionPower		DisplayString,
				msaPaEdfaModuleOutputSignalGain					DisplayString,
				msaPaEdfaModuleVoaActualAttenuation				DisplayString,
				msaPaEdfaModulePump1TchipTemperature			DisplayString,

				msaBaEdfaModuleOpticalInputPower				DisplayString,
				msaBaEdfaModuleOpticalOutputPower				DisplayString,
				msaBaEdfaModuleTemperature						DisplayString,
				msaBaEdfaModulePump1TecCurrent					DisplayString,
				msaBaEdfaModuleVoaInputPower					DisplayString,
				msaBaEdfaModuleVoaOutputPower					DisplayString,
				msaBaEdfaModuleAmplifiedSpontaneousEmissionPower		DisplayString,
				msaBaEdfaModuleOutputSignalGain					DisplayString,
				msaBaEdfaModuleVoaActualAttenuation				DisplayString,
				msaBaEdfaModulePump1TchipTemperature			DisplayString,

				msaEdfaPerformanceTableRowStatus				RowStatus
			}

	msaPaEdfaModuleOpticalInputPower OBJECT-TYPE
		SYNTAX  	DisplayString
		MAX-ACCESS  	read-only
		STATUS  	current

		DESCRIPTION
		 " to get MSA EDFA card input power 
		-----------------------------
		Values:
		eg: 1.5
		-----------------------------"

		::= { msaEdfaPerformanceEntry 1 }	 
	      
	msaPaEdfaModuleOpticalOutputPower OBJECT-TYPE
		SYNTAX  	DisplayString
		MAX-ACCESS  	read-only
		STATUS  	current

		DESCRIPTION
		 " to get MSA EDFA card output power 
		-----------------------------
		Values:
		eg: 18.5
		-----------------------------"
	
	      ::= { msaEdfaPerformanceEntry 2 }	 
	
	msaPaEdfaModuleTemperature OBJECT-TYPE
		SYNTAX  	DisplayString
		MAX-ACCESS  	read-only
		STATUS  	current

		DESCRIPTION
		 " to get MSA EDFA card module temperature.
		-----------------------------
		Values:
		eg: 18.5
		-----------------------------"

		::= { msaEdfaPerformanceEntry 3 }

	msaPaEdfaModulePump1TecCurrent OBJECT-TYPE
		SYNTAX  	DisplayString
		MAX-ACCESS  	read-only
		STATUS  	current

		DESCRIPTION
		 " to get MSA EDFA card pump 1 thermo electric cooler current.
		-----------------------------
		Values:
		eg: 18.5
		-----------------------------"
	
	      ::= { msaEdfaPerformanceEntry 4 }
	      
	msaPaEdfaModuleVoaInputPower OBJECT-TYPE
		SYNTAX  	DisplayString
		MAX-ACCESS  	read-only
		STATUS  	current

		DESCRIPTION
		 " to get MSA EDFA card variable optical attenuator input power.
		-----------------------------
		Values:
		eg: 18.5
		-----------------------------"

		::= { msaEdfaPerformanceEntry 5 }	

	msaPaEdfaModuleVoaOutputPower OBJECT-TYPE
		SYNTAX  	DisplayString
		MAX-ACCESS  	read-only
		STATUS  	current

		DESCRIPTION
		 " to get MSA EDFA card variable optical attenuator Output power.
		-----------------------------
		Values:
		eg: 18.5
		-----------------------------"

		::= { msaEdfaPerformanceEntry 6 }	
					      				
	msaPaEdfaModuleAmplifiedSpontaneousEmissionPower OBJECT-TYPE
		SYNTAX  	DisplayString
		MAX-ACCESS  	read-only
		STATUS  	current

		DESCRIPTION
		 " to get MSA EDFA card Amplified Spontaneous Emmission power .
		-----------------------------
		Values:
		eg: 2.5
		-----------------------------"

		::= { msaEdfaPerformanceEntry 7 }

	msaPaEdfaModuleOutputSignalGain OBJECT-TYPE
		SYNTAX  	DisplayString
		MAX-ACCESS  	read-only
		STATUS  	current

		DESCRIPTION
		 " to get MSA EDFA signal gain 
		-----------------------------
		Values:
		eg: 18.5
		-----------------------------"

		::= { msaEdfaPerformanceEntry 8 }

	msaPaEdfaModuleVoaActualAttenuation OBJECT-TYPE
		SYNTAX  	DisplayString
		MAX-ACCESS  	read-only
		STATUS  	current

		DESCRIPTION
		 " to get MSA EDFA card variable optical attenuator actual attenuation.
		-----------------------------
		Values:
		eg: 18.5
		-----------------------------"

		::= { msaEdfaPerformanceEntry 9 }

	msaPaEdfaModulePump1TchipTemperature OBJECT-TYPE
		SYNTAX  	DisplayString
		MAX-ACCESS  	read-only
		STATUS  	current

		DESCRIPTION
		 " to get MSA EDFA Module Pump Tchip Temperature.
		-----------------------------
		Values:
		eg: 18.5
		-----------------------------"

		::= { msaEdfaPerformanceEntry 10 }

-- ********************

	msaBaEdfaModuleOpticalInputPower OBJECT-TYPE
		SYNTAX  	DisplayString
		MAX-ACCESS  	read-only
		STATUS  	current

		DESCRIPTION
		 " to get MSA EDFA card input power 
		-----------------------------
		Values:
		eg: 1.5
		-----------------------------"

		::= { msaEdfaPerformanceEntry 11 }	 
	      
	msaBaEdfaModuleOpticalOutputPower OBJECT-TYPE
		SYNTAX  	DisplayString
		MAX-ACCESS  	read-only
		STATUS  	current

		DESCRIPTION
		 " to get MSA EDFA card output power 
		-----------------------------
		Values:
		eg: 18.5
		-----------------------------"
	
	      ::= { msaEdfaPerformanceEntry 12 }	 
	
	msaBaEdfaModuleTemperature OBJECT-TYPE
		SYNTAX  	DisplayString
		MAX-ACCESS  	read-only
		STATUS  	current

		DESCRIPTION
		 " to get MSA EDFA card module temperature.
		-----------------------------
		Values:
		eg: 18.5
		-----------------------------"

		::= { msaEdfaPerformanceEntry 13 }

	msaBaEdfaModulePump1TecCurrent OBJECT-TYPE
		SYNTAX  	DisplayString
		MAX-ACCESS  	read-only
		STATUS  	current

		DESCRIPTION
		 " to get MSA EDFA card pump 1 thermo electric cooler current.
		-----------------------------
		Values:
		eg: 18.5
		-----------------------------"
	
	      ::= { msaEdfaPerformanceEntry 14 }
	      
	msaBaEdfaModuleVoaInputPower OBJECT-TYPE
		SYNTAX  	DisplayString
		MAX-ACCESS  	read-only
		STATUS  	current

		DESCRIPTION
		 " to get MSA EDFA card variable optical attenuator input power.
		-----------------------------
		Values:
		eg: 18.5
		344-----------------------------"

		::= { msaEdfaPerformanceEntry 15 }

	msaBaEdfaModuleVoaOutputPower OBJECT-TYPE
		SYNTAX  	DisplayString
		MAX-ACCESS  	read-only
		STATUS  	current

		DESCRIPTION
		 " to get MSA EDFA card variable optical attenuator Output power.
		-----------------------------
		Values:
		eg: 18.5
		-----------------------------"

		::= { msaEdfaPerformanceEntry 16 }

	msaBaEdfaModuleAmplifiedSpontaneousEmissionPower OBJECT-TYPE
		SYNTAX  	DisplayString
		MAX-ACCESS  	read-only
		STATUS  	current

		DESCRIPTION
		 " to get MSA EDFA card Amplified Spontaneous Emmission power .
		-----------------------------
		Values:
		eg: 2.5
		-----------------------------"

		::= { msaEdfaPerformanceEntry 17 }

	msaBaEdfaModuleOutputSignalGain OBJECT-TYPE
		SYNTAX  	DisplayString
		MAX-ACCESS  	read-only
		STATUS  	current

		DESCRIPTION
		 " to get MSA EDFA signal gain 
		-----------------------------
		Values:
		eg: 18.5
		-----------------------------"

		::= { msaEdfaPerformanceEntry 18 }

	msaBaEdfaModuleVoaActualAttenuation OBJECT-TYPE
		SYNTAX  	DisplayString
		MAX-ACCESS  	read-only
		STATUS  	current

		DESCRIPTION
		 " to get MSA EDFA card variable optical attenuator actual attenuation.
		-----------------------------
		Values:
		eg: 18.5
		-----------------------------"

		::= { msaEdfaPerformanceEntry 19 }

	msaBaEdfaModulePump1TchipTemperature OBJECT-TYPE
		SYNTAX  	DisplayString
		MAX-ACCESS  	read-only
		STATUS  	current

		DESCRIPTION
		 " to get MSA EDFA Module Pump Tchip Temperature.
		-----------------------------
		Values:
		eg: 18.5
		-----------------------------"

		::= { msaEdfaPerformanceEntry 20 }

	msaEdfaPerformanceTableRowStatus OBJECT-TYPE
              SYNTAX      RowStatus
              MAX-ACCESS  read-write
              STATUS      current
              DESCRIPTION
                      "	This is MIB realted property,
			NOT to be considered as a card property"
              ::= { msaEdfaPerformanceEntry 21 }

--**********************************************************************************************
--				PA and BA Module Alarms
--**********************************************************************************************

	msaEdfaAlarmQueryTable 			OBJECT-TYPE
		SYNTAX  			SEQUENCE OF MsaEdfaAlarmQueryEntry
		MAX-ACCESS			not-accessible
		STATUS				current

		DESCRIPTION
		 " we can get MSA PA and BA EDFA module Alarms "

		::= { msaEdfaAlarmQuery 1 }

	msaEdfaAlarmQueryEntry 			OBJECT-TYPE
		SYNTAX  			MsaEdfaAlarmQueryEntry
		MAX-ACCESS  			not-accessible
		STATUS  			current

		DESCRIPTION 
		 "Enter node rack, subrack, slot and msaEdfaInterface numbers"

		INDEX   { node, rack, subRack, slot, msaEdfaInterface }

		::= { msaEdfaAlarmQueryTable 1 }

	MsaEdfaAlarmQueryEntry ::= 
		SEQUENCE {
					msaPaEdfaOpticalInputPowerFailureAlarm				DisplayString,
					msaPaEdfaOpticalOutputPowerFailureAlarm		                DisplayString,
					msaPaEdfaLowOpticalInputPowerAlarm                   		DisplayString,
					msaPaEdfaLowOpticalInputPowerWarning                  		DisplayString,
					msaPaEdfaHighOpticalInputPowerAlarm                   		DisplayString,
					msaPaEdfaHighOpticalInputPowerWarning                 		DisplayString,
					msaPaEdfaLowOpticalOutputPowerAlarm                   		DisplayString,
					msaPaEdfaLowOpticalOutputPowerWarning                  		DisplayString,
					msaPaEdfaHighOpticalOutputPowerAlarm                  		DisplayString,
					msaPaEdfaHighOpticalOutputPowerWarning                  	DisplayString,
					msaPaEdfaHighTemperatureAlarm                   		DisplayString,
					msaPaEdfaHighTemperatureWarning                  		DisplayString,
					msaPaEdfaLowTemperatureAlarm                   			DisplayString,
					msaPaEdfaLowTemperatureWarning                  		DisplayString,
					msaPaEdfaHighOperatingCurrentAlarm                   		DisplayString,
					msaPaEdfaHighOperatingCurrentWarning                  		DisplayString,
					msaPaEdfaLowOperatingCurrentAlarm                   		DisplayString,
					msaPaEdfaLowOperatingCurrentWarning                  		DisplayString,
					msaPaEdfaHighTECCurrentAlarm                   			DisplayString,
					msaPaEdfaHighTECCurrentWarning                  		DisplayString,
					msaPaEdfaLowTECCurrentAlarm                   			DisplayString,
					msaPaEdfaLowTECCurrentWarning                 			DisplayString,
					msaPaEdfaHighVoaInputPowerAlarm                   		DisplayString,
					msaPaEdfaHighVoaInputPowerWarning                  		DisplayString,
					msaPaEdfaLowVoaInputPowerAlarm                   		DisplayString,
					msaPaEdfaLowVoaInputPowerWarning                  		DisplayString,
					msaPaEdfaInputOutOfRangeAlarm                   		DisplayString,
					msaPaEdfaOutputOutOfRangeAlarm                  		DisplayString,
					msaPaEdfaModuleCommunicationAlarm				DisplayString,
					msaBaEdfaOpticalInputPowerFailureAlarm				DisplayString,
					msaBaEdfaOpticalOutputPowerFailureAlarm		                DisplayString,
					msaBaEdfaLowOpticalInputPowerAlarm                   		DisplayString,
					msaBaEdfaLowOpticalInputPowerWarning                  		DisplayString,
					msaBaEdfaHighOpticalInputPowerAlarm                   		DisplayString,
					msaBaEdfaHighOpticalInputPowerWarning                 		DisplayString,
					msaBaEdfaLowOpticalOutputPowerAlarm                   		DisplayString,
					msaBaEdfaLowOpticalOutputPowerWarning                  		DisplayString,
					msaBaEdfaHighOpticalOutputPowerAlarm                  		DisplayString,
					msaBaEdfaHighOpticalOutputPowerWarning                  	DisplayString,
					msaBaEdfaHighTemperatureAlarm                   		DisplayString,
					msaBaEdfaHighTemperatureWarning                  		DisplayString,
					msaBaEdfaLowTemperatureAlarm                   			DisplayString,
					msaBaEdfaLowTemperatureWarning                  		DisplayString,
					msaBaEdfaHighOperatingCurrentAlarm                   		DisplayString,
					msaBaEdfaHighOperatingCurrentWarning                  		DisplayString,
					msaBaEdfaLowOperatingCurrentAlarm                   		DisplayString,
					msaBaEdfaLowOperatingCurrentWarning                  		DisplayString,
					msaBaEdfaHighTECCurrentAlarm                   			DisplayString,
					msaBaEdfaHighTECCurrentWarning                  		DisplayString,
					msaBaEdfaLowTECCurrentAlarm                   			DisplayString,
					msaBaEdfaLowTECCurrentWarning                 			DisplayString,
					msaBaEdfaHighVoaInputPowerAlarm                   		DisplayString,
					msaBaEdfaHighVoaInputPowerWarning                  		DisplayString,
					msaBaEdfaLowVoaInputPowerAlarm                   		DisplayString,
					msaBaEdfaLowVoaInputPowerWarning                  		DisplayString,
					msaBaEdfaInputOutOfRangeAlarm                   		DisplayString,
					msaBaEdfaOutputOutOfRangeAlarm                  		DisplayString,
					msaBaEdfaModuleCommunicationAlarm				DisplayString,
					msaEdfaAlarmTableRowStatus					RowStatus
			}

msaPaEdfaOpticalInputPowerFailureAlarm  		OBJECT-TYPE
		SYNTAX  				DisplayString		
		MAX-ACCESS  				read-only
		STATUS  				current
		DESCRIPTION
							"the user can get the current status of the 
							Input Power Failure status. Whenever no receive 
							power is detected, this alarm 
							will be raised and if receive power is detected,then  
							this alarm will be cleared. 			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 1 }

msaPaEdfaOpticalOutputPowerFailureAlarm  		OBJECT-TYPE
		SYNTAX  				DisplayString		
		MAX-ACCESS  				read-only
		STATUS  				current
		DESCRIPTION
							"the user can get the current status of the 
							Output Power Failure status. Whenever the transmit
							laser is OFF, this alarm 
							will be raised and if transmit power is ON,then  
							this alarm will be cleared. 			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 2 }

msaPaEdfaLowOpticalInputPowerAlarm  			OBJECT-TYPE
		SYNTAX  				DisplayString		
		MAX-ACCESS  				read-only
		STATUS  				current
		DESCRIPTION
							"the user can get the current status of the 
							Low Input Power Alarm status. Whenever the receive 
							power is lesser then the Low input power Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 3 }

msaPaEdfaLowOpticalInputPowerWarning  			OBJECT-TYPE
		SYNTAX  				DisplayString		
		MAX-ACCESS  				read-only
		STATUS  				current
		DESCRIPTION
							"the user can get the current status of the 
							Low Input Power Warning status. Whenever the receive 
							power is lesser then the Low input power Warning threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 4 }

msaPaEdfaHighOpticalInputPowerAlarm  			OBJECT-TYPE
		SYNTAX  				DisplayString		
		MAX-ACCESS  				read-only
		STATUS  				current
		DESCRIPTION
							"the user can get the current status of the 
							High Input Power Alarm status. Whenever the receive 
							power is greater then the High input power Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 5 }

msaPaEdfaHighOpticalInputPowerWarning  			OBJECT-TYPE
		SYNTAX  				DisplayString		
		MAX-ACCESS  				read-only
		STATUS  				current
		DESCRIPTION
							"the user can get the current status of the 
							High Input Power Warning status. Whenever the receive 
							power is greater then the High input power Warning threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 6 }


msaPaEdfaLowOpticalOutputPowerAlarm  			OBJECT-TYPE
		SYNTAX  				DisplayString		
		MAX-ACCESS  				read-only
		STATUS  				current
		DESCRIPTION
							"the user can get the current status of the 
							Low Output Power Alarm status. Whenever the transmit 
							power is lesser then the Low input power Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 7 }

msaPaEdfaLowOpticalOutputPowerWarning  			OBJECT-TYPE
		SYNTAX  				DisplayString		
		MAX-ACCESS  				read-only
		STATUS  				current
		DESCRIPTION
							"the user can get the current status of the 
							Low Output Power Warning status. Whenever the transmit 
							power is lesser then the Low input power Warning threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 8 }

msaPaEdfaHighOpticalOutputPowerAlarm  			OBJECT-TYPE
		SYNTAX  				DisplayString		
		MAX-ACCESS  				read-only
		STATUS  				current
		DESCRIPTION
							"the user can get the current status of the 
							High Output Power Alarm status. Whenever the transmit 
							power is greater then the High Output power Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 9 }

msaPaEdfaHighOpticalOutputPowerWarning  		OBJECT-TYPE
		SYNTAX  				DisplayString		
		MAX-ACCESS  				read-only
		STATUS  				current
		DESCRIPTION
							"the user can get the current status of the 
							High Output Power Warning status. Whenever the receive 
							power is greater then the High Output power Warning threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 10 }

msaPaEdfaHighTemperatureAlarm	  			OBJECT-TYPE
		SYNTAX  				DisplayString		
		MAX-ACCESS  				read-only
		STATUS  				current
		DESCRIPTION
							"the user can get the current status of the 
							High Temperature Alarm status. Whenever the module
							greater then the High Temperature Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 11 }

msaPaEdfaHighTemperatureWarning	  			OBJECT-TYPE
		SYNTAX  				DisplayString		
		MAX-ACCESS  				read-only
		STATUS  				current
		DESCRIPTION
							"the user can get the current status of the 
							High Temperature Warning status. Whenever the module
							greater then the High Temperature Warning threshold, 
							this alarm will be raised and else it will be in cleared 								state			
							--------------------------------------------------------------------
							InterfaceNumber:
							Always 0
							--------------------------------------------------------------------
							Get response:
							If Alarm is Present - Date and Time Stamp
							eg:2017-5-18,9:47:20.0,+5:30
							If Alarm is Absent  - 0
							--------------------------------------------------------------------"
               	
		::= { msaEdfaAlarmQueryEntry 12 }

msaPaEdfaLowTemperatureAlarm	  			OBJECT-TYPE
		SYNTAX  				DisplayString		
		MAX-ACCESS  				read-only
		STATUS  				current
		DESCRIPTION
							"the user can get the current status of the 
							High Temperature Alarm status. Whenever the module
							lesser then the Low Temperature Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 13 }

msaPaEdfaLowTemperatureWarning	  			OBJECT-TYPE
		SYNTAX  				DisplayString		
		MAX-ACCESS  				read-only
		STATUS  				current
		DESCRIPTION
							"the user can get the current status of the 
							High Temperature Warning status. Whenever the module
							lesser then the low Temperature Warning threshold, 
							this alarm will be raised and else it will be in cleared 								state			
							--------------------------------------------------------------------
							InterfaceNumber:
							Always 0
							--------------------------------------------------------------------
							Get response:
							If Alarm is Present - Date and Time Stamp
							eg:2017-5-18,9:47:20.0,+5:30
							If Alarm is Absent  - 0
							--------------------------------------------------------------------"
               	
		::= { msaEdfaAlarmQueryEntry 14 }

msaPaEdfaHighOperatingCurrentAlarm	  		OBJECT-TYPE
		SYNTAX  				DisplayString		
		MAX-ACCESS  				read-only
		STATUS  				current
		DESCRIPTION
							"the user can get the current status of the 
							High Operating Current Alarm status. Whenever the Operating
							Current of the module is greater than High Operating current Alarm 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 15 }

msaPaEdfaHighOperatingCurrentWarning	  		OBJECT-TYPE
		SYNTAX  				DisplayString		
		MAX-ACCESS  				read-only
		STATUS  				current
		DESCRIPTION
							"the user can get the current status of the 
							High Operating Current Warning status. Whenever the Operating
							Current of the module is greater than High Operating current Warning 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 16 }


msaPaEdfaLowOperatingCurrentAlarm	  		OBJECT-TYPE
		SYNTAX  				DisplayString		
		MAX-ACCESS  				read-only
		STATUS  				current
		DESCRIPTION
							"the user can get the current status of the 
							High Operating Current Alarm status. Whenever the Operating
							Current of the module is lesser than Low Operating current Alarm 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 17 }

msaPaEdfaLowOperatingCurrentWarning	  		OBJECT-TYPE
		SYNTAX  				DisplayString		
		MAX-ACCESS  				read-only
		STATUS  				current
		DESCRIPTION
							"the user can get the current status of the 
							High Operating Current Warning status. Whenever the Operating
							Current of the module is lesser than Low Operating current Warning 
							threshold,this alarm will be raised else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 18 }

msaPaEdfaHighTECCurrentAlarm		  		OBJECT-TYPE
		SYNTAX  				DisplayString		
		MAX-ACCESS  				read-only
		STATUS  				current
		DESCRIPTION
							"the user can get the current status of the 
							High TEC Current Alarm status. Whenever the Thermo electric cooler
							Current  is greater than High TEC current Alarm 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 19 }

msaPaEdfaHighTECCurrentWarning		  		OBJECT-TYPE
		SYNTAX  				DisplayString		
		MAX-ACCESS  				read-only
		STATUS  				current
		DESCRIPTION
							"the user can get the current status of the 
							High TEC Current Warning status. Whenever the Thermo electric cooler
							Current is greater than High TEC current Warning 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 20 }

msaPaEdfaLowTECCurrentAlarm		  		OBJECT-TYPE
		SYNTAX  				DisplayString		
		MAX-ACCESS  				read-only
		STATUS  				current
		DESCRIPTION
							"the user can get the current status of the 
							Low TEC Current Alarm status. Whenever the Thermo electric cooler
							Current  is lesser than Low TEC current Alarm 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 21 }

msaPaEdfaLowTECCurrentWarning		  		OBJECT-TYPE
		SYNTAX  				DisplayString		
		MAX-ACCESS  				read-only
		STATUS  				current
		DESCRIPTION
							"the user can get the current status of the 
							Low TEC Current Warning status. Whenever the Thermo electric cooler
							Current is lesser than Low TEC current Warning 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 22 }

msaPaEdfaHighVoaInputPowerAlarm		  		OBJECT-TYPE
		SYNTAX  				DisplayString		
		MAX-ACCESS  				read-only
		STATUS  				current
		DESCRIPTION
							"the user can get the current status of the 
							High Voa Input Power Alarm status. Whenever the VOA Input 
							Power is greater than High VOA Input Power Alarm 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 23 }

msaPaEdfaHighVoaInputPowerWarning		  	OBJECT-TYPE
		SYNTAX  				DisplayString		
		MAX-ACCESS  				read-only
		STATUS  				current
		DESCRIPTION
							"the user can get the current status of the 
							High Voa Input Power Warning status. Whenever the VOA Input 
							Power is greater than High VOA Input Power Warning 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 24 }

msaPaEdfaLowVoaInputPowerAlarm		  		OBJECT-TYPE
		SYNTAX  				DisplayString		
		MAX-ACCESS  				read-only
		STATUS  				current
		DESCRIPTION
							"the user can get the current status of the 
							High Voa Input Power Alarm status. Whenever the VOA Input 
							Power is lesser than Low VOA Input Power Alarm 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 25 }

msaPaEdfaLowVoaInputPowerWarning		  	OBJECT-TYPE
		SYNTAX  				DisplayString		
		MAX-ACCESS  				read-only
		STATUS  				current
		DESCRIPTION
							"the user can get the current status of the 
							Low Voa Input Power Warning status. Whenever the VOA Input 
							Power is lesser than Low VOA Input Power Warning 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 26 }

msaPaEdfaInputOutOfRangeAlarm		  		OBJECT-TYPE
		SYNTAX  				DisplayString		
		MAX-ACCESS  				read-only
		STATUS  				current
		DESCRIPTION
							"the user can get the current status of the 
							Input OutOf Range Alarm status. Whenever the Input 
							Power is greater than the  Input Out Of Range Alarm 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 27 }

msaPaEdfaOutputOutOfRangeAlarm		  		OBJECT-TYPE
		SYNTAX  				DisplayString		
		MAX-ACCESS  				read-only
		STATUS  				current
		DESCRIPTION
							"the user can get the current status of the 
							Output OutOf Range Alarm status. Whenever the Output 
							Power is greater than the  Output Out Of Range Alarm 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 28 }

msaPaEdfaModuleCommunicationAlarm		  		OBJECT-TYPE
		SYNTAX  				DisplayString		
		MAX-ACCESS  				read-only
		STATUS  				current
		DESCRIPTION
							"the user can get the current status of the 
							Module communication alarm.			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 29 }

--**********************************************************************************************
--				BA Module Alarms
--**********************************************************************************************


msaBaEdfaOpticalInputPowerFailureAlarm  		OBJECT-TYPE
		SYNTAX  				DisplayString		
		MAX-ACCESS  				read-only
		STATUS  				current
		DESCRIPTION
							"the user can get the current status of the 
							Input Power Failure status. Whenever no receive 
							power is detected, this alarm 
							will be raised and if receive power is detected,then  
							this alarm will be cleared. 			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 30 }

msaBaEdfaOpticalOutputPowerFailureAlarm  		OBJECT-TYPE
		SYNTAX  				DisplayString		
		MAX-ACCESS  				read-only
		STATUS  				current
		DESCRIPTION
							"the user can get the current status of the 
							Output Power Failure status. Whenever the transmit
							laser is OFF, this alarm 
							will be raised and if transmit power is ON,then  
							this alarm will be cleared. 			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 31 }

msaBaEdfaLowOpticalInputPowerAlarm  			OBJECT-TYPE
		SYNTAX  				DisplayString		
		MAX-ACCESS  				read-only
		STATUS  				current
		DESCRIPTION
							"the user can get the current status of the 
							Low Input Power Alarm status. Whenever the receive 
							power is lesser then the Low input power Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 32 }

msaBaEdfaLowOpticalInputPowerWarning  			OBJECT-TYPE
		SYNTAX  				DisplayString		
		MAX-ACCESS  				read-only
		STATUS  				current
		DESCRIPTION
							"the user can get the current status of the 
							Low Input Power Warning status. Whenever the receive 
							power is lesser then the Low input power Warning threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 33 }

msaBaEdfaHighOpticalInputPowerAlarm  			OBJECT-TYPE
		SYNTAX  				DisplayString		
		MAX-ACCESS  				read-only
		STATUS  				current
		DESCRIPTION
							"the user can get the current status of the 
							High Input Power Alarm status. Whenever the receive 
							power is greater then the High input power Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 34 }

msaBaEdfaHighOpticalInputPowerWarning  			OBJECT-TYPE
		SYNTAX  				DisplayString		
		MAX-ACCESS  				read-only
		STATUS  				current
		DESCRIPTION
							"the user can get the current status of the 
							High Input Power Warning status. Whenever the receive 
							power is greater then the High input power Warning threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 35 }


msaBaEdfaLowOpticalOutputPowerAlarm  			OBJECT-TYPE
		SYNTAX  				DisplayString		
		MAX-ACCESS  				read-only
		STATUS  				current
		DESCRIPTION
							"the user can get the current status of the 
							Low Output Power Alarm status. Whenever the transmit 
							power is lesser then the Low input power Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 36 }

msaBaEdfaLowOpticalOutputPowerWarning  			OBJECT-TYPE
		SYNTAX  				DisplayString		
		MAX-ACCESS  				read-only
		STATUS  				current
		DESCRIPTION
							"the user can get the current status of the 
							Low Output Power Warning status. Whenever the transmit 
							power is lesser then the Low input power Warning threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 37 }

msaBaEdfaHighOpticalOutputPowerAlarm  			OBJECT-TYPE
		SYNTAX  				DisplayString		
		MAX-ACCESS  				read-only
		STATUS  				current
		DESCRIPTION
							"the user can get the current status of the 
							High Output Power Alarm status. Whenever the transmit 
							power is greater then the High Output power Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 38 }

msaBaEdfaHighOpticalOutputPowerWarning  		OBJECT-TYPE
		SYNTAX  				DisplayString		
		MAX-ACCESS  				read-only
		STATUS  				current
		DESCRIPTION
							"the user can get the current status of the 
							High Output Power Warning status. Whenever the receive 
							power is greater then the High Output power Warning threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 39 }

msaBaEdfaHighTemperatureAlarm	  			OBJECT-TYPE
		SYNTAX  				DisplayString		
		MAX-ACCESS  				read-only
		STATUS  				current
		DESCRIPTION
							"the user can get the current status of the 
							High Temperature Alarm status. Whenever the module
							greater then the High Temperature Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 40 }

msaBaEdfaHighTemperatureWarning	  			OBJECT-TYPE
		SYNTAX  				DisplayString		
		MAX-ACCESS  				read-only
		STATUS  				current
		DESCRIPTION
							"the user can get the current status of the 
							High Temperature Warning status. Whenever the module
							greater then the High Temperature Warning threshold, 
							this alarm will be raised and else it will be in cleared 								state			
							--------------------------------------------------------------------
							InterfaceNumber:
							Always 0
							--------------------------------------------------------------------
							Get response:
							If Alarm is Present - Date and Time Stamp
							eg:2017-5-18,9:47:20.0,+5:30
							If Alarm is Absent  - 0
							--------------------------------------------------------------------"
               	
		::= { msaEdfaAlarmQueryEntry 41 }

msaBaEdfaLowTemperatureAlarm	  			OBJECT-TYPE
		SYNTAX  				DisplayString		
		MAX-ACCESS  				read-only
		STATUS  				current
		DESCRIPTION
							"the user can get the current status of the 
							High Temperature Alarm status. Whenever the module
							lesser then the Low Temperature Alarm threshold, 
							this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 42 }

msaBaEdfaLowTemperatureWarning	  			OBJECT-TYPE
		SYNTAX  				DisplayString		
		MAX-ACCESS  				read-only
		STATUS  				current
		DESCRIPTION
							"the user can get the current status of the 
							High Temperature Warning status. Whenever the module
							lesser then the low Temperature Warning threshold, 
							this alarm will be raised and else it will be in cleared 								state			
							--------------------------------------------------------------------
							InterfaceNumber:
							Always 0
							--------------------------------------------------------------------
							Get response:
							If Alarm is Present - Date and Time Stamp
							eg:2017-5-18,9:47:20.0,+5:30
							If Alarm is Absent  - 0
							--------------------------------------------------------------------"
               	
		::= { msaEdfaAlarmQueryEntry 43 }

msaBaEdfaHighOperatingCurrentAlarm	  		OBJECT-TYPE
		SYNTAX  				DisplayString		
		MAX-ACCESS  				read-only
		STATUS  				current
		DESCRIPTION
							"the user can get the current status of the 
							High Operating Current Alarm status. Whenever the Operating
							Current of the module is greater than High Operating current Alarm 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 44 }

msaBaEdfaHighOperatingCurrentWarning	  		OBJECT-TYPE
		SYNTAX  				DisplayString		
		MAX-ACCESS  				read-only
		STATUS  				current
		DESCRIPTION
							"the user can get the current status of the 
							High Operating Current Warning status. Whenever the Operating
							Current of the module is greater than High Operating current Warning 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 45 }


msaBaEdfaLowOperatingCurrentAlarm	  		OBJECT-TYPE
		SYNTAX  				DisplayString		
		MAX-ACCESS  				read-only
		STATUS  				current
		DESCRIPTION
							"the user can get the current status of the 
							High Operating Current Alarm status. Whenever the Operating
							Current of the module is lesser than Low Operating current Alarm 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 46 }

msaBaEdfaLowOperatingCurrentWarning	  		OBJECT-TYPE
		SYNTAX  				DisplayString		
		MAX-ACCESS  				read-only
		STATUS  				current
		DESCRIPTION
							"the user can get the current status of the 
							High Operating Current Warning status. Whenever the Operating
							Current of the module is lesser than Low Operating current Warning 
							threshold,this alarm will be raised else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 47 }

msaBaEdfaHighTECCurrentAlarm		  		OBJECT-TYPE
		SYNTAX  				DisplayString		
		MAX-ACCESS  				read-only
		STATUS  				current
		DESCRIPTION
							"the user can get the current status of the 
							High TEC Current Alarm status. Whenever the Thermo electric cooler
							Current  is greater than High TEC current Alarm 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 48 }

msaBaEdfaHighTECCurrentWarning		  		OBJECT-TYPE
		SYNTAX  				DisplayString		
		MAX-ACCESS  				read-only
		STATUS  				current
		DESCRIPTION
							"the user can get the current status of the 
							High TEC Current Warning status. Whenever the Thermo electric cooler
							Current is greater than High TEC current Warning 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 49 }

msaBaEdfaLowTECCurrentAlarm		  		OBJECT-TYPE
		SYNTAX  				DisplayString		
		MAX-ACCESS  				read-only
		STATUS  				current
		DESCRIPTION
							"the user can get the current status of the 
							Low TEC Current Alarm status. Whenever the Thermo electric cooler
							Current  is lesser than Low TEC current Alarm 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 50 }

msaBaEdfaLowTECCurrentWarning		  		OBJECT-TYPE
		SYNTAX  				DisplayString		
		MAX-ACCESS  				read-only
		STATUS  				current
		DESCRIPTION
							"the user can get the current status of the 
							Low TEC Current Warning status. Whenever the Thermo electric cooler
							Current is lesser than Low TEC current Warning 
							threshold,this alarm will be raised and else it will be in cleared 								state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 51 }

msaBaEdfaHighVoaInputPowerAlarm		  		OBJECT-TYPE
		SYNTAX  				DisplayString		
		MAX-ACCESS  				read-only
		STATUS  				current
		DESCRIPTION
							"the user can get the current status of the 
							High Voa Input Power Alarm status. Whenever the VOA Input 
							Power is greater than High VOA Input Power Alarm 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 52 }

msaBaEdfaHighVoaInputPowerWarning		  	OBJECT-TYPE
		SYNTAX  				DisplayString		
		MAX-ACCESS  				read-only
		STATUS  				current
		DESCRIPTION
							"the user can get the current status of the 
							High Voa Input Power Warning status. Whenever the VOA Input 
							Power is greater than High VOA Input Power Warning 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 53 }

msaBaEdfaLowVoaInputPowerAlarm		  		OBJECT-TYPE
		SYNTAX  				DisplayString		
		MAX-ACCESS  				read-only
		STATUS  				current
		DESCRIPTION
							"the user can get the current status of the 
							High Voa Input Power Alarm status. Whenever the VOA Input 
							Power is lesser than Low VOA Input Power Alarm 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 54 }

msaBaEdfaLowVoaInputPowerWarning		  	OBJECT-TYPE
		SYNTAX  				DisplayString		
		MAX-ACCESS  				read-only
		STATUS  				current
		DESCRIPTION
							"the user can get the current status of the 
							Low Voa Input Power Warning status. Whenever the VOA Input 
							Power is lesser than Low VOA Input Power Warning 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 55 }

msaBaEdfaInputOutOfRangeAlarm		  		OBJECT-TYPE
		SYNTAX  				DisplayString		
		MAX-ACCESS  				read-only
		STATUS  				current
		DESCRIPTION
							"the user can get the current status of the 
							Input OutOf Range Alarm status. Whenever the Input 
							Power is greater than the  Input Out Of Range Alarm 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 56 }

msaBaEdfaOutputOutOfRangeAlarm		  		OBJECT-TYPE
		SYNTAX  				DisplayString		
		MAX-ACCESS  				read-only
		STATUS  				current
		DESCRIPTION
							"the user can get the current status of the 
							Output OutOf Range Alarm status. Whenever the Output 
							Power is greater than the  Output Out Of Range Alarm 
							threshold, then this alarm will be raised or else it will 
							be in cleared state			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 57 }

msaBaEdfaModuleCommunicationAlarm		  	OBJECT-TYPE
		SYNTAX  				DisplayString		
		MAX-ACCESS  				read-only
		STATUS  				current
		DESCRIPTION
							"the user can get the current status of the 
							Module communication alarm.			
							--------------------------------------------------------------------
							InterfaceNumber:
							Always 0
							--------------------------------------------------------------------
							Get response:
							If Alarm is Present - Date and Time Stamp
								eg:2017-5-18,9:47:20.0,+5:30
							If Alarm is Absent  - 0
							--------------------------------------------------------------------"
               	
		::= { msaEdfaAlarmQueryEntry 58 }

	msaEdfaAlarmTableRowStatus 				OBJECT-TYPE
              SYNTAX      				RowStatus
              MAX-ACCESS  				read-write
              STATUS      				current
              DESCRIPTION
                      					"This is MIB realted property,
							NOT to be considered as a card property"
              ::= { msaEdfaAlarmQueryEntry 59 }

--*****************************************************************************
--				    ALARM Notification Table
--*****************************************************************************

    	msaPaEdfaOpticalInputPowerFailureAlarmTrap 	NOTIFICATION-TYPE
		OBJECTS 					{ msaPaEdfaOpticalInputPowerFailureAlarm }
                STATUS  					current
 		DESCRIPTION
                        				"This alarm trap will be raised whether XFP input power failure 
							alarm is detected or cleared"

        	::= { msaEdfaAlarmNotification 1 }


	msaPaEdfaOpticalOutputPowerFailureAlarmTrap 	NOTIFICATION-TYPE
		OBJECTS 					{ msaPaEdfaOpticalOutputPowerFailureAlarm }
                STATUS  					current
 		DESCRIPTION
                        				"This alarm trap will be raised whether XFP Output power failure 
							alarm is detected or cleared"

        	::= { msaEdfaAlarmNotification 2 }


	msaPaEdfaLowOpticalInputPowerAlarmTrap 	NOTIFICATION-TYPE
		OBJECTS 					{ msaPaEdfaLowOpticalInputPowerAlarm }
                STATUS  					current
 		DESCRIPTION
                        				"This alarm trap will be raised Whenever the receive 
							power is lesser then the Low input power Alarm threshold 
							then the alarm is detected or cleared"

        	::= { msaEdfaAlarmNotification 3 }

	msaPaEdfaLowOpticalInputPowerWarningTrap 	NOTIFICATION-TYPE
		OBJECTS 					{ msaPaEdfaLowOpticalInputPowerWarning }
                STATUS  					current
 		DESCRIPTION
                        				"This alarm trap will be raised Whenever the receive 
							power is lesser then the Low input power Warning threshold 
							then the alarm is detected or cleared"

        	::= { msaEdfaAlarmNotification 4 }

	msaPaEdfaHighOpticalInputPowerAlarmTrap 	NOTIFICATION-TYPE
		OBJECTS 					{ msaPaEdfaHighOpticalInputPowerAlarm }
                STATUS  					current
 		DESCRIPTION
                        				"This alarm trap will be raised Whenever the receive 
							power is Greater then the High input power Alarm threshold 
							then the alarm is detected or cleared"

        	::= { msaEdfaAlarmNotification 5 }

	msaPaEdfaHighOpticalInputPowerWarningTrap 	NOTIFICATION-TYPE
		OBJECTS 					{ msaPaEdfaHighOpticalInputPowerWarning }
                STATUS  					current
 		DESCRIPTION
                        				"This alarm trap will be raised Whenever the receive 
							power is Greater then the High input power Warning threshold 
							then the alarm is detected or cleared"

        	::= { msaEdfaAlarmNotification 6 }

	msaPaEdfaLowOpticalOutputPowerAlarmTrap 	NOTIFICATION-TYPE
		OBJECTS 					{ msaPaEdfaLowOpticalOutputPowerAlarm }
                STATUS  					current
 		DESCRIPTION
                        				"This alarm trap will be raised Whenever the transmit 
							power is lesser then the Low input power Alarm threshold 
							then the alarm is detected or cleared"

        	::= { msaEdfaAlarmNotification 7 }

	msaPaEdfaLowOpticalOutputPowerWarningTrap 	NOTIFICATION-TYPE
		OBJECTS 					{ msaPaEdfaLowOpticalOutputPowerWarning }
                STATUS  					current
 		DESCRIPTION
                        				"This alarm trap will be raised Whenever the transmit 
							power is lesser then the Low input power Warning threshold 
							then the alarm is detected or cleared"

        	::= { msaEdfaAlarmNotification 8 }

	msaPaEdfaHighOpticalOutputPowerAlarmTrap 	NOTIFICATION-TYPE
		OBJECTS 					{ msaPaEdfaHighOpticalOutputPowerAlarm }
                STATUS  					current
 		DESCRIPTION
                        				"This alarm trap will be raised Whenever the transmit 
							power is Greater then the High input power Alarm threshold 
							then the alarm is detected or cleared"

        	::= { msaEdfaAlarmNotification 9 }

	msaPaEdfaHighOpticalOutputPowerWarningTrap 	NOTIFICATION-TYPE
		OBJECTS 					{ msaPaEdfaHighOpticalOutputPowerWarning }
                STATUS  					current
 		DESCRIPTION
                        				"This alarm trap will be raised Whenever the transmit 
							power is Greater then the High input power Warning threshold 
							then the alarm is detected or cleared"

        	::= { msaEdfaAlarmNotification 10 }

	msaPaEdfaHighTemperatureAlarmTrap 		NOTIFICATION-TYPE
		OBJECTS 					{ msaPaEdfaHighTemperatureAlarm }
                STATUS  					current
 		DESCRIPTION
                        				"This alarm trap will be raised Whenever the Module 
							temperature is Greater then the High Temperature Alarm threshold 
							then the alarm is detected or cleared"

        	::= { msaEdfaAlarmNotification 11 }

	msaPaEdfaHighTemperatureWarningTrap 		NOTIFICATION-TYPE
		OBJECTS 					{ msaPaEdfaHighTemperatureWarning }
                STATUS  					current
 		DESCRIPTION
                        				"This alarm trap will be raised Whenever the Module 
							temperature is Greater then the High Temperature Warning threshold 
							then the alarm is detected or cleared"

        	::= { msaEdfaAlarmNotification 12 }


	msaPaEdfaLowTemperatureAlarmTrap 		NOTIFICATION-TYPE
		OBJECTS 					{ msaPaEdfaLowTemperatureAlarm }
                STATUS  					current
 		DESCRIPTION
                        				"This alarm trap will be raised Whenever the Module 
							temperature is lesser then the High Temperature Alarm threshold 
							then the alarm is detected or cleared"

        	::= { msaEdfaAlarmNotification 13 }

	msaPaEdfaLowTemperatureWarningTrap 		NOTIFICATION-TYPE
		OBJECTS 					{ msaPaEdfaLowTemperatureWarning }
                STATUS  					current
 		DESCRIPTION
                        				"This alarm trap will be raised Whenever the Module 
							temperature is Greater then the Low Temperature Warning threshold 
							then the alarm is detected or cleared"

        	::= { msaEdfaAlarmNotification 14 }

	msaPaEdfaHighOperatingCurrentAlarmTrap 		NOTIFICATION-TYPE
		OBJECTS 					{ msaPaEdfaHighOperatingCurrentAlarm }
                STATUS  					current
 		DESCRIPTION
                        				"This alarm trap will be raised Whenever the Module 
							Operating current is Greater then the High Operating current 
							Alarm threshold then the alarm is detected or cleared"

        	::= { msaEdfaAlarmNotification 15 }


	msaPaEdfaHighOperatingCurrentWarningTrap 		NOTIFICATION-TYPE
		OBJECTS 					{ msaPaEdfaHighOperatingCurrentWarning }
                STATUS  					current
 		DESCRIPTION
                        				"This alarm trap will be raised Whenever the Module 
							Operating current is Greater then the High Operating current 
							Warning threshold then the alarm is detected or cleared"

        	::= { msaEdfaAlarmNotification 16 }

	msaPaEdfaLowOperatingCurrentAlarmTrap 		NOTIFICATION-TYPE
		OBJECTS 					{ msaPaEdfaLowOperatingCurrentAlarm }
                STATUS  					current
 		DESCRIPTION
                        				"This alarm trap will be raised Whenever the Module 
							Operating current is lesser then the Low Operating current 
							Alarm threshold then the alarm is detected or cleared"

        	::= { msaEdfaAlarmNotification 17 }


	msaPaEdfaLowOperatingCurrentWarningTrap 		NOTIFICATION-TYPE
		OBJECTS 					{ msaPaEdfaLowOperatingCurrentWarning }
                STATUS  					current
 		DESCRIPTION
                        				"This alarm trap will be raised Whenever the Module 
							Operating current is Lesser then the Low Operating current 
							Warning threshold then the alarm is detected or cleared"

        	::= { msaEdfaAlarmNotification 18 }


	msaPaEdfaHighTECCurrentAlarmTrap 		NOTIFICATION-TYPE
		OBJECTS 					{ msaPaEdfaHighTECCurrentAlarm }
                STATUS  					current
 		DESCRIPTION
                        				"This alarm trap will be raised Whenever the Module 
							TEC Current is Greater then the High TEC Current 
							Alarm threshold then the alarm is detected or cleared"

        	::= { msaEdfaAlarmNotification 19 }


	msaPaEdfaHighTECCurrentWarningTrap 		NOTIFICATION-TYPE
		OBJECTS 					{ msaPaEdfaHighTECCurrentWarning }
                STATUS  					current
 		DESCRIPTION
                        				"This alarm trap will be raised Whenever the Module 
							TEC Current is Greater then the High TEC Current 
							Warning threshold then the alarm is detected or cleared"

        	::= { msaEdfaAlarmNotification 20 }


	msaPaEdfaLowTECCurrentAlarmTrap 		NOTIFICATION-TYPE
		OBJECTS 					{ msaPaEdfaLowTECCurrentAlarm }
                STATUS  					current
 		DESCRIPTION
                        				"This alarm trap will be raised Whenever the Module 
							TEC Current is Lesser then the Low TEC Current 
							Alarm threshold then the alarm is detected or cleared"

        	::= { msaEdfaAlarmNotification 21 }


	msaPaEdfaLowTECCurrentWarningTrap 		NOTIFICATION-TYPE
		OBJECTS 					{ msaPaEdfaLowTECCurrentWarning }
                STATUS  					current
 		DESCRIPTION
                        				"This alarm trap will be raised Whenever the Module 
							TEC Current is Lesser then the Low TEC Current 
							Warning threshold then the alarm is detected or cleared"

        	::= { msaEdfaAlarmNotification 22 }


	msaPaEdfaHighVoaInputPowerAlarmTrap 		NOTIFICATION-TYPE
		OBJECTS 					{ msaPaEdfaHighVoaInputPowerAlarm }
                STATUS  					current
 		DESCRIPTION
                        				"This alarm trap will be raised Whenever the Module 
							VOA Input power is Greater then the High VOA Input power 
							Alarm threshold then the alarm is detected or cleared"

        	::= { msaEdfaAlarmNotification 23 }


	msaPaEdfaHighVoaInputPowerWarningTrap 		NOTIFICATION-TYPE
		OBJECTS 					{ msaPaEdfaHighVoaInputPowerWarning }
                STATUS  					current
 		DESCRIPTION
                        				"This alarm trap will be raised Whenever the Module 
							VOA Input power is Greater then the High VOA Input power 
							Warning threshold then the alarm is detected or cleared"

        	::= { msaEdfaAlarmNotification 24 }


	msaPaEdfaLowVoaInputPowerAlarmTrap 		NOTIFICATION-TYPE
		OBJECTS 					{ msaPaEdfaLowVoaInputPowerAlarm }
                STATUS  					current
 		DESCRIPTION
                        				"This alarm trap will be raised Whenever the Module 
							VOA Input power is Lesser then the Low VOA Input power 
							Alarm threshold then the alarm is detected or cleared"

        	::= { msaEdfaAlarmNotification 25 }


	msaPaEdfaLowVoaInputPowerWarningTrap 		NOTIFICATION-TYPE
		OBJECTS 					{ msaPaEdfaLowVoaInputPowerWarning }
                STATUS  					current
 		DESCRIPTION
                        				"This alarm trap will be raised Whenever the Module 
							VOA Input power is Lesser then the Low VOA Input power 
							Warning threshold then the alarm is detected or cleared"

        	::= { msaEdfaAlarmNotification 26 }

	msaPaEdfaInputOutOfRangeAlarmTrap 		NOTIFICATION-TYPE
		OBJECTS 					{ msaPaEdfaInputOutOfRangeAlarm }
                STATUS  					current
 		DESCRIPTION
                        				"This alarm trap will be raised Whenever the Module 
							Input power is Greater than the I/p Out of range 
							Alarm threshold then the alarm is detected or cleared"

        	::= { msaEdfaAlarmNotification 27 }


	msaPaEdfaOutputOutOfRangeAlarmTrap 		NOTIFICATION-TYPE
		OBJECTS 					{ msaPaEdfaOutputOutOfRangeAlarm }
                STATUS  					current
 		DESCRIPTION
                        				"This alarm trap will be raised Whenever the Module 
							Output power is Greater than the O/p Out of range 
							Alarm threshold then the alarm is detected or cleared"

        	::= { msaEdfaAlarmNotification 28 } 

	msaPaEdfaModuleCommunicationAlarmTrap 		NOTIFICATION-TYPE
		OBJECTS 					{ msaPaEdfaModuleCommunicationAlarm }
                STATUS  					current
 		DESCRIPTION
                        				"This alarm trap will be raised Whenever the Module 
							Communication is not happens , then the alarm is 
							detected or cleared"

        	::= { msaEdfaAlarmNotification 29 }

	msaBaEdfaOpticalInputPowerFailureAlarmTrap 	NOTIFICATION-TYPE
		OBJECTS 					{ msaBaEdfaOpticalInputPowerFailureAlarm }
                STATUS  					current
 		DESCRIPTION
                        				"This alarm trap will be raised whether XFP input power failure 
							alarm is detected or cleared"

        	::= { msaEdfaAlarmNotification 30 }


	msaBaEdfaOpticalOutputPowerFailureAlarmTrap 	NOTIFICATION-TYPE
		OBJECTS 					{ msaBaEdfaOpticalOutputPowerFailureAlarm }
                STATUS  					current
 		DESCRIPTION
                        				"This alarm trap will be raised whether XFP Output power failure 
							alarm is detected or cleared"

        	::= { msaEdfaAlarmNotification 31 }


	msaBaEdfaLowOpticalInputPowerAlarmTrap 	NOTIFICATION-TYPE
		OBJECTS 					{ msaBaEdfaLowOpticalInputPowerAlarm }
                STATUS  					current
 		DESCRIPTION
                        				"This alarm trap will be raised Whenever the receive 
							power is lesser then the Low input power Alarm threshold 
							then the alarm is detected or cleared"

        	::= { msaEdfaAlarmNotification 32 }

	msaBaEdfaLowOpticalInputPowerWarningTrap 	NOTIFICATION-TYPE
		OBJECTS 					{ msaBaEdfaLowOpticalInputPowerWarning }
                STATUS  					current
 		DESCRIPTION
                        				"This alarm trap will be raised Whenever the receive 
							power is lesser then the Low input power Warning threshold 
							then the alarm is detected or cleared"

        	::= { msaEdfaAlarmNotification 33 }

	msaBaEdfaHighOpticalInputPowerAlarmTrap 	NOTIFICATION-TYPE
		OBJECTS 					{ msaBaEdfaHighOpticalInputPowerAlarm }
                STATUS  					current
 		DESCRIPTION
                        				"This alarm trap will be raised Whenever the receive 
							power is Greater then the High input power Alarm threshold 
							then the alarm is detected or cleared"

        	::= { msaEdfaAlarmNotification 34 }

	msaBaEdfaHighOpticalInputPowerWarningTrap 	NOTIFICATION-TYPE
		OBJECTS 					{ msaBaEdfaHighOpticalInputPowerWarning }
                STATUS  					current
 		DESCRIPTION
                        				"This alarm trap will be raised Whenever the receive 
							power is Greater then the High input power Warning threshold 
							then the alarm is detected or cleared"

        	::= { msaEdfaAlarmNotification 35 }

	msaBaEdfaLowOpticalOutputPowerAlarmTrap 	NOTIFICATION-TYPE
		OBJECTS 					{ msaBaEdfaLowOpticalOutputPowerAlarm }
                STATUS  					current
 		DESCRIPTION
                        				"This alarm trap will be raised Whenever the transmit 
							power is lesser then the Low input power Alarm threshold 
							then the alarm is detected or cleared"

        	::= { msaEdfaAlarmNotification 36 }

	msaBaEdfaLowOpticalOutputPowerWarningTrap 	NOTIFICATION-TYPE
		OBJECTS 					{ msaBaEdfaLowOpticalOutputPowerWarning }
                STATUS  					current
 		DESCRIPTION
                        				"This alarm trap will be raised Whenever the transmit 
							power is lesser then the Low input power Warning threshold 
							then the alarm is detected or cleared"

        	::= { msaEdfaAlarmNotification 37 }

	msaBaEdfaHighOpticalOutputPowerAlarmTrap 	NOTIFICATION-TYPE
		OBJECTS 					{ msaBaEdfaHighOpticalOutputPowerAlarm }
                STATUS  					current
 		DESCRIPTION
                        				"This alarm trap will be raised Whenever the transmit 
							power is Greater then the High input power Alarm threshold 
							then the alarm is detected or cleared"

        	::= { msaEdfaAlarmNotification 38 }

	msaBaEdfaHighOpticalOutputPowerWarningTrap 	NOTIFICATION-TYPE
		OBJECTS 					{ msaBaEdfaHighOpticalOutputPowerWarning }
                STATUS  					current
 		DESCRIPTION
                        				"This alarm trap will be raised Whenever the transmit 
							power is Greater then the High input power Warning threshold 
							then the alarm is detected or cleared"

        	::= { msaEdfaAlarmNotification 39 }

	msaBaEdfaHighTemperatureAlarmTrap 		NOTIFICATION-TYPE
		OBJECTS 					{ msaBaEdfaHighTemperatureAlarm }
                STATUS  					current
 		DESCRIPTION
                        				"This alarm trap will be raised Whenever the Module 
							temperature is Greater then the High Temperature Alarm threshold 
							then the alarm is detected or cleared"

        	::= { msaEdfaAlarmNotification 40 }

	msaBaEdfaHighTemperatureWarningTrap 		NOTIFICATION-TYPE
		OBJECTS 					{ msaBaEdfaHighTemperatureWarning }
                STATUS  					current
 		DESCRIPTION
                        				"This alarm trap will be raised Whenever the Module 
							temperature is Greater then the High Temperature Warning threshold 
							then the alarm is detected or cleared"

        	::= { msaEdfaAlarmNotification 41 }


	msaBaEdfaLowTemperatureAlarmTrap 		NOTIFICATION-TYPE
		OBJECTS 					{ msaBaEdfaLowTemperatureAlarm }
                STATUS  					current
 		DESCRIPTION
                        				"This alarm trap will be raised Whenever the Module 
							temperature is lesser then the High Temperature Alarm threshold 
							then the alarm is detected or cleared"

        	::= { msaEdfaAlarmNotification 42 }

	msaBaEdfaLowTemperatureWarningTrap 		NOTIFICATION-TYPE
		OBJECTS 					{ msaBaEdfaLowTemperatureWarning }
                STATUS  					current
 		DESCRIPTION
                        				"This alarm trap will be raised Whenever the Module 
							temperature is Greater then the Low Temperature Warning threshold 
							then the alarm is detected or cleared"

        	::= { msaEdfaAlarmNotification 43 }

	msaBaEdfaHighOperatingCurrentAlarmTrap 		NOTIFICATION-TYPE
		OBJECTS 					{ msaBaEdfaHighOperatingCurrentAlarm }
                STATUS  					current
 		DESCRIPTION
                        				"This alarm trap will be raised Whenever the Module 
							Operating current is Greater then the High Operating current 
							Alarm threshold then the alarm is detected or cleared"

        	::= { msaEdfaAlarmNotification 44 }


	msaBaEdfaHighOperatingCurrentWarningTrap 		NOTIFICATION-TYPE
		OBJECTS 					{ msaBaEdfaHighOperatingCurrentWarning }
                STATUS  					current
 		DESCRIPTION
                        				"This alarm trap will be raised Whenever the Module 
							Operating current is Greater then the High Operating current 
							Warning threshold then the alarm is detected or cleared"

        	::= { msaEdfaAlarmNotification 45 }

	msaBaEdfaLowOperatingCurrentAlarmTrap 		NOTIFICATION-TYPE
		OBJECTS 					{ msaBaEdfaLowOperatingCurrentAlarm }
                STATUS  					current
 		DESCRIPTION
                        				"This alarm trap will be raised Whenever the Module 
							Operating current is lesser then the Low Operating current 
							Alarm threshold then the alarm is detected or cleared"

        	::= { msaEdfaAlarmNotification 46 }


	msaBaEdfaLowOperatingCurrentWarningTrap 		NOTIFICATION-TYPE
		OBJECTS 					{ msaBaEdfaLowOperatingCurrentWarning }
                STATUS  					current
 		DESCRIPTION
                        				"This alarm trap will be raised Whenever the Module 
							Operating current is Lesser then the Low Operating current 
							Warning threshold then the alarm is detected or cleared"

        	::= { msaEdfaAlarmNotification 47 }

	msaBaEdfaHighTECCurrentAlarmTrap 		NOTIFICATION-TYPE
		OBJECTS 					{ msaBaEdfaHighTECCurrentAlarm }
                STATUS  					current
 		DESCRIPTION
                        				"This alarm trap will be raised Whenever the Module 
							TEC Current is Greater then the High TEC Current 
							Alarm threshold then the alarm is detected or cleared"

        	::= { msaEdfaAlarmNotification 48 }


	msaBaEdfaHighTECCurrentWarningTrap 		NOTIFICATION-TYPE
		OBJECTS 					{ msaBaEdfaHighTECCurrentWarning }
                STATUS  					current
 		DESCRIPTION
                        				"This alarm trap will be raised Whenever the Module 
							TEC Current is Greater then the High TEC Current 
							Warning threshold then the alarm is detected or cleared"

        	::= { msaEdfaAlarmNotification 49 }


	msaBaEdfaLowTECCurrentAlarmTrap 		NOTIFICATION-TYPE
		OBJECTS 					{ msaBaEdfaLowTECCurrentAlarm }
                STATUS  					current
 		DESCRIPTION
                        				"This alarm trap will be raised Whenever the Module 
							TEC Current is Lesser then the Low TEC Current 
							Alarm threshold then the alarm is detected or cleared"

        	::= { msaEdfaAlarmNotification 50 }


	msaBaEdfaLowTECCurrentWarningTrap 		NOTIFICATION-TYPE
		OBJECTS 					{ msaBaEdfaLowTECCurrentWarning }
                STATUS  					current
 		DESCRIPTION
                        				"This alarm trap will be raised Whenever the Module 
							TEC Current is Lesser then the Low TEC Current 
							Warning threshold then the alarm is detected or cleared"

        	::= { msaEdfaAlarmNotification 51 }


	msaBaEdfaHighVoaInputPowerAlarmTrap 		NOTIFICATION-TYPE
		OBJECTS 					{ msaBaEdfaHighVoaInputPowerAlarm }
                STATUS  					current
 		DESCRIPTION
                        				"This alarm trap will be raised Whenever the Module 
							VOA Input power is Greater then the High VOA Input power 
							Alarm threshold then the alarm is detected or cleared"

        	::= { msaEdfaAlarmNotification 52 }


	msaBaEdfaHighVoaInputPowerWarningTrap 		NOTIFICATION-TYPE
		OBJECTS 					{ msaBaEdfaHighVoaInputPowerWarning }
                STATUS  					current
 		DESCRIPTION
                        				"This alarm trap will be raised Whenever the Module 
							VOA Input power is Greater then the High VOA Input power 
							Warning threshold then the alarm is detected or cleared"

        	::= { msaEdfaAlarmNotification 53 }


	msaBaEdfaLowVoaInputPowerAlarmTrap 		NOTIFICATION-TYPE
		OBJECTS 					{ msaBaEdfaLowVoaInputPowerAlarm }
                STATUS  					current
 		DESCRIPTION
                        				"This alarm trap will be raised Whenever the Module 
							VOA Input power is Lesser then the Low VOA Input power 
							Alarm threshold then the alarm is detected or cleared"

        	::= { msaEdfaAlarmNotification 54 }


	msaBaEdfaLowVoaInputPowerWarningTrap 		NOTIFICATION-TYPE
		OBJECTS 					{ msaBaEdfaLowVoaInputPowerWarning }
                STATUS  					current
 		DESCRIPTION
                        				"This alarm trap will be raised Whenever the Module 
							VOA Input power is Lesser then the Low VOA Input power 
							Warning threshold then the alarm is detected or cleared"

        	::= { msaEdfaAlarmNotification 55 }

	msaBaEdfaInputOutOfRangeAlarmTrap 		NOTIFICATION-TYPE
		OBJECTS 					{ msaBaEdfaInputOutOfRangeAlarm }
                STATUS  					current
 		DESCRIPTION
                        				"This alarm trap will be raised Whenever the Module 
							Input power is Greater than the I/p Out of range 
							Alarm threshold then the alarm is detected or cleared"

        	::= { msaEdfaAlarmNotification 56 }


	msaBaEdfaOutputOutOfRangeAlarmTrap 		NOTIFICATION-TYPE
		OBJECTS 					{ msaBaEdfaOutputOutOfRangeAlarm }
                STATUS  					current
 		DESCRIPTION
                        				"This alarm trap will be raised Whenever the Module 
							Output power is Greater than the O/p Out of range 
							Alarm threshold then the alarm is detected or cleared"

        	::= { msaEdfaAlarmNotification 57 } 

	msaBaEdfaModuleCommunicationAlarmTrap 		NOTIFICATION-TYPE
		OBJECTS 					{ msaBaEdfaModuleCommunicationAlarm }
                STATUS  					current
 		DESCRIPTION
                        				"This alarm trap will be raised Whenever the Module 
							Communication is not happens , then the alarm is 
							detected or cleared"

        	::= { msaEdfaAlarmNotification 58 }

--*****************************************************************************
--*****************************************************************************

snmpCurrentNotificationsGroup NOTIFICATION-GROUP
		NOTIFICATIONS { 
					msaPaEdfaOpticalInputPowerFailureAlarmTrap				,
					msaPaEdfaOpticalOutputPowerFailureAlarmTrap		                ,
					msaPaEdfaLowOpticalInputPowerAlarmTrap                   		,
					msaPaEdfaLowOpticalInputPowerWarningTrap                  		,
					msaPaEdfaHighOpticalInputPowerAlarmTrap                   		,
					msaPaEdfaHighOpticalInputPowerWarningTrap                 		,
					msaPaEdfaLowOpticalOutputPowerAlarmTrap                   		,
					msaPaEdfaLowOpticalOutputPowerWarningTrap                  		,
					msaPaEdfaHighOpticalOutputPowerAlarmTrap                  		,
					msaPaEdfaHighOpticalOutputPowerWarningTrap                  	,
					msaPaEdfaHighTemperatureAlarmTrap                   		,
					msaPaEdfaHighTemperatureWarningTrap                  		,
					msaPaEdfaLowTemperatureAlarmTrap                   			,
					msaPaEdfaLowTemperatureWarningTrap                  		,
					msaPaEdfaHighOperatingCurrentAlarmTrap                   		,
					msaPaEdfaHighOperatingCurrentWarningTrap                  		,
					msaPaEdfaLowOperatingCurrentAlarmTrap                   		,
					msaPaEdfaLowOperatingCurrentWarningTrap                  		,
					msaPaEdfaHighTECCurrentAlarmTrap                   			,
					msaPaEdfaHighTECCurrentWarningTrap                  		,
					msaPaEdfaLowTECCurrentAlarmTrap                   			,
					msaPaEdfaLowTECCurrentWarningTrap                 			,
					msaPaEdfaHighVoaInputPowerAlarmTrap                   		,
					msaPaEdfaHighVoaInputPowerWarningTrap                  		,
					msaPaEdfaLowVoaInputPowerAlarmTrap                   		,
					msaPaEdfaLowVoaInputPowerWarningTrap                  		,
					msaPaEdfaInputOutOfRangeAlarmTrap                   		,
					msaPaEdfaOutputOutOfRangeAlarmTrap                  		,
					msaPaEdfaModuleCommunicationAlarmTrap				,
					msaBaEdfaOpticalInputPowerFailureAlarmTrap				,
					msaBaEdfaOpticalOutputPowerFailureAlarmTrap		                ,
					msaBaEdfaLowOpticalInputPowerAlarmTrap                   		,
					msaBaEdfaLowOpticalInputPowerWarningTrap                  		,
					msaBaEdfaHighOpticalInputPowerAlarmTrap                   		,
					msaBaEdfaHighOpticalInputPowerWarningTrap                 		,
					msaBaEdfaLowOpticalOutputPowerAlarmTrap                   		,
					msaBaEdfaLowOpticalOutputPowerWarningTrap                  		,
					msaBaEdfaHighOpticalOutputPowerAlarmTrap                  		,
					msaBaEdfaHighOpticalOutputPowerWarningTrap                  	,
					msaBaEdfaHighTemperatureAlarmTrap                   		,
					msaBaEdfaHighTemperatureWarningTrap                  		,
					msaBaEdfaLowTemperatureAlarmTrap                   			,
					msaBaEdfaLowTemperatureWarningTrap                  		,
					msaBaEdfaHighOperatingCurrentAlarmTrap                   		,
					msaBaEdfaHighOperatingCurrentWarningTrap                  		,
					msaBaEdfaLowOperatingCurrentAlarmTrap                   		,
					msaBaEdfaLowOperatingCurrentWarningTrap                  		,
					msaBaEdfaHighTECCurrentAlarmTrap                   			,
					msaBaEdfaHighTECCurrentWarningTrap                  		,
					msaBaEdfaLowTECCurrentAlarmTrap                   			,
					msaBaEdfaLowTECCurrentWarningTrap                 			,
					msaBaEdfaHighVoaInputPowerAlarmTrap                   		,
					msaBaEdfaHighVoaInputPowerWarningTrap                  		,
					msaBaEdfaLowVoaInputPowerAlarmTrap                   		,
					msaBaEdfaLowVoaInputPowerWarningTrap                  		,
					msaBaEdfaInputOutOfRangeAlarmTrap                   		,
					msaBaEdfaOutputOutOfRangeAlarmTrap                  		,
					msaBaEdfaModuleCommunicationAlarmTrap				
		}
  	  STATUS current
  	  DESCRIPTION
		"msaEdfa alarm notifications group"
  	  ::=  { msaEdfa 6 }

--***************************************************************************** 
		
	snmpcurrentGroup OBJECT-GROUP
		OBJECTS {
				msaEdfaInterface,
				msaEdfaEepromCardId,
				msaEdfaEepromCardName,
				msaEdfaEepromPartCode,
				msaEdfaEepromCardSerialNumber,
				msaEdfaEepromHardwareExternalReleaseVersion,
				msaEdfaSoftwareExternalReleaseVersion,
				msaEdfaEepromHardwareInternalReleaseVersion,
				msaEdfaSoftwareInternalReleaseVersion,
				msaEdfaEepromCardUidNumber,
				msaEdfaEepromCardEUI48Number,
				msaEdfaEepromCardEUI64Number,
				msaEdfaEepromModuleType,
				msaEdfaInstallationDate,
				msaEdfaCommissionDate,
				msaEdfaCardRunningTime,
				msaEdfaCardRestartCount,
			   	msaPaEdfaModuleVendorName,
				msaPaEdfaModuleSerialNumber,		
				msaPaEdfaModuleNumberOfChannelsSupported,
				msaPaEdfaModuleNumberOfPumpSupported,			
				msaPaEdfaModuleMaxGainSupported,
				msaPaEdfaModuleSaturationOutputPowerSupported,
				msaPaEdfaModuleVoaPresenceStatus,				
				msaBaEdfaModuleVendorName,
				msaBaEdfaModuleSerialNumber,
				msaBaEdfaModuleNumberOfChannelsSupported,
				msaBaEdfaModuleNumberOfPumpSupported,
				msaBaEdfaModuleMaxGainSupported,
				msaBaEdfaModuleSaturationOutputPowerSupported,
				msaBaEdfaModuleVoaPresenceStatus,
				msaEdfaDirection,
				msaEdfaCardGeneralDetailsTableRowStatus,

				msaEdfaCardSoftReset,
				msaEdfaCardDefaultFactoryReset,
				msaEdfaCardSoftwareUpgrade,
				msaEdfaAlarmMonitoringStatus,

				msaEdfaSystemTimeAndRtcTime,
				msaEdfaSyncRtcWithNtpServer,
				msaEdfaSyncRtcWithSystemTime,
				msaEdfaSyncSystemTimeWithNtpServer,
				msaEdfaUpdateGivenTimeIntoRtc,
				msaEdfaUpdateGivenTimeIntoSystem,

				msaPaEdfaModulePumpLaserStatus,
				msaPaEdfaModuleAutomaticLaserShutdownStatusForStage1,
				msaPaEdfaModuleOperatingMode,
				msaPaEdfaModuleGainInAutomaticGainControlMode,
				msaPaEdfaModuleGainTilt,
				msaPaEdfaModuleOpticalOutputPowerInAutomaticPowerControlMode,
				msaPaEdfaModulePump1OperatingCurrentInAutomaticCurrentControlMode,
				msaPaEdfaModuleVariableOpticalAttenuatorAttenuation,
				msaPaEdfaModuleResetOpticalAmplifier,

				msaBaEdfaModulePumpLaserStatus,
				msaBaEdfaModuleAutomaticLaserShutdownStatusForStage1,
				msaBaEdfaModuleOperatingMode,
				msaBaEdfaModuleOpticalOutputPowerInAutomaticPowerControlMode,
				msaBaEdfaModulePump1OperatingCurrentInAutomaticCurrentControlMode,
				msaBaEdfaModuleVariableOpticalAttenuatorAttenuation,
				msaBaEdfaModuleResetOpticalAmplifier,

				msaPaEdfaOpticalInputPowerFailureAlarmThreshold				,
				msaPaEdfaOpticalInputPowerFailureAlarmThresholdMinimumValue		,
				msaPaEdfaOpticalInputPowerFailureAlarmThresholdMaximumValue		,
				msaPaEdfaHighOpticalInputPowerAlarmThreshold				,
				msaPaEdfaHighOpticalInputPowerAlarmThresholdMinimumValue		,
				msaPaEdfaHighOpticalInputPowerAlarmThresholdMaximumValue		,
				msaPaEdfaLowOpticalInputPowerAlarmThreshold				,
				msaPaEdfaLowOpticalInputPowerAlarmThresholdMinimumValue			,
				msaPaEdfaLowOpticalInputPowerAlarmThresholdMaximumValue			,
				msaPaEdfaHighOpticalInputPowerWarningThreshold				,
				msaPaEdfaHighOpticalInputPowerWarningThresholdMinimumValue		,
				msaPaEdfaHighOpticalInputPowerWarningThresholdMaximumValue		,
				msaPaEdfaLowOpticalInputPowerWarningThreshold				,
				msaPaEdfaLowOpticalInputPowerWarningThresholdMinimumValue		,
				msaPaEdfaLowOpticalInputPowerWarningThresholdMaximumValue		,
				msaPaEdfaHighOpticalOutputPowerWarningThreshold				,
				msaPaEdfaHighOpticalOutputPowerWarningThresholdMinimumValue		,
				msaPaEdfaHighOpticalOutputPowerWarningThresholdMaximumValue		,
				msaPaEdfaLowOpticalOutputPowerWarningThreshold				,
				msaPaEdfaLowOpticalOutputPowerWarningThresholdMinimumValue		,
				msaPaEdfaLowOpticalOutputPowerWarningThresholdMaximumValue		,
				msaPaEdfaOpticalOutputPowerFailureAlarmThreshold			,
				msaPaEdfaOpticalOutputPowerFailureAlarmThresholdMinimumValue		,
				msaPaEdfaOpticalOutputPowerFailureAlarmThresholdMaximumValue		,
				msaPaEdfaHighOpticalOutputPowerAlarmThreshold				,
				msaPaEdfaHighOpticalOutputPowerAlarmThresholdMinimumValue		,
				msaPaEdfaHighOpticalOutputPowerAlarmThresholdMaximumValue		,
				msaPaEdfaLowOpticalOutputPowerAlarmThreshold				,
				msaPaEdfaLowOpticalOutputPowerAlarmThresholdMinimumValue		,
				msaPaEdfaLowOpticalOutputPowerAlarmThresholdMaximumValue		,
				msaPaEdfaHighTemperatureAlarmThreshold					,
				msaPaEdfaHighTemperatureAlarmThresholdMinimumValue			,
				msaPaEdfaHighTemperatureAlarmThresholdMaximumValue			,
				msaPaEdfaLowTemperatureAlarmThreshold					,
				msaPaEdfaLowTemperatureAlarmThresholdMinimumValue			,
				msaPaEdfaLowTemperatureAlarmThresholdMaximumValue			,
				msaPaEdfaHighTemperatureWarningThreshold				,
				msaPaEdfaHighTemperatureWarningThresholdMinimumValue			,
				msaPaEdfaHighTemperatureWarningThresholdMaximumValue			,
				msaPaEdfaLowTemperatureWarningThreshold					,
				msaPaEdfaLowTemperatureWarningThresholdMinimumValue			,
				msaPaEdfaLowTemperatureWarningThresholdMaximumValue			,
				msaPaEdfaHighOperatingCurrentAlarmThreshold				,
				msaPaEdfaHighOperatingCurrentAlarmThresholdMinimumValue			,
				msaPaEdfaHighOperatingCurrentAlarmThresholdMaximumValue			,
				msaPaEdfaLowOperatingCurrentAlarmThreshold				,
				msaPaEdfaLowOperatingCurrentAlarmThresholdMinimumValue			,
				msaPaEdfaLowOperatingCurrentAlarmThresholdMaximumValue			,
				msaPaEdfaHighOperatingCurrentWarningThreshold				,
				msaPaEdfaHighOperatingCurrentWarningThresholdMinimumValue		,
				msaPaEdfaHighOperatingCurrentWarningThresholdMaximumValue		,
				msaPaEdfaLowOperatingCurrentWarningThreshold				,
				msaPaEdfaLowOperatingCurrentWarningThresholdMinimumValue		,
				msaPaEdfaLowOperatingCurrentWarningThresholdMaximumValue		,
				msaPaEdfaHighTECCurrentAlarmThreshold					,
				msaPaEdfaHighTECCurrentAlarmThresholdMinimumValue			,
				msaPaEdfaHighTECCurrentAlarmThresholdMaximumValue			,
				msaPaEdfaLowTECCurrentAlarmThreshold					,
				msaPaEdfaLowTECCurrentAlarmThresholdMinimumValue			,
				msaPaEdfaLowTECCurrentAlarmThresholdMaximumValue			,
				msaPaEdfaHighTECCurrentWarningThreshold					,
				msaPaEdfaHighTECCurrentWarningThresholdMinimumValue			,
				msaPaEdfaHighTECCurrentWarningThresholdMaximumValue			,
				msaPaEdfaLowTECCurrentWarningThreshold					,
				msaPaEdfaLowTECCurrentWarningThresholdMinimumValue			,
				msaPaEdfaLowTECCurrentWarningThresholdMaximumValue			,
				msaPaEdfaVoaHighInputPowerAlarmThreshold				,
				msaPaEdfaVoaHighInputPowerAlarmThresholdMinimumValue			,
				msaPaEdfaVoaHighInputPowerAlarmThresholdMaximumValue			,
				msaPaEdfaVoaLowInputPowerAlarmThreshold					,
				msaPaEdfaVoaLowInputPowerAlarmThresholdMinimumValue			,
				msaPaEdfaVoaLowInputPowerAlarmThresholdMaximumValue			,
				msaPaEdfaVoaHighInputPowerWarningThreshold				,
				msaPaEdfaVoaHighInputPowerWarningThresholdMinimumValue			,
				msaPaEdfaVoaHighInputPowerWarningThresholdMaximumValue			,
				msaPaEdfaVoaLowInputPowerWarningThreshold				,
				msaPaEdfaVoaLowInputPowerWarningThresholdMinimumValue			,
				msaPaEdfaVoaLowInputPowerWarningThresholdMaximumValue			,
				msaPaEdfaModuleInputOpticalPowerLowAlarmThreshold			,
				msaPaEdfaModuleInputOpticalPowerLowAlarmThresholdMinimumValue		,
				msaPaEdfaModuleInputOpticalPowerLowAlarmThresholdMaximumValue		,
				msaPaEdfaModuleInputOpticalPowerHighAlarmThreshold			,
				msaPaEdfaModuleInputOpticalPowerHighAlarmThresholdMinimumValue		,
				msaPaEdfaModuleInputOpticalPowerHighAlarmThresholdMaximumValue		,
				msaPaEdfaModuleOutputOpticalPowerFailureAlarmThreshold			,
				msaPaEdfaModuleOutputOpticalPowerFailureAlarmThresholdMinimumValue	,
				msaPaEdfaModuleOutputOpticalPowerFailureAlarmThresholdMaximumValue	,
				msaPaEdfaModuleInputAlarmThreshold					,
				msaPaEdfaModuleInputAlarmThresholdMinimumValue				,
				msaPaEdfaModuleInputAlarmThresholdMaximumValue				,
				msaBaEdfaOpticalInputPowerFailureAlarmThreshold				,
				msaBaEdfaOpticalInputPowerFailureAlarmThresholdMinimumValue		,
				msaBaEdfaOpticalInputPowerFailureAlarmThresholdMaximumValue		,
				msaBaEdfaHighOpticalInputPowerAlarmThreshold				,
				msaBaEdfaHighOpticalInputPowerAlarmThresholdMinimumValue		,
				msaBaEdfaHighOpticalInputPowerAlarmThresholdMaximumValue		,
				msaBaEdfaLowOpticalInputPowerAlarmThreshold				,
				msaBaEdfaLowOpticalInputPowerAlarmThresholdMinimumValue			,
				msaBaEdfaLowOpticalInputPowerAlarmThresholdMaximumValue			,
				msaBaEdfaHighOpticalInputPowerWarningThreshold				,
				msaBaEdfaHighOpticalInputPowerWarningThresholdMinimumValue		,
				msaBaEdfaHighOpticalInputPowerWarningThresholdMaximumValue		,
				msaBaEdfaLowOpticalInputPowerWarningThreshold				,
				msaBaEdfaLowOpticalInputPowerWarningThresholdMinimumValue		,
				msaBaEdfaLowOpticalInputPowerWarningThresholdMaximumValue		,
				msaBaEdfaHighOpticalOutputPowerWarningThreshold				,
				msaBaEdfaHighOpticalOutputPowerWarningThresholdMinimumValue		,
				msaBaEdfaHighOpticalOutputPowerWarningThresholdMaximumValue		,
				msaBaEdfaLowOpticalOutputPowerWarningThreshold				,
				msaBaEdfaLowOpticalOutputPowerWarningThresholdMinimumValue		,
				msaBaEdfaLowOpticalOutputPowerWarningThresholdMaximumValue		,
				msaBaEdfaOpticalOutputPowerFailureAlarmThreshold			,
				msaBaEdfaOpticalOutputPowerFailureAlarmThresholdMinimumValue		,
				msaBaEdfaOpticalOutputPowerFailureAlarmThresholdMaximumValue		,
				msaBaEdfaHighOpticalOutputPowerAlarmThreshold				,
				msaBaEdfaHighOpticalOutputPowerAlarmThresholdMinimumValue		,
				msaBaEdfaHighOpticalOutputPowerAlarmThresholdMaximumValue		,
				msaBaEdfaLowOpticalOutputPowerAlarmThreshold				,
				msaBaEdfaLowOpticalOutputPowerAlarmThresholdMinimumValue		,
				msaBaEdfaLowOpticalOutputPowerAlarmThresholdMaximumValue		,
				msaBaEdfaHighTemperatureAlarmThreshold					,
				msaBaEdfaHighTemperatureAlarmThresholdMinimumValue			,
				msaBaEdfaHighTemperatureAlarmThresholdMaximumValue			,
				msaBaEdfaLowTemperatureAlarmThreshold					,
				msaBaEdfaLowTemperatureAlarmThresholdMinimumValue			,
				msaBaEdfaLowTemperatureAlarmThresholdMaximumValue			,
				msaBaEdfaHighTemperatureWarningThreshold				,
				msaBaEdfaHighTemperatureWarningThresholdMinimumValue			,
				msaBaEdfaHighTemperatureWarningThresholdMaximumValue			,
				msaBaEdfaLowTemperatureWarningThreshold					,
				msaBaEdfaLowTemperatureWarningThresholdMinimumValue			,
				msaBaEdfaLowTemperatureWarningThresholdMaximumValue			,
				msaBaEdfaHighOperatingCurrentAlarmThreshold				,
				msaBaEdfaHighOperatingCurrentAlarmThresholdMinimumValue			,
				msaBaEdfaHighOperatingCurrentAlarmThresholdMaximumValue			,
				msaBaEdfaLowOperatingCurrentAlarmThreshold				,
				msaBaEdfaLowOperatingCurrentAlarmThresholdMinimumValue			,
				msaBaEdfaLowOperatingCurrentAlarmThresholdMaximumValue			,
				msaBaEdfaHighOperatingCurrentWarningThreshold				,
				msaBaEdfaHighOperatingCurrentWarningThresholdMinimumValue		,
				msaBaEdfaHighOperatingCurrentWarningThresholdMaximumValue		,
				msaBaEdfaLowOperatingCurrentWarningThreshold				,
				msaBaEdfaLowOperatingCurrentWarningThresholdMinimumValue			,
				msaBaEdfaLowOperatingCurrentWarningThresholdMaximumValue			,
				msaBaEdfaHighTECCurrentAlarmThreshold					,
				msaBaEdfaHighTECCurrentAlarmThresholdMinimumValue			,
				msaBaEdfaHighTECCurrentAlarmThresholdMaximumValue			,
				msaBaEdfaLowTECCurrentAlarmThreshold					,
				msaBaEdfaLowTECCurrentAlarmThresholdMinimumValue			,
				msaBaEdfaLowTECCurrentAlarmThresholdMaximumValue			,
				msaBaEdfaHighTECCurrentWarningThreshold					,
				msaBaEdfaHighTECCurrentWarningThresholdMinimumValue			,
				msaBaEdfaHighTECCurrentWarningThresholdMaximumValue			,
				msaBaEdfaLowTECCurrentWarningThreshold					,
				msaBaEdfaLowTECCurrentWarningThresholdMinimumValue			,
				msaBaEdfaLowTECCurrentWarningThresholdMaximumValue			,
				msaBaEdfaVoaHighInputPowerAlarmThreshold				,
				msaBaEdfaVoaHighInputPowerAlarmThresholdMinimumValue			,
				msaBaEdfaVoaHighInputPowerAlarmThresholdMaximumValue			,
				msaBaEdfaVoaLowInputPowerAlarmThreshold					,
				msaBaEdfaVoaLowInputPowerAlarmThresholdMinimumValue			,
				msaBaEdfaVoaLowInputPowerAlarmThresholdMaximumValue			,
				msaBaEdfaVoaHighInputPowerWarningThreshold				,
				msaBaEdfaVoaHighInputPowerWarningThresholdMinimumValue			,
				msaBaEdfaVoaHighInputPowerWarningThresholdMaximumValue			,
				msaBaEdfaVoaLowInputPowerWarningThreshold				,
				msaBaEdfaVoaLowInputPowerWarningThresholdMinimumValue			,
				msaBaEdfaVoaLowInputPowerWarningThresholdMaximumValue			,
				msaBaEdfaModuleInputOpticalPowerLowAlarmThreshold			,
				msaBaEdfaModuleInputOpticalPowerLowAlarmThresholdMinimumValue		,
				msaBaEdfaModuleInputOpticalPowerLowAlarmThresholdMaximumValue		,
				msaBaEdfaModuleInputOpticalPowerHighAlarmThreshold			,
				msaBaEdfaModuleInputOpticalPowerHighAlarmThresholdMinimumValue		,
				msaBaEdfaModuleInputOpticalPowerHighAlarmThresholdMaximumValue		,
				msaBaEdfaModuleOutputOpticalPowerFailureAlarmThreshold			,
				msaBaEdfaModuleOutputOpticalPowerFailureAlarmThresholdMinimumValue	,
				msaBaEdfaModuleOutputOpticalPowerFailureAlarmThresholdMaximumValue	,
				msaBaEdfaModuleInputAlarmThreshold					,
				msaBaEdfaModuleInputAlarmThresholdMinimumValue				,
				msaBaEdfaModuleInputAlarmThresholdMaximumValue				,
				msaPaEdfaOpticalInputPowerFailureAlarmInhibit				,
				msaPaEdfaOpticalOutputPowerFailureAlarmInhibit				,
				msaPaEdfaLowOpticalInputPowerAlarmInhibit				,
				msaPaEdfaHighOpticalInputPowerAlarmInhibit				,
				msaPaEdfaLowOpticalOutputPowerAlarmInhibit				,
				msaPaEdfaHighOpticalOutputPowerAlarmInhibit				,
				msaPaEdfaLowTemperatureAlarmInhibit					,
				msaPaEdfaHighTemperatureAlarmInhibit					,
				msaPaEdfaLowOperatingCurrentAlarmInhibit				,
				msaPaEdfaHighOperatingCurrentAlarmInhibit				,
				msaPaEdfaLowTECCurrentAlarmInhibit					,
				msaPaEdfaHighTECCurrentAlarmInhibit					,
				msaPaEdfaLowVoaInputPowerAlarmInhibit					,
				msaPaEdfaHighVoaInputPowerAlarmInhibit					,
				msaPaEdfaInputOutOfRangeAlarmInhibit					,
				msaPaEdfaOutputOutOfRangeAlarmInhibit					,
				msaPaEdfaModuleCommunicationAlarmInhibit				,
				msaPaEdfaOpticalInputPowerFailureWarningInhibit				,
				msaPaEdfaOpticalOutputPowerFailureWarningInhibit			,
				msaPaEdfaLowOpticalInputPowerWarningInhibit				,
				msaPaEdfaHighOpticalInputPowerWarningInhibit				,
				msaPaEdfaLowOpticalOutputPowerWarningInhibit				,
				msaPaEdfaHighOpticalOutputPowerWarningInhibit				,
				msaPaEdfaLowTemperatureWarningInhibit					,
				msaPaEdfaHighTemperatureWarningInhibit					,
				msaPaEdfaLowOperatingCurrentWarningInhibit				,
				msaPaEdfaHighOperatingCurrentWarningInhibit				,
				msaPaEdfaLowTECCurrentWarningInhibit					,
				msaPaEdfaHighTECCurrentWarningInhibit					,
				msaPaEdfaLowVoaInputPowerWarningInhibit					,
				msaPaEdfaHighVoaInputPowerWarningInhibit				,
				msaPaEdfaInputOutOfRangeWarningInhibit					,
				msaPaEdfaOutputOutOfRangeWarningInhibit					,
				msaPaEdfaModuleCommunicationWarningInhibit				,
				msaPaEdfaOpticalInputPowerFailureAlarmSeverity				,
				msaPaEdfaOpticalOutputPowerFailureAlarmSeverity				,
				msaPaEdfaLowOpticalInputPowerAlarmSeverity				,
				msaPaEdfaHighOpticalInputPowerAlarmSeverity				,
				msaPaEdfaLowOpticalOutputPowerAlarmSeverity				,
				msaPaEdfaHighOpticalOutputPowerAlarmSeverity				,
				msaPaEdfaLowTemperatureAlarmSeverity					,
				msaPaEdfaHighTemperatureAlarmSeverity					,
				msaPaEdfaLowOperatingCurrentAlarmSeverity				,
				msaPaEdfaHighOperatingCurrentAlarmSeverity				,
				msaPaEdfaLowTECCurrentAlarmSeverity					,
				msaPaEdfaHighTECCurrentAlarmSeverity					,
				msaPaEdfaLowVoaInputPowerAlarmSeverity					,
				msaPaEdfaHighVoaInputPowerAlarmSeverity					,
				msaPaEdfaInputOutOfRangeAlarmSeverity					,
				msaPaEdfaOutputOutOfRangeAlarmSeverity					,
				msaPaEdfaModuleCommunicationAlarmSeverity				,
				msaPaEdfaOpticalInputPowerFailureWarningSeverity			,
				msaPaEdfaOpticalOutputPowerFailureWarningSeverity			,
				msaPaEdfaLowOpticalInputPowerWarningSeverity				,
				msaPaEdfaHighOpticalInputPowerWarningSeverity				,
				msaPaEdfaLowOpticalOutputPowerWarningSeverity				,
				msaPaEdfaHighOpticalOutputPowerWarningSeverity				,
				msaPaEdfaLowTemperatureWarningSeverity					,
				msaPaEdfaHighTemperatureWarningSeverity					,
				msaPaEdfaLowOperatingCurrentWarningSeverity				,
				msaPaEdfaHighOperatingCurrentWarningSeverity				,
				msaPaEdfaLowTECCurrentWarningSeverity					,
				msaPaEdfaHighTECCurrentWarningSeverity					,
				msaPaEdfaLowVoaInputPowerWarningSeverity				,
				msaPaEdfaHighVoaInputPowerWarningSeverity				,
				msaPaEdfaInputOutOfRangeWarningSeverity					,
				msaPaEdfaOutputOutOfRangeWarningSeverity				,
				msaPaEdfaModuleCommunicationWarningSeverity				,
				msaBaEdfaOpticalInputPowerFailureAlarmInhibit				,
				msaBaEdfaOpticalOutputPowerFailureAlarmInhibit				,
				msaBaEdfaLowOpticalInputPowerAlarmInhibit				,
				msaBaEdfaHighOpticalInputPowerAlarmInhibit				,
				msaBaEdfaLowOpticalOutputPowerAlarmInhibit				,
				msaBaEdfaHighOpticalOutputPowerAlarmInhibit				,
				msaBaEdfaLowTemperatureAlarmInhibit					,
				msaBaEdfaHighTemperatureAlarmInhibit					,
				msaBaEdfaLowOperatingCurrentAlarmInhibit				,
				msaBaEdfaHighOperatingCurrentAlarmInhibit				,
				msaBaEdfaLowTECCurrentAlarmInhibit					,
				msaBaEdfaHighTECCurrentAlarmInhibit					,
				msaBaEdfaLowVoaInputPowerAlarmInhibit					,
				msaBaEdfaHighVoaInputPowerAlarmInhibit					,
				msaBaEdfaInputOutOfRangeAlarmInhibit					,
				msaBaEdfaOutputOutOfRangeAlarmInhibit					,
				msaBaEdfaModuleCommunicationAlarmInhibit				,
				msaBaEdfaOpticalInputPowerFailureWarningInhibit				,
				msaBaEdfaOpticalOutputPowerFailureWarningInhibit			,
				msaBaEdfaLowOpticalInputPowerWarningInhibit				,
				msaBaEdfaHighOpticalInputPowerWarningInhibit				,
				msaBaEdfaLowOpticalOutputPowerWarningInhibit				,
				msaBaEdfaHighOpticalOutputPowerWarningInhibit				,
				msaBaEdfaLowTemperatureWarningInhibit					,
				msaBaEdfaHighTemperatureWarningInhibit					,
				msaBaEdfaLowOperatingCurrentWarningInhibit				,
				msaBaEdfaHighOperatingCurrentWarningInhibit				,
				msaBaEdfaLowTECCurrentWarningInhibit					,
				msaBaEdfaHighTECCurrentWarningInhibit					,
				msaBaEdfaLowVoaInputPowerWarningInhibit					,
				msaBaEdfaHighVoaInputPowerWarningInhibit				,
				msaBaEdfaInputOutOfRangeWarningInhibit					,
				msaBaEdfaOutputOutOfRangeWarningInhibit					,
				msaBaEdfaModuleCommunicationWarningInhibit				,
				msaBaEdfaOpticalInputPowerFailureAlarmSeverity				,
				msaBaEdfaOpticalOutputPowerFailureAlarmSeverity				,
				msaBaEdfaLowOpticalInputPowerAlarmSeverity				,
				msaBaEdfaHighOpticalInputPowerAlarmSeverity				,
				msaBaEdfaLowOpticalOutputPowerAlarmSeverity				,
				msaBaEdfaHighOpticalOutputPowerAlarmSeverity				,
				msaBaEdfaLowTemperatureAlarmSeverity					,
				msaBaEdfaHighTemperatureAlarmSeverity					,
				msaBaEdfaLowOperatingCurrentAlarmSeverity				,
				msaBaEdfaHighOperatingCurrentAlarmSeverity				,
				msaBaEdfaLowTECCurrentAlarmSeverity					,
				msaBaEdfaHighTECCurrentAlarmSeverity					,
				msaBaEdfaLowVoaInputPowerAlarmSeverity					,
				msaBaEdfaHighVoaInputPowerAlarmSeverity					,
				msaBaEdfaInputOutOfRangeAlarmSeverity					,
				msaBaEdfaOutputOutOfRangeAlarmSeverity					,
				msaBaEdfaModuleCommunicationAlarmSeverity				,
				msaBaEdfaOpticalInputPowerFailureWarningSeverity			,
				msaBaEdfaOpticalOutputPowerFailureWarningSeverity			,
				msaBaEdfaLowOpticalInputPowerWarningSeverity				,
				msaBaEdfaHighOpticalInputPowerWarningSeverity				,
				msaBaEdfaLowOpticalOutputPowerWarningSeverity				,
				msaBaEdfaHighOpticalOutputPowerWarningSeverity				,
				msaBaEdfaLowTemperatureWarningSeverity					,
				msaBaEdfaHighTemperatureWarningSeverity					,
				msaBaEdfaLowOperatingCurrentWarningSeverity				,
				msaBaEdfaHighOperatingCurrentWarningSeverity				,
				msaBaEdfaLowTECCurrentWarningSeverity					,
				msaBaEdfaHighTECCurrentWarningSeverity					,
				msaBaEdfaLowVoaInputPowerWarningSeverity				,
				msaBaEdfaHighVoaInputPowerWarningSeverity				,
				msaBaEdfaInputOutOfRangeWarningSeverity					,
				msaBaEdfaOutputOutOfRangeWarningSeverity				,
				msaBaEdfaModuleCommunicationWarningSeverity				,
				msaEdfaConfigurationTableRowStatus,

				msaPaEdfaOpticalInputPowerFailureAlarm				,
				msaPaEdfaOpticalOutputPowerFailureAlarm		                ,
				msaPaEdfaLowOpticalInputPowerAlarm                   		,
				msaPaEdfaLowOpticalInputPowerWarning                  		,
				msaPaEdfaHighOpticalInputPowerAlarm                   		,
				msaPaEdfaHighOpticalInputPowerWarning                 		,
				msaPaEdfaLowOpticalOutputPowerAlarm                   		,
				msaPaEdfaLowOpticalOutputPowerWarning                  		,
				msaPaEdfaHighOpticalOutputPowerAlarm                  		,
				msaPaEdfaHighOpticalOutputPowerWarning                  	,
				msaPaEdfaHighTemperatureAlarm                   		,
				msaPaEdfaHighTemperatureWarning                  		,
				msaPaEdfaLowTemperatureAlarm                   			,
				msaPaEdfaLowTemperatureWarning                  		,
				msaPaEdfaHighOperatingCurrentAlarm                   		,
				msaPaEdfaHighOperatingCurrentWarning                  		,
				msaPaEdfaLowOperatingCurrentAlarm                   		,
				msaPaEdfaLowOperatingCurrentWarning                  		,
				msaPaEdfaHighTECCurrentAlarm                   			,
				msaPaEdfaHighTECCurrentWarning                  		,
				msaPaEdfaLowTECCurrentAlarm                   			,
				msaPaEdfaLowTECCurrentWarning                 			,
				msaPaEdfaHighVoaInputPowerAlarm                   		,
				msaPaEdfaHighVoaInputPowerWarning                  		,
				msaPaEdfaLowVoaInputPowerAlarm                   		,
				msaPaEdfaLowVoaInputPowerWarning                  		,
				msaPaEdfaInputOutOfRangeAlarm                   		,
				msaPaEdfaOutputOutOfRangeAlarm                  		,
				msaPaEdfaModuleCommunicationAlarm				,
				msaBaEdfaOpticalInputPowerFailureAlarm				,
				msaBaEdfaOpticalOutputPowerFailureAlarm		                ,
				msaBaEdfaLowOpticalInputPowerAlarm                   		,
				msaBaEdfaLowOpticalInputPowerWarning                  		,
				msaBaEdfaHighOpticalInputPowerAlarm                   		,
				msaBaEdfaHighOpticalInputPowerWarning                 		,
				msaBaEdfaLowOpticalOutputPowerAlarm                   		,
				msaBaEdfaLowOpticalOutputPowerWarning                  		,
				msaBaEdfaHighOpticalOutputPowerAlarm                  		,
				msaBaEdfaHighOpticalOutputPowerWarning                  	,
				msaBaEdfaHighTemperatureAlarm                   		,
				msaBaEdfaHighTemperatureWarning                  		,
				msaBaEdfaLowTemperatureAlarm                   			,
				msaBaEdfaLowTemperatureWarning                  		,
				msaBaEdfaHighOperatingCurrentAlarm                   		,
				msaBaEdfaHighOperatingCurrentWarning                  		,
				msaBaEdfaLowOperatingCurrentAlarm                   		,
				msaBaEdfaLowOperatingCurrentWarning                  		,
				msaBaEdfaHighTECCurrentAlarm                   			,
				msaBaEdfaHighTECCurrentWarning                  		,
				msaBaEdfaLowTECCurrentAlarm                   			,
				msaBaEdfaLowTECCurrentWarning                 			,
				msaBaEdfaHighVoaInputPowerAlarm                   		,
				msaBaEdfaHighVoaInputPowerWarning                  		,
				msaBaEdfaLowVoaInputPowerAlarm                   		,
				msaBaEdfaLowVoaInputPowerWarning                  		,
				msaBaEdfaInputOutOfRangeAlarm                   		,
				msaBaEdfaOutputOutOfRangeAlarm                  		,
				msaBaEdfaModuleCommunicationAlarm				,
				msaEdfaAlarmTableRowStatus					,

				msaPaEdfaModuleOpticalInputPower,
				msaPaEdfaModuleOpticalOutputPower,
				msaPaEdfaModuleTemperature,
				msaPaEdfaModulePump1OperatingCurrentInAutomaticCurrentControlMode,
				msaPaEdfaModulePump1TecCurrent,
				msaPaEdfaModuleVoaInputPower,
				msaPaEdfaModuleVoaOutputPower,
				msaPaEdfaModuleAmplifiedSpontaneousEmissionPower,
				msaPaEdfaModuleOutputSignalGain,
				msaPaEdfaModuleVoaActualAttenuation,
				msaPaEdfaModulePump1TchipTemperature,

				msaBaEdfaModuleOpticalInputPower,
				msaBaEdfaModuleOpticalOutputPower,
				msaBaEdfaModuleTemperature,
				msaBaEdfaModulePump1TecCurrent,
				msaBaEdfaModuleVoaInputPower,
				msaBaEdfaModuleVoaOutputPower,
				msaBaEdfaModuleAmplifiedSpontaneousEmissionPower,
				msaBaEdfaModuleOutputSignalGain,
				msaBaEdfaModuleVoaActualAttenuation,
				msaBaEdfaModulePump1TchipTemperature,
				msaEdfaPerformanceTableRowStatus
			}
		STATUS	current

		DESCRIPTION
		"A collection of objects from RFC 1213 made current by this MIB module."

		::= { utlrnd 2 }
	
END

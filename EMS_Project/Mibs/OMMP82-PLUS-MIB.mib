--*****************************************************************************
--			MIB FILE FOR THE OMMP82-PLUS CARD
--*****************************************************************************

OMMP82-PLUS-MIB DEFINITIONS ::= BEGIN
 
          IMPORTS
        	
		RowStatus      			FROM STANDARD-MIB
			
		DisplayString  			FROM RFC1213-MIB       
    	
    		OBJECT-IDENTITY,
    		NOTIFICATION-TYPE,
    		MODULE-IDENTITY,
    		Integer32,
    		Unsigned32,
    		IpAddress,
    		TimeTicks			FROM SNMPv2-SMI
	 
	 	OBJECT-TYPE    			FROM RFC-1212
	 		
		MODULE-COMPLIANCE,
		OBJECT-GROUP,
		NOTIFICATION-GROUP		FROM SNMPv2-CONF
	
		node,
		rack,
		subRack,
		slot				FROM SCC-MIB
    
		enterprises			FROM RFC1155-SMI
	;

 

	utl   MODULE-IDENTITY
            LAST-UPDATED    	"1807130630Z"
            ORGANIZATION    	"United Telecoms Limited, Bangalore-560048."
            CONTACT-INFO    	"Website: http://www.utlindia.com."                                           
            DESCRIPTION     	"MIB module for UTL 40/80 channel DWDM."
            REVISION 	    	"1807130630Z"
            DESCRIPTION    	"MIB module for OMMP82-PLUS Card."
            ::= { enterprises 18036 }

	utlrnd  OBJECT-IDENTITY
            STATUS  current
            DESCRIPTION "UTL Research and Development."
            ::= { utl 1 }

	dwdm 	OBJECT IDENTIFIER				::=	{ utlrnd 1 }
	indus 	OBJECT IDENTIFIER				::=	{ dwdm 1 }
	ommp82Plus 	OBJECT IDENTIFIER 			::=	{ indus 87 }

	ommp82PlusCardGeneralDetails OBJECT IDENTIFIER		::=	{ ommp82Plus 1 }
	ommp82PlusConfiguration OBJECT IDENTIFIER 		::=	{ ommp82Plus 2 }
	ommp82PlusAlarm OBJECT IDENTIFIER 			::=	{ ommp82Plus 3 }
	ommp82PlusPerformance OBJECT IDENTIFIER 		::=	{ ommp82Plus 4 }
	ommp82PlusDiagnostics OBJECT IDENTIFIER 		::=	{ ommp82Plus 5 }

	ommp82PlusAlarmQuery OBJECT IDENTIFIER			::=	{ ommp82PlusAlarm 1 }
	ommp82PlusAlarmNotification OBJECT IDENTIFIER		::=	{ ommp82PlusAlarm 2 }

--******************************************************************************
--				CARD GENERAL DETAILS
--******************************************************************************

	ommp82PlusCardGeneralDetailsTable OBJECT-TYPE
		SYNTAX  SEQUENCE OF Ommp82PlusCardGeneralDetailsEntry 
		MAX-ACCESS  not-accessible
		STATUS  current
		DESCRIPTION
                     "Contains card general details' queries for the OMMP82-PLUS card"
		::= { ommp82PlusCardGeneralDetails 1 }

	ommp82PlusCardGeneralDetailsEntry  OBJECT-TYPE
		SYNTAX  Ommp82PlusCardGeneralDetailsEntry 
		MAX-ACCESS  not-accessible
		STATUS  current
		DESCRIPTION 
              	""
		INDEX   { node, rack, subRack, slot, ommp82PlusInterfaceNumber }
		::= { ommp82PlusCardGeneralDetailsTable 1 }

	Ommp82PlusCardGeneralDetailsEntry  ::= 
		SEQUENCE {
				ommp82PlusInterfaceNumber					INTEGER,
				ommp82PlusEepromCardId					        INTEGER,
				ommp82PlusEepromCardName					DisplayString,
				ommp82PlusEepromPartCode					DisplayString,
				ommp82PlusEepromCardSerialNumber				DisplayString,
				ommp82PlusEepromHardwareExternalReleaseVersion		        DisplayString,
				ommp82PlusSoftwareExternalReleaseVersion		        DisplayString,
				ommp82PlusEepromHardwareInternalReleaseVersion		        DisplayString,
				ommp82PlusSoftwareInternalReleaseVersion		        DisplayString,
				ommp82PlusEepromCardUidNumber			                DisplayString,
				ommp82PlusEepromCardEui48Number				        DisplayString,
				ommp82PlusEepromCardEui64Number				        DisplayString,
				ommp82PlusCardRootFileSystemVersion				DisplayString,
				ommp82PlusCardInstallationDate				        DisplayString,
				ommp82PlusCardCommissionDate				        DisplayString,
				ommp82PlusCardRunningTime					DisplayString,
				ommp82PlusCardRestartCount					INTEGER,
				ommp82PlusXfpReadyForOperation				        INTEGER,
				ommp82PlusXfpI2cCommunicationStatus				INTEGER,
				ommp82PlusXfpEepromPage					        INTEGER,
				ommp82PlusCheckCodeOfXfpEepromPage				INTEGER,
				ommp82PlusExtendedCheckCodeOfXfpEepromPage			INTEGER,
				ommp82PlusXfpVendorName					        DisplayString,
				ommp82PlusXfpVendorIeeeId					DisplayString,
				ommp82PlusXfpPartNumber					        DisplayString,
				ommp82PlusXfpSerialNumber					DisplayString,
				ommp82PlusXfpRevisionNumber					DisplayString,
				ommp82PlusXfpManufacturingDate				        DisplayString,
				ommp82PlusFixedXfpLaserWavelength				DisplayString,
				ommp82PlusXfpLaserWavelengthTolerance				DisplayString,
				ommp82PlusXfpWavelengthTunabilitySupported			INTEGER,
				ommp82PlusTunableXfpLaserWavelengthError			DisplayString,
				ommp82PlusTunableXfpLaserFrequencyError			        DisplayString,
				ommp82PlusTunableXfpLaserFirstFrequency			        DisplayString,
				ommp82PlusTunableXfpLaserLastFrequency			        DisplayString,
				ommp82PlusTunableXfpWavelengthGridSpacing			DisplayString,
				ommp82PlusXfpConnectorType					DisplayString,
				ommp82PlusXfpLinkLength					        DisplayString,
				ommp82PlusXfpCdrRateSupported				        INTEGER,
				ommp82PlusXfpSignalEncodingTypeSupported			INTEGER,
				ommp82PlusXfpTransceiverCodesSupported			        DisplayString,
				ommp82PlusXfpMaximumBitrateSupported			        DisplayString,
				ommp82PlusXfpMinimumBitrateSupported			        DisplayString,
				ommp82PlusXfpMaximumCaseTemperatureSupported		        INTEGER,
				ommp82PlusXfpMaximumPowerDissipationSupported			INTEGER,
				ommp82PlusXfpMaximumPowerDissipationSupportedAtPowerDownMode	INTEGER,
				ommp82PlusXfpMaximumCurrentLimitSupportedAtPlus5vSupply		INTEGER,
				ommp82PlusXfpMaximumCurrentLimitSupportedAtPlus3Point3vSupply	INTEGER,
				ommp82PlusXfpMaximumCurrentLimitSupportedAtPlus1Point8vSupply	INTEGER,
				ommp82PlusXfpMaximumCurrentLimitSupportedAtMinus5Point2vSupply	INTEGER,
				ommp82PlusXfpLineLoopbackSupported				INTEGER,
				ommp82PlusXfpXfiLoopbackSupported				INTEGER,
				ommp82PlusXfpOptionalVpsSupported				INTEGER,
				ommp82PlusXfpLaserDisableThroughI2cSupported			INTEGER,
				ommp82PlusXfpPowerDownThroughI2cSupported			INTEGER,
				ommp82PlusXfpVpsLvRegulatorModeSupported			INTEGER,
				ommp82PlusXfpVpsBypassedRegulatorModeSupported			INTEGER,
				ommp82PlusXfpActiveFecControlSupported				INTEGER,
				ommp82PlusXfpOptionalCmuModeSupported				INTEGER,
				ommp82PlusXfpFecBerSupported					INTEGER,
				ommp82PlusXfpReceivePowerMeasurementIsInOmaOrAverage		INTEGER,
				ommp82PlusXfpActiveWavelengthControlSupported			INTEGER,
				ommp82PlusXfpTransmitterIsCooledOrUncooled			INTEGER,
				ommp82PlusXfpReceiverTypeIsPinOrApd                             INTEGER,
				ommp82PlusSfpEepromPage						INTEGER,
				ommp82PlusCheckCodeOfSfpEepromPage				INTEGER,
				ommp82PlusExtendedCheckCodeOfSfpEepromPage			INTEGER,
				ommp82PlusSfpVendorName						DisplayString,
				ommp82PlusSfpVendorIeeeId					DisplayString,
				ommp82PlusSfpPartNumber						DisplayString,
				ommp82PlusSfpSerialNumber					DisplayString,
				ommp82PlusSfpRevisionNumber					DisplayString,
				ommp82PlusSfpManufacturingDate					DisplayString,
				ommp82PlusFixedSfpLaserWavelength				DisplayString,
				ommp82PlusSfpConnectorType					DisplayString,
				ommp82PlusSfpLinkLength						DisplayString,
				ommp82PlusSfpSignalEncodingTypeSupported			INTEGER,
				ommp82PlusSfpTransceiverCodesSupported				DisplayString,
				ommp82PlusSfpMaximumBitrateSupported				DisplayString,
				ommp82PlusSfpNominalBitrateSupported				DisplayString,
				ommp82PlusSfpMinimumBitrateSupported				DisplayString,
				ommp82PlusCardGeneralDetailsTableRowStatus			RowStatus
			 }
	

	ommp82PlusInterfaceNumber OBJECT-TYPE
		SYNTAX  INTEGER
		MAX-ACCESS  not-accessible
		STATUS  current
		DESCRIPTION
			"Interface number represents the port number.
			InterfaceNumber to port mapping is as follows:
			1 - CLIENT-1,
			2 - CLIENT-2,
			3 - CLIENT-3,
			4 - CLIENT-4,
			5 - CLIENT-5,
			6 - CLIENT-6,
			7 - CLIENT-7,
			8 - CLIENT-8,
			9 - LINE-1(Primary),
			10 - LINE-2(Secondary)
			-----------------------------
			Values of the demultiplexing properties can be accessed
			with respect to slice number.  In such cases the
			InterfaceNumber will represent the slice number.
			1 - Slice-1
			2 - Slice-2
			3 - Slice-3
			4 - Slice-4
			-----------------------------
			For properties which do not apply on any interface,
			the interface number must be passed as 0
			-----------------------------"
		::= { ommp82PlusCardGeneralDetailsEntry 1 }
	
	ommp82PlusEepromCardId OBJECT-TYPE		 
		SYNTAX  INTEGER
		MAX-ACCESS  read-only
		STATUS current
		DESCRIPTION
			"Tells the card ID of the OMMP82-PLUS card, present in the EEPROM
			-----------------------------
			ommp82PlusInterfaceNumber: 0
			-----------------------------"
		::= { ommp82PlusCardGeneralDetailsEntry 2 }

	ommp82PlusEepromCardName OBJECT-TYPE		 
		SYNTAX  DisplayString
		MAX-ACCESS  read-only
		STATUS current
		DESCRIPTION
			"Tells the card name of the OMMP82-PLUS card, present in the EEPROM
			-----------------------------
			ommp82PlusInterfaceNumber: 0
			-----------------------------"
		::= { ommp82PlusCardGeneralDetailsEntry 3 }

	ommp82PlusEepromPartCode OBJECT-TYPE		 
		SYNTAX  DisplayString
		MAX-ACCESS  read-only
		STATUS current
		DESCRIPTION
			"Tells the part code of the OMMP82-PLUS card, present in the EEPROM
			-----------------------------
			ommp82PlusInterfaceNumber: 0
			-----------------------------"
		::= { ommp82PlusCardGeneralDetailsEntry 4 }

	ommp82PlusEepromCardSerialNumber OBJECT-TYPE		 
		SYNTAX  DisplayString
		MAX-ACCESS  read-write
		STATUS current
		DESCRIPTION
			"This property get / set the information about 
			OMMP82-PLUS Card's Serial Number.
			-----------------------------
			ommp82PlusInterfaceNumber: 0
			-----------------------------
			Values:
			eg: 123456
			-----------------------------"
		::= { ommp82PlusCardGeneralDetailsEntry 5 }

	ommp82PlusEepromHardwareExternalReleaseVersion OBJECT-TYPE		 
		SYNTAX  DisplayString
		MAX-ACCESS  read-only
		STATUS current
		DESCRIPTION
			"Gets the Card's Hardware External Release Version. 
			This detail will be displayed to the customer.
			This version will increment only if there are significant
			architectural changes in the product
			-----------------------------
			ommp82PlusInterfaceNumber: 0
			-----------------------------
			Value:
			eg: 0.1
			-----------------------------"
		::= { ommp82PlusCardGeneralDetailsEntry 6 }

	ommp82PlusSoftwareExternalReleaseVersion OBJECT-TYPE		 
		SYNTAX  DisplayString
		MAX-ACCESS  read-only
		STATUS current
		DESCRIPTION
			"Gets the Card's Software External Release Version. 
			This detail will be displayed to the customer.
			This version will increment only if there are
			significant architectural changes in the product
			-----------------------------
			ommp82PlusInterfaceNumber: 0
			-----------------------------
			Value:
			eg: 0.1
			-----------------------------"
		::= { ommp82PlusCardGeneralDetailsEntry 7 }

	ommp82PlusEepromHardwareInternalReleaseVersion OBJECT-TYPE		 
		SYNTAX  DisplayString
		MAX-ACCESS  read-only
		STATUS current
		DESCRIPTION
			"Gets the Card's Hardware Internal Release Version.
			This detail is used for development purposes only.
			It differs from the external hardware version.
			-----------------------------
			ommp82PlusInterfaceNumber: 0
			-----------------------------
			Value:
			eg: 4.1
			-----------------------------"
		::= { ommp82PlusCardGeneralDetailsEntry 8 }

	ommp82PlusSoftwareInternalReleaseVersion OBJECT-TYPE		 
		SYNTAX  DisplayString
		MAX-ACCESS  read-only
		STATUS current
		DESCRIPTION
			"Gets the Card's Software Internal Release Version.
			This detail is used for development purposes only.
			It differs from the external software version.
		      	-----------------------------
			ommp82PlusInterfaceNumber: 0
			-----------------------------
			Value:
			eg: 5.1
			-----------------------------"
		::= { ommp82PlusCardGeneralDetailsEntry 9 }

	ommp82PlusEepromCardUidNumber OBJECT-TYPE		 
		SYNTAX  DisplayString
		MAX-ACCESS  read-only
		STATUS current
		DESCRIPTION
			"Tells the Card Unique IDentifier. It is a 4 byte
			address used to uniquely identify a card.
			----------------------------
			ommp82PlusInterfaceNumber: 0
			------------------------------
			Value:
		      	eg: 12345678
			-----------------------------"
		::= { ommp82PlusCardGeneralDetailsEntry 10 }

	ommp82PlusEepromCardEui48Number OBJECT-TYPE		 
		SYNTAX  DisplayString
		MAX-ACCESS  read-only
		STATUS current
		DESCRIPTION
			"Tells the Card EUI-48 Number. It is a 6 byte address
			used to uniquely identify a card.
			-----------------------------
			ommp82PlusInterfaceNumber: 0
			-----------------------------
			Value:
		      	eg: 0004A3123456
			-----------------------------"
		::= { ommp82PlusCardGeneralDetailsEntry 11 }

	ommp82PlusEepromCardEui64Number OBJECT-TYPE		 
		SYNTAX  DisplayString
		MAX-ACCESS  read-only
		STATUS current
		DESCRIPTION
			"Tells the Card EUI-64 Number. It is a 8 byte address
			used to uniquely identify a card.
			-----------------------------
			ommp82PlusInterfaceNumber: 0
			-----------------------------
			Value:
		      	eg: 0004A31234567890
			-----------------------------"
		::= { ommp82PlusCardGeneralDetailsEntry 12 }
		
        ommp82PlusCardRootFileSystemVersion OBJECT-TYPE		 
		SYNTAX  DisplayString
		MAX-ACCESS  read-only
		STATUS current
		DESCRIPTION
			"Tells the Card's Root File System Version
			-----------------------------
			ommp82PlusInterfaceNumber: 0
			-----------------------------
			Value:
		      	eg: 8
			-----------------------------"
		::= { ommp82PlusCardGeneralDetailsEntry 13 }

	ommp82PlusCardInstallationDate OBJECT-TYPE		 
		SYNTAX  DisplayString
		MAX-ACCESS  read-write
		STATUS current
		DESCRIPTION
			"Gets the card's installation date in
			dd/mm/yyyy format
			-----------------------------
			ommp82PlusInterfaceNumber: 0
			-----------------------------
			Value:
		      	eg: 12/03/2016
			-----------------------------"
		::= { ommp82PlusCardGeneralDetailsEntry 21 }

	ommp82PlusCardCommissionDate OBJECT-TYPE		 
		SYNTAX  DisplayString
		MAX-ACCESS  read-write
		STATUS current
		DESCRIPTION
			"Gets the card's commission date in
			dd/mm/yyyy format
			-----------------------------
			ommp82PlusInterfaceNumber: 0
			-----------------------------
			Value:
		      	eg: 20/03/2016
			-----------------------------"
		::= { ommp82PlusCardGeneralDetailsEntry 22 }

	ommp82PlusCardRunningTime OBJECT-TYPE		 
		SYNTAX  DisplayString
		MAX-ACCESS  read-only
		STATUS current
		DESCRIPTION
			"Get the duration of time for which the card is
			operational/running
			-----------------------------
			ommp82PlusInterfaceNumber: 0
			-----------------------------
			Values:
		      	eg: 4d:3h:2m:1s
			-----------------------------"
		::= { ommp82PlusCardGeneralDetailsEntry 23 }

	ommp82PlusCardRestartCount OBJECT-TYPE		 
		SYNTAX  INTEGER
		MAX-ACCESS  read-only
		STATUS current
		DESCRIPTION
			"Get the number of times the card has been soft reset.
			This value will get reset to 0 on factory reset.
			-----------------------------
			ommp82PlusInterfaceNumber: 0
			-----------------------------
			Values:
		      	eg: 10
			-----------------------------"
		::= { ommp82PlusCardGeneralDetailsEntry 24 }

	ommp82PlusXfpReadyForOperation OBJECT-TYPE		 
		SYNTAX  INTEGER
		MAX-ACCESS  read-only
		STATUS current
		DESCRIPTION
			"Module not ready indicates that the XFP
			has detected a condition that tells
			transmit or receive data is invalid.
			It shall consist of logical OR of the
			following signals:
			> Transmit Signal Conditioner Loss of Lock
			> Transmitter Laser Fault
			> Receiver Signal Conditioner Loss of Lock
			(Ref: INF-8077 2.4.1)
			-----------------------------
			ommp82PlusInterfaceNumber:
			9 - LINE-1
			10 - LINE-2
			-----------------------------
			Values:		
			1 - XFP is ready for operation 
			0 - XFP is not ready for operation
			-----------------------------"
		::= { ommp82PlusCardGeneralDetailsEntry 31 }

	ommp82PlusXfpI2cCommunicationStatus OBJECT-TYPE		 
		SYNTAX  INTEGER
		MAX-ACCESS  read-write
		STATUS current
		DESCRIPTION
			"Tells whether the XFP can be accessed
			on a single 2-wire interface bus or not.
			(Ref: INF-8077 2.4.2)
			-----------------------------
			ommp82PlusInterfaceNumber:
			9 - LINE-1
			10 - LINE-2
			-----------------------------
			Values:			
			1 - Enable I2C communication for XFP
				i.e. the XFP responds to 2-wire serial
				communication commands.
			0 - Disable I2C communication for XFP
				i.e. the XFP will not respond to or
				acknowledge any 2-wire interface communication
				from the host.
			-----------------------------"
		::= { ommp82PlusCardGeneralDetailsEntry 32 }

	ommp82PlusXfpEepromPage OBJECT-TYPE		 
		SYNTAX  INTEGER
		MAX-ACCESS  read-write
		STATUS current
		DESCRIPTION
			"This property sets/gets the XFP EEPROM page, 
			the value represents the XFP EEPROM page number.
			-----------------------------
			ommp82PlusInterfaceNumber:
			9 - LINE-1
			10 - LINE-2
			-----------------------------
			Values:			
			eg: 1(EEPROM Page number)
			-----------------------------"
		::= { ommp82PlusCardGeneralDetailsEntry 33 }

	ommp82PlusCheckCodeOfXfpEepromPage OBJECT-TYPE		 
		SYNTAX  INTEGER
		MAX-ACCESS  read-only
		STATUS current
		DESCRIPTION
			"This property provides the XFP
			check code(checksum) value for bytes 128 to 190
			present in XFP EEPROM Page number 1. 
			-----------------------------
			ommp82PlusInterfaceNumber:
			9 - LINE-1
			10 - LINE-2
			-----------------------------
			Values:			
			eg: 1(EEPROM Page number)
			-----------------------------"
		::= { ommp82PlusCardGeneralDetailsEntry 34 }

	ommp82PlusExtendedCheckCodeOfXfpEepromPage OBJECT-TYPE		 
		SYNTAX  INTEGER
		MAX-ACCESS  read-only
		STATUS current
		DESCRIPTION
			"This property provides the XFP
			extended check code(checksum) value for bytes 192 to 222
			present in XFP EEPROM Page number 1. 
			-----------------------------
			ommp82PlusInterfaceNumber:
			9 - LINE-1
			10 - LINE-2
			-----------------------------
			Values:			
			eg: 1(EEPROM Page number)
			-----------------------------"
		::= { ommp82PlusCardGeneralDetailsEntry 35 }

	ommp82PlusXfpVendorName OBJECT-TYPE		 
		SYNTAX  DisplayString
		MAX-ACCESS  read-only
		STATUS current
		DESCRIPTION
			"This property provides Vendor Name for given XFP. 
			The vendor name shall be the full name of the 
			corporation, a commonly accepted abbreviation of 
			the name of the corporation, the SCSI company code
			for the corporation, or the stock exchange code for
			the corporation.
			-----------------------------
			ommp82PlusInterfaceNumber:
			9 - LINE-1
			10 - LINE-2
			-----------------------------
			Values:			
			eg: WTD
			-----------------------------"
		::= { ommp82PlusCardGeneralDetailsEntry 36 }

	ommp82PlusXfpVendorIeeeId OBJECT-TYPE		 
		SYNTAX  DisplayString
		MAX-ACCESS  read-only
		STATUS current
		DESCRIPTION
			"This property defines the IEEE company Identifier for
			the vendor of XFP. A value of all zero in the 3-byte
			field indicates that the Vendor OUI is unspecified.
			-----------------------------
			ommp82PlusInterfaceNumber:
			9 - LINE-1
			10 - LINE-2
			-----------------------------
			Values:			
			eg: 010
			-----------------------------"
		::= { ommp82PlusCardGeneralDetailsEntry 37 }

	ommp82PlusXfpPartNumber OBJECT-TYPE		 
		SYNTAX  DisplayString
		MAX-ACCESS  read-only
		STATUS current
		DESCRIPTION
			"This property defines the vendor part number or
			product name of the XFP. A value of all zero
			indicates that the vendor Part Number is unspecified.
			-----------------------------
			ommp82PlusInterfaceNumber:
			9 - LINE-1
			10 - LINE-2
			-----------------------------
			Values:			
			eg: FTRX-1811-2D2
			-----------------------------"
		::= { ommp82PlusCardGeneralDetailsEntry 38 }

	ommp82PlusXfpSerialNumber OBJECT-TYPE		 
		SYNTAX  DisplayString
		MAX-ACCESS  read-only
		STATUS current
		DESCRIPTION
			"This property provides vendor serial number defining
			the vendor’s serial number for the XFP. A value of all
			zero in the 16-byte field indicates that the vendor
			serial number is unspecified.
			-----------------------------
			ommp82PlusInterfaceNumber:
			9 - LINE-1
			10 - LINE-2
			-----------------------------
			Values:			
			eg: KBG02CU
			-----------------------------"
		::= { ommp82PlusCardGeneralDetailsEntry 39 }

	ommp82PlusXfpRevisionNumber OBJECT-TYPE		 
		SYNTAX  DisplayString
		MAX-ACCESS  read-only
		STATUS current
		DESCRIPTION
			"The vendor revision number defining the vendor’s
			product revision number. A value of all zero indicates
			that the vendor revision number is unspecified
			-----------------------------
			ommp82PlusInterfaceNumber:
			9 - LINE-1
			10 - LINE-2
			-----------------------------
			Values:			
			eg: RT
			-----------------------------"
		::= { ommp82PlusCardGeneralDetailsEntry 40 }

	ommp82PlusXfpManufacturingDate OBJECT-TYPE		 
		SYNTAX  DisplayString
		MAX-ACCESS  read-only
		STATUS current
		DESCRIPTION
			"This property defines the manufacturing date for 
			XFP. A value of 8-byte field in ASCII which represents
			year, month and date of each two bytes. 
			Extra two bytes may be blank
			-----------------------------
			ommp82PlusInterfaceNumber:
			9 - LINE-1
			10 - LINE-2
			-----------------------------
			Values:			
			eg: 160224
			-----------------------------"
		::= { ommp82PlusCardGeneralDetailsEntry 41 }

	ommp82PlusFixedXfpLaserWavelength OBJECT-TYPE		 
		SYNTAX  DisplayString
		MAX-ACCESS  read-only
		STATUS current
		DESCRIPTION
			"This property provides transmitter LASER wavelength(nm)
			of the XFP
			-----------------------------
			ommp82PlusInterfaceNumber:
			9 - LINE-1
			10 - LINE-2
			-----------------------------
			Values:			
			eg: 1310
			-----------------------------"
		::= { ommp82PlusCardGeneralDetailsEntry 42 }

	ommp82PlusXfpLaserWavelengthTolerance OBJECT-TYPE		 
		SYNTAX  DisplayString
		MAX-ACCESS  read-only
		STATUS current
		DESCRIPTION
			"This property provides XFP wavelength tolerance in GhZ
			-----------------------------
			ommp82PlusInterfaceNumber:
			9 - LINE-1
			10 - LINE-2
			-----------------------------
			Values:			
			eg: 0.02
			-----------------------------"
		::= { ommp82PlusCardGeneralDetailsEntry 43 }

	ommp82PlusXfpWavelengthTunabilitySupported OBJECT-TYPE		 
		SYNTAX  INTEGER
		MAX-ACCESS  read-only
		STATUS current
		DESCRIPTION
			"This property provides information whether the XFP
			supports wavelength tunability or not.
			-----------------------------
			ommp82PlusInterfaceNumber:
			9 - LINE-1
			10 - LINE-2
			-----------------------------
			Values:			
			1 - XFP supports wavelength tunability
			0 - XFP does not supports wavelength tunability
			-----------------------------"
		::= { ommp82PlusCardGeneralDetailsEntry 44 }

	ommp82PlusTunableXfpLaserWavelengthError OBJECT-TYPE		 
		SYNTAX  DisplayString
		MAX-ACCESS  read-only
		STATUS current
		DESCRIPTION
			"This property provides wavelength error in picometer(pm)
			-----------------------------
			ommp82PlusInterfaceNumber:
			9 - LINE-1
			10 - LINE-2
			-----------------------------
			Values:			
			eg: 0.02
			-----------------------------"
		::= { ommp82PlusCardGeneralDetailsEntry 45 }

	ommp82PlusTunableXfpLaserFrequencyError OBJECT-TYPE		 
		SYNTAX  DisplayString
		MAX-ACCESS  read-only
		STATUS current
		DESCRIPTION
			"This property provides frequency error in Ghz.
			-----------------------------
			ommp82PlusInterfaceNumber:
			9 - LINE-1
			10 - LINE-2
			-----------------------------
			Values:			
			eg: 0.03
			-----------------------------"
		::= { ommp82PlusCardGeneralDetailsEntry 46 }

	ommp82PlusTunableXfpLaserFirstFrequency OBJECT-TYPE		 
		SYNTAX  DisplayString
		MAX-ACCESS  read-only
		STATUS current
		DESCRIPTION
			"This property defines the first LASER frequency of XFP.
			The two byte value is specified in units of THz.
			-----------------------------
			ommp82PlusInterfaceNumber:
			9 - LINE-1
			10 - LINE-2
			-----------------------------
			Values:			
			eg: 1529.45
			-----------------------------"
		::= { ommp82PlusCardGeneralDetailsEntry 47 }

	ommp82PlusTunableXfpLaserLastFrequency OBJECT-TYPE		 
		SYNTAX  DisplayString
		MAX-ACCESS  read-only
		STATUS current
		DESCRIPTION
			"This property defines the last laser frequency of XFP.
		 	 The two byte value is specified in units of THz.
			-----------------------------
			ommp82PlusInterfaceNumber:
			9 - LINE-1
			10 - LINE-2
			-----------------------------
			Values:			
			eg: 1563.45
			-----------------------------"
		::= { ommp82PlusCardGeneralDetailsEntry 48 }

	ommp82PlusTunableXfpWavelengthGridSpacing OBJECT-TYPE		 
		SYNTAX  DisplayString
		MAX-ACCESS  read-only
		STATUS current
		DESCRIPTION
			"This property gives difference in the wavelength
			between two channels In GHz.
			-----------------------------
			ommp82PlusInterfaceNumber:
			9 - LINE-1
			10 - LINE-2
			-----------------------------
			Values:
			eg: 50
			-----------------------------"
		::= { ommp82PlusCardGeneralDetailsEntry 49 }

	ommp82PlusXfpConnectorType OBJECT-TYPE		 
		SYNTAX  DisplayString
		MAX-ACCESS  read-only
		STATUS current
		DESCRIPTION
			"This property provides information of the XFP
			connector, value indicates the external connector
			provided on the XFP.
			-----------------------------
			ommp82PlusInterfaceNumber:
			9 - LINE-1
			10 - LINE-2
			-----------------------------
			Values:
			00h 	Unknown or unspecified
			01h 	SC
			02h 	Fibre Channel Style 1 copper connector
			03h 	Fibre Channel Style 2 copper connector
			04h 	BNC/TNC
			05h 	Fibre Channel coaxial headers
			06h 	FiberJack
			07h 	LC
			08h 	MT-RJ
			09h 	MU
			0Ah 	SG
			0Bh 	Optical pigtail
			0C-1Fh 	Reserved
			20h 	HSSDC II
			21h 	Copper Pigtail
			22h-7Fh Reserved
			80-FFh 	Vendor specific
			-----------------------------"
		::= { ommp82PlusCardGeneralDetailsEntry 50 }

	ommp82PlusXfpLinkLength OBJECT-TYPE		 
		SYNTAX  DisplayString
		MAX-ACCESS  read-only
		STATUS current
		DESCRIPTION
			"This property provides link length suported by the XFP
			-----------------------------
			ommp82PlusInterfaceNumber:
			9 - LINE-1
			10 - LINE-2
			-----------------------------
			Values:
			eg: 80.00
			-----------------------------"
		::= { ommp82PlusCardGeneralDetailsEntry 51 }

	ommp82PlusXfpCdrRateSupported OBJECT-TYPE		 
		SYNTAX  INTEGER
		MAX-ACCESS  read-only
		STATUS current
		DESCRIPTION
			"This property indicates which rates are supported by
			the CDR present in XFP.
			-----------------------------
			ommp82PlusInterfaceNumber:
			9 - LINE-1
			10 - LINE-2
			-----------------------------
			Values:
			Return value 1-Byte represetation:
			Byte-1  CDR Rates
			Bit-7	9.95 Gb/s
			Bit-6	10.3 Gb/s
			Bit-5	10.5 Gb/s
			Bit-4	10.7 Gb/s
			Bit-3	11.1 Gb/s
			Bit-2	Reserved
			Bit-1	Dont care for this property
			Bit-0	Dont care for this property
			-----------------------------"
		::= { ommp82PlusCardGeneralDetailsEntry 52 }

	ommp82PlusXfpSignalEncodingTypeSupported OBJECT-TYPE		 
		SYNTAX  INTEGER
		MAX-ACCESS  read-only
		STATUS current
		DESCRIPTION
			"This property indicates the serial encoding mechanisms
			that are supported by the XFP.
			-----------------------------
			ommp82PlusInterfaceNumber:
			9 - LINE-1
			10 - LINE-2
			-----------------------------
			Values:
			Return value 1-Byte represetation:
			Byte-1  Encoding Type
			Bit-7	64B/66B          
			Bit-6	8B10B     	 	 
			Bit-5	SONET Scrambled  
			Bit-4	NRZ              
			Bit-3	RZ              
			Bit-2	Reserved        
			Bit-1	Reserved         
			Bit-0	Reserved 
			-----------------------------"
		::= { ommp82PlusCardGeneralDetailsEntry 53 }

	ommp82PlusXfpTransceiverCodesSupported OBJECT-TYPE		 
		SYNTAX  DisplayString
		MAX-ACCESS  read-only
		STATUS current
		DESCRIPTION
			"The identifier value specifies which transceiver
			codes are supported by the XFP
			-----------------------------
			ommp82PlusInterfaceNumber:
			9 - LINE-1
			10 - LINE-2
			-----------------------------
			Values:
			Return value 8-Byte represetation:
			---------------------------------------------------------------------------------------------------------------------------------------
				  Byte-1	  Byte-2	          Byte-3	  Byte-4	          Byte-5    Byte-6    Byte-7	        Byte-8
			---------------------------------------------------------------------------------------------------------------------------------------
			Bit-7	 10GBASE-SR	 1200-MX-SN-I        	 Reserved	 1000BASE-SX/1xFC MMF	 I-64.1r   S-64.1    L-64.1	       V-64.2a
			Bit-6	 10GBASE-LR	 1200-SM-LL-L	         Reserved	 1000BASE-LX/1xFC-SMF	 I-64.1	   S-64.2a   L-64.2a	       V-64.2b
			Bit-5	 10GBASE-ER	 Extended 1550 nm	 Reserved	 2xFC-MMF/2xFC-SMF	 I-64.2r   S-64.2b   L-64.2b	       V-64.3
			Bit-4	 10GBASE-LRM	 Intermediate 1300 nm	 Reserved	 OC-48-SR	         I-64.2	   S-64.3a   L-64.2c	       Reserved
			Bit-3	 10GBASE-SW	 Reserved	         Reserved	 OC-48-IR	         I-64.3	   S-64.3b   L-64.3	       Reserved
			Bit-2	 10GBASE-LW	 Reserved	         Reserved	 OC-48-LR	         I-64.5	   S-64.5a   G.959.1 P1L1-2D2  Reserved
			Bit-1	 10GBASE-EW	 Reserved	         Reserved	 Reserved	         Reserved  S-64.5b   Reserved	       Reserved
			Bit-0	 Reserved	 Reserved	         Reserved	 Reserved	         Reserved  Reserved  Reserved	       Reserved
			-----------------------------"
		::= { ommp82PlusCardGeneralDetailsEntry 54 }

	ommp82PlusXfpMaximumBitrateSupported OBJECT-TYPE		 
		SYNTAX  DisplayString
		MAX-ACCESS  read-only
		STATUS current
		DESCRIPTION
			"This property provides maximum bit rate(Gbps) value
			supported by XFP
			-----------------------------
			ommp82PlusInterfaceNumber:
			9 - LINE-1
			10 - LINE-2
			-----------------------------
			Values: 9.5
			-----------------------------"
		::= { ommp82PlusCardGeneralDetailsEntry 55 }

	ommp82PlusXfpMinimumBitrateSupported OBJECT-TYPE		 
		SYNTAX  DisplayString
		MAX-ACCESS  read-only
		STATUS current
		DESCRIPTION
			"This property provides minimum bit rate(Gbps) value
			supported by XFP
			-----------------------------
			ommp82PlusInterfaceNumber:
			9 - LINE-1
			10 - LINE-2
			-----------------------------
			Values: 5.5
			-----------------------------"

		::= { ommp82PlusCardGeneralDetailsEntry 56 }

	ommp82PlusXfpMaximumCaseTemperatureSupported OBJECT-TYPE		 
		SYNTAX  INTEGER
		MAX-ACCESS  read-only
		STATUS current
		DESCRIPTION
			"This property provides the maximum case temperature
			(degree celcius) supported by XFP.
			-----------------------------
			ommp82PlusInterfaceNumber:
			9 - LINE-1
			10 - LINE-2
			-----------------------------
			Values:
			eg: 70
			-----------------------------"


		::= { ommp82PlusCardGeneralDetailsEntry 57 }

	ommp82PlusXfpMaximumPowerDissipationSupported OBJECT-TYPE		 
		SYNTAX  INTEGER
		MAX-ACCESS  read-only
		STATUS current
		DESCRIPTION
			"This property provides the maximum power dissipation(mW)
			supported from XFP.
			-----------------------------
			ommp82PlusInterfaceNumber:
			9 - LINE-1
			10 - LINE-2
			-----------------------------
			Values:
			eg: 25
			-----------------------------"
		::= { ommp82PlusCardGeneralDetailsEntry 58 }

	ommp82PlusXfpMaximumPowerDissipationSupportedAtPowerDownMode OBJECT-TYPE		 
		SYNTAX  INTEGER
		MAX-ACCESS  read-only
		STATUS current
		DESCRIPTION
			"This property provides the maximum power dissipation(mW)
			supported from XFP in power-down mode.
			-----------------------------
			ommp82PlusInterfaceNumber:
			9 - LINE-1
			10 - LINE-2
			-----------------------------
			Values:
			eg: 20
			-----------------------------"
		::= { ommp82PlusCardGeneralDetailsEntry 59 }

	ommp82PlusXfpMaximumCurrentLimitSupportedAtPlus5vSupply OBJECT-TYPE		 
		SYNTAX  INTEGER
		MAX-ACCESS  read-only
		STATUS current
		DESCRIPTION
			"This property defines the maximum current(mA) required
			by XFP at +5V power supply.
			-----------------------------
			ommp82PlusInterfaceNumber:
			9 - LINE-1
			10 - LINE-2
			-----------------------------
			Values:
			eg: 50
			-----------------------------"
		::= { ommp82PlusCardGeneralDetailsEntry 60 }

	ommp82PlusXfpMaximumCurrentLimitSupportedAtPlus3Point3vSupply OBJECT-TYPE		 
		SYNTAX  INTEGER
		MAX-ACCESS  read-only
		STATUS current
		DESCRIPTION
			"This property defines the maximum current(mA) required
			by XFP at +3.3V power supply.
			-----------------------------
			ommp82PlusInterfaceNumber:
			9 - LINE-1
			10 - LINE-2
			-----------------------------
			Values:
			eg: 50
			-----------------------------"
		::= { ommp82PlusCardGeneralDetailsEntry 61 }

	ommp82PlusXfpMaximumCurrentLimitSupportedAtPlus1Point8vSupply OBJECT-TYPE		 
		SYNTAX  INTEGER
		MAX-ACCESS  read-only
		STATUS current
		DESCRIPTION
			"This property defines the maximum current(mA) required
			by XFP at +1.8V power supply.
			-----------------------------
			ommp82PlusInterfaceNumber:
			9 - LINE-1
			10 - LINE-2
			-----------------------------
			Values:
			eg: 50
			-----------------------------"
		::= { ommp82PlusCardGeneralDetailsEntry 62 }

	ommp82PlusXfpMaximumCurrentLimitSupportedAtMinus5Point2vSupply OBJECT-TYPE		 
		SYNTAX  INTEGER
		MAX-ACCESS  read-only
		STATUS current
		DESCRIPTION
			"This property defines the maximum current(mA) required
			by XFP at -5.2V power supply.
			-----------------------------
			ommp82PlusInterfaceNumber:
			9 - LINE-1
			10 - LINE-2
			-----------------------------
			Values:
			eg: 50
			-----------------------------"
		::= { ommp82PlusCardGeneralDetailsEntry 63 }

	ommp82PlusXfpLineLoopbackSupported OBJECT-TYPE		 
		SYNTAX  INTEGER
		MAX-ACCESS  read-only
		STATUS current
		DESCRIPTION
			"This property provides information whether Line side
			loopback is supported or not.
			-----------------------------
			ommp82PlusInterfaceNumber:
			9 - LINE-1
			10 - LINE-2
			-----------------------------
			Values:
			1 - Lineside Loopback is supported in XFP
			0 - Lineside Loopback is not supported in XFP
			-----------------------------"
		::= { ommp82PlusCardGeneralDetailsEntry 64 }

	ommp82PlusXfpXfiLoopbackSupported OBJECT-TYPE		 
		SYNTAX  INTEGER
		MAX-ACCESS  read-only
		STATUS current
		DESCRIPTION
			"This property provides information whether Line side
			loopback at the Xfi level is supported or not.
			-----------------------------
			ommp82PlusInterfaceNumber:
			9 - LINE-1
			10 - LINE-2
			-----------------------------
			Values:
			1 - Xfi Loopback is supported in XFP
			0 - Xfi Loopback is not supported in XFP
			-----------------------------"
		::= { ommp82PlusCardGeneralDetailsEntry 65 }

	ommp82PlusXfpOptionalVpsSupported OBJECT-TYPE		 
		SYNTAX  INTEGER
		MAX-ACCESS  read-only
		STATUS current
		DESCRIPTION
			"This property provides information whether XFP
			supports optional variable power supply or not.
			-----------------------------
			ommp82PlusInterfaceNumber:
			9 - LINE-1
			10 - LINE-2
			-----------------------------
			Values:
			1 - XFP supports optional vps
			0 - XFP does not support optional vps
			-----------------------------"
		::= { ommp82PlusCardGeneralDetailsEntry 66 }

	ommp82PlusXfpLaserDisableThroughI2cSupported OBJECT-TYPE		 
		SYNTAX  INTEGER
		MAX-ACCESS  read-only
		STATUS current
		DESCRIPTION
			"This property provides information whether XFP
			LASER can be operated through single 2-wire interface
			bus or not.
			-----------------------------
			ommp82PlusInterfaceNumber:
			9 - LINE-1
			10 - LINE-2
			-----------------------------
			Values:
			1 - XFP supports LASER disable through I2C
			0 - XFP does not support LASER disable through I2C
			-----------------------------"
		::= { ommp82PlusCardGeneralDetailsEntry 67 }

	ommp82PlusXfpPowerDownThroughI2cSupported OBJECT-TYPE		 
		SYNTAX  INTEGER
		MAX-ACCESS  read-only
		STATUS current
		DESCRIPTION
			"This property provides information whether XFP-
			Power-down can be operated through single 2-wire 
			interface bus or not.
			-----------------------------
			ommp82PlusInterfaceNumber:
			9 - LINE-1
			10 - LINE-2
			-----------------------------
			Values:
			1 - XFP Supports XFP-power-down through I2C  
			0 - XFP does not supports XFP-power-down through I2C  
			-----------------------------"
		::= { ommp82PlusCardGeneralDetailsEntry 68 }

	ommp82PlusXfpVpsLvRegulatorModeSupported OBJECT-TYPE		 
		SYNTAX  INTEGER
		MAX-ACCESS  read-only
		STATUS current
		DESCRIPTION
			"This property provides information whether XFP
			supports VPS_LV_regulator_mode or not.
			-----------------------------
			ommp82PlusInterfaceNumber:
			9 - LINE-1
			10 - LINE-2
			-----------------------------
			Values:
			1 - XFP supports VPS_LV_regulator_mode
			0 - XFP does not support VPS_LV_regulator_mode
			-----------------------------"
		::= { ommp82PlusCardGeneralDetailsEntry 69 }

	ommp82PlusXfpVpsBypassedRegulatorModeSupported OBJECT-TYPE		 
		SYNTAX  INTEGER
		MAX-ACCESS  read-only
		STATUS current
		DESCRIPTION
			"This property provides information whether XFP
			supports VPS bypassed regulator mode or not.
			-----------------------------
			ommp82PlusInterfaceNumber:
			9 - LINE-1
			10 - LINE-2
			-----------------------------
			Values:
			1 - XFP supports VPS bypassed regulator mode
			0 - XFP does not support active VPS bypassed regulator mode
			-----------------------------"
		::= { ommp82PlusCardGeneralDetailsEntry 70 }

	ommp82PlusXfpActiveFecControlSupported OBJECT-TYPE		 
		SYNTAX  INTEGER
		MAX-ACCESS  read-only
		STATUS current
		DESCRIPTION
			"This property provides information whether XFP
			supports active FEC control functions or not.
			-----------------------------
			ommp82PlusInterfaceNumber:
			9 - LINE-1
			10 - LINE-2
			-----------------------------
			Values:
			1 - XFP supports active FEC control functions
			0 - XFP does not support active FEC control functions
			-----------------------------"
		::= { ommp82PlusCardGeneralDetailsEntry 71 }

	ommp82PlusXfpOptionalCmuModeSupported OBJECT-TYPE		 
		SYNTAX  INTEGER
		MAX-ACCESS  read-only
		STATUS current
		DESCRIPTION
			"This property provides information whether XFP
			supports CMU mode or not.
			-----------------------------
			ommp82PlusInterfaceNumber:
			9 - LINE-1
			10 - LINE-2
			-----------------------------
			Values:
			1 - XFP supports CMU mode
			0 - XFP does not support CMU mode
			-----------------------------"
		::= { ommp82PlusCardGeneralDetailsEntry 72 }

	ommp82PlusXfpFecBerSupported OBJECT-TYPE		 
		SYNTAX  INTEGER
		MAX-ACCESS  read-only
		STATUS current
		DESCRIPTION
			"This property provides information whether XFP
			supports FEC BER or not.
			-----------------------------
			ommp82PlusInterfaceNumber:
			9 - LINE-1
			10 - LINE-2
			-----------------------------
			Values:
			1 - XFP supports FEC BER
			0 - XFP does not support FEC BER
			-----------------------------"
		::= { ommp82PlusCardGeneralDetailsEntry 73 }

	ommp82PlusXfpReceivePowerMeasurementIsInOmaOrAverage OBJECT-TYPE		 
		SYNTAX  INTEGER
		MAX-ACCESS  read-only
		STATUS current
		DESCRIPTION
			"This property tells whether the received power  
			measurement from XFP is given as Oma or Average.
			-----------------------------
			ommp82PlusInterfaceNumber:
			9 - LINE-1
			10 - LINE-2
			-----------------------------
			Values:
			1 - OMA
			0 - Average Power
			-----------------------------"
		::= { ommp82PlusCardGeneralDetailsEntry 74 }

	ommp82PlusXfpActiveWavelengthControlSupported OBJECT-TYPE		 
		SYNTAX  INTEGER
		MAX-ACCESS  read-only
		STATUS current
		DESCRIPTION
			"This property provides whether the XFP wavelength 
			controlling state is active or not
			-----------------------------
			ommp82PlusInterfaceNumber:
			9 - LINE-1
			10 - LINE-2
			-----------------------------
			Values:
			1 - Active
			0 - Inactive
			-----------------------------"
		::= { ommp82PlusCardGeneralDetailsEntry 75 }

	ommp82PlusXfpTransmitterIsCooledOrUncooled OBJECT-TYPE		 
		SYNTAX  INTEGER
		MAX-ACCESS  read-only
		STATUS current
		DESCRIPTION
			"This property provide information on which type of
			diode used in transmitter of the XFP
			-----------------------------
			ommp82PlusInterfaceNumber:
			9 - LINE-1
			10 - LINE-2
			-----------------------------
			Values:
			1 - Cooling circuit supported for XFP transmitter. 
			0 - Cooling circuit not supported for XFP transmitter.
			-----------------------------"
		::= { ommp82PlusCardGeneralDetailsEntry 76 }

	ommp82PlusXfpReceiverTypeIsPinOrApd OBJECT-TYPE		 
		SYNTAX  INTEGER
		MAX-ACCESS  read-only
		STATUS current
		DESCRIPTION
			"This property provide information on which type of
			diode used in transmitter of the XFP.
			-----------------------------
			ommp82PlusInterfaceNumber:
			9 - LINE-1
			10 - LINE-2
			-----------------------------
			Values:
			1 - PIN detector
			0 - APD detector			 
			-----------------------------"
		::= { ommp82PlusCardGeneralDetailsEntry 77 }

	ommp82PlusSfpEepromPage OBJECT-TYPE		 
		SYNTAX  INTEGER
		MAX-ACCESS  read-write
		STATUS current
		DESCRIPTION
			"This property sets/gets the SFP EEPROM page, 
			the value represents the SFP EEPROM page number.
			-----------------------------
			ommp82PlusInterfaceNumber:
			1 to 8 - CLIENT-1 to CLIENT-8
			-----------------------------
			Values:			
			eg: 1(EEPROM Page number)
			-----------------------------"
		::= { ommp82PlusCardGeneralDetailsEntry 101 }

	ommp82PlusCheckCodeOfSfpEepromPage OBJECT-TYPE		 
		SYNTAX  INTEGER
		MAX-ACCESS  read-only
		STATUS current
		DESCRIPTION
			"This property provides the SFP
			check code(checksum) value for bytes 128 to 190
			present in SFP EEPROM Page number 1. 
			-----------------------------
			ommp82PlusInterfaceNumber:
			1 to 8 - CLIENT-1 to CLIENT-8
			-----------------------------
			Values:			
			eg: 1(EEPROM Page number)
			-----------------------------"
		::= { ommp82PlusCardGeneralDetailsEntry 102 }

	ommp82PlusExtendedCheckCodeOfSfpEepromPage OBJECT-TYPE		 
		SYNTAX  INTEGER
		MAX-ACCESS  read-only
		STATUS current
		DESCRIPTION
			"This property provides the SFP
			extended check code(checksum) value for bytes 192 to 222
			present in SFP EEPROM Page number 1. 
			-----------------------------
			ommp82PlusInterfaceNumber:
			1 to 8 - CLIENT-1 to CLIENT-8
			-----------------------------
			Values:			
			eg: 1(EEPROM Page number)
			-----------------------------"
		::= { ommp82PlusCardGeneralDetailsEntry 103 }

	ommp82PlusSfpVendorName OBJECT-TYPE		 
		SYNTAX  DisplayString
		MAX-ACCESS  read-only
		STATUS current
		DESCRIPTION
			"This property provides Vendor Name for given SFP. 
			The vendor name shall be the full name of the 
			corporation, a commonly accepted abbreviation of 
			the name of the corporation, the SCSI company code
			for the corporation, or the stock exchange code for
			the corporation.
			-----------------------------
			ommp82PlusInterfaceNumber:
			1 to 8 - CLIENT-1 to CLIENT-8
			-----------------------------
			Values:			
			eg: WTD
			-----------------------------"

		::= { ommp82PlusCardGeneralDetailsEntry 104 }

	ommp82PlusSfpVendorIeeeId OBJECT-TYPE		 
		SYNTAX  DisplayString
		MAX-ACCESS  read-only
		STATUS current
		DESCRIPTION
			"This property defines the IEEE company Identifier for
			the vendor of SFP. A value of all zero in the 3-byte
			field indicates that the Vendor OUI is unspecified.
			-----------------------------
			ommp82PlusInterfaceNumber:
			1 to 8 - CLIENT-1 to CLIENT-8
			-----------------------------
			Values:			
			eg: 010
			-----------------------------"
		::= { ommp82PlusCardGeneralDetailsEntry 105 }

	ommp82PlusSfpPartNumber OBJECT-TYPE		 
		SYNTAX  DisplayString
		MAX-ACCESS  read-only
		STATUS current
		DESCRIPTION
			"This property defines the vendor part number or
			product name of the SFP. A value of all zero
			indicates that the vendor Part Number is unspecified.
			-----------------------------
			ommp82PlusInterfaceNumber:
			1 to 8 - CLIENT-1 to CLIENT-8
			-----------------------------
			Values:			
			eg: WXTR15101000427
			-----------------------------"
		::= { ommp82PlusCardGeneralDetailsEntry 106 }

	ommp82PlusSfpSerialNumber OBJECT-TYPE		 
		SYNTAX  DisplayString
		MAX-ACCESS  read-only
		STATUS current
		DESCRIPTION
			"This property provides vendor serial number defining
			the vendor’s serial number for the SFP. A value of all
			zero in the 16-byte field indicates that the vendor
			serial number is unspecified.
			-----------------------------
			ommp82PlusInterfaceNumber:
			1 to 8 - CLIENT-1 to CLIENT-8
			-----------------------------
			Values:			
			eg: WXTRRPGEAS1
			-----------------------------"
		::= { ommp82PlusCardGeneralDetailsEntry 107 }

	ommp82PlusSfpRevisionNumber OBJECT-TYPE		 
		SYNTAX  DisplayString
		MAX-ACCESS  read-only
		STATUS current
		DESCRIPTION
			"The vendor revision number defining the vendor’s
			product revision number. A value of all zero indicates
			that the vendor revision number is unspecified
			-----------------------------
			ommp82PlusInterfaceNumber:
			1 to 8 - CLIENT-1 to CLIENT-8
			-----------------------------
			Values:			
			eg: RT
			-----------------------------"
		::= { ommp82PlusCardGeneralDetailsEntry 108 }

	ommp82PlusSfpManufacturingDate OBJECT-TYPE		 
		SYNTAX  DisplayString
		MAX-ACCESS  read-only
		STATUS current
		DESCRIPTION
			"This property defines the manufacturing date for 
			SFP. A value of 8-byte field in ASCII which represents
			year, month and date of each two bytes. 
			Extra two bytes may be blank
			-----------------------------
			ommp82PlusInterfaceNumber:
			1 to 8 - CLIENT-1 to CLIENT-8
			-----------------------------
			Values:			
			eg: 160224
			-----------------------------"
		::= { ommp82PlusCardGeneralDetailsEntry 109 }

	ommp82PlusFixedSfpLaserWavelength OBJECT-TYPE		 
		SYNTAX  DisplayString
		MAX-ACCESS  read-only
		STATUS current
		DESCRIPTION
			"This property provides transmitter LASER wavelength(nm)
			of the SFP
			-----------------------------
			ommp82PlusInterfaceNumber:
			1 to 8 - CLIENT-1 to CLIENT-8
			-----------------------------
			Values:			
			eg: 1310.0
			-----------------------------"
		::= { ommp82PlusCardGeneralDetailsEntry 110 }

	ommp82PlusSfpConnectorType OBJECT-TYPE		 
		SYNTAX  DisplayString
		MAX-ACCESS  read-only
		STATUS current
		DESCRIPTION
			"This property provides information of the SFP
			connector, value indicates the external connector
			provided on the SFP.
			-----------------------------
			ommp82PlusInterfaceNumber:
			1 to 8 - CLIENT-1 to CLIENT-8
			-----------------------------
			Values:
			00h 	Unknown or unspecified
			01h 	SC (Subscriber Connector)
			02h 	Fibre Channel Style 1 copper connector
			03h 	Fibre Channel Style 2 copper connector
			04h 	BNC/TNC (Bayonet/Threaded Neill-Concelman)
			05h 	Fibre Channel coax headers
			06h 	Fiber Jack
			07h 	LC (Lucent Connector)
			08h 	MT-RJ (Mechanical Transfer - Registered Jack)
			09h 	MU (Multiple Optical)
			0Ah 	SG
			0Bh 	Optical Pigtail
			0Ch 	MPO 1x12 (Multifiber Parallel Optic)
			0Dh 	MPO 2x16
			0E-1Fh 	Reserved
			20h 	HSSDC II (High Speed Serial Data Connector)
			21h 	Copper pigtail
			22h 	RJ45 (Registered Jack)
			23h 	No separable connector
			24h 	MXC 2x16
			25h-7Fh Reserved
			80h-FFh Vendor specific
			-----------------------------"
		::= { ommp82PlusCardGeneralDetailsEntry 111 }

	ommp82PlusSfpLinkLength OBJECT-TYPE		 
		SYNTAX  DisplayString
		MAX-ACCESS  read-only
		STATUS current
		DESCRIPTION
			"This property provides link length suported by the SFP
			-----------------------------
			ommp82PlusInterfaceNumber:
			1 to 8 - CLIENT-1 to CLIENT-8
			-----------------------------
			Values:
			eg: 80.00
			-----------------------------"
		::= { ommp82PlusCardGeneralDetailsEntry 112 }

	ommp82PlusSfpSignalEncodingTypeSupported OBJECT-TYPE		 
		SYNTAX  INTEGER
		MAX-ACCESS  read-only
		STATUS current
		DESCRIPTION
			"This property indicates the serial encoding mechanisms
			that are supported by the SFP.
			-----------------------------
			ommp82PlusInterfaceNumber:
			1 to 8 - CLIENT-1 to CLIENT-8
			-----------------------------
			Values:
			1 - 64B/66B
			2 - 8B10B
			3 - SONET Scrambled
			4 - NRZ
			5 - RZ
			-----------------------------"
		::= { ommp82PlusCardGeneralDetailsEntry 113 }

	ommp82PlusSfpTransceiverCodesSupported OBJECT-TYPE		 
		SYNTAX  DisplayString
		MAX-ACCESS  read-only
		STATUS current
		DESCRIPTION
			"The identifier value specifies which transceiver
			codes are supported by the SFP
			-----------------------------
			ommp82PlusInterfaceNumber:
			1 to 8 - CLIENT-1 to CLIENT-8
			-----------------------------
			Values:

			Return value 8-Byte represetation:
				  			 Byte-1	 Byte-2	 Byte-3	 Byte-4	 Byte-5  Byte-6  Byte-7	Byte-8
			100-M5-SN-I and 100-M6-SN-I	 0x00	 0x00   0x00	 0x00	 0x20    0x40    0x0C   0x01
			200-SM-LC-L and 100-SM-LC-L	 0x00	 0x00	 0x00	 0x00	 0x12	 0x00    0x01	0x05
			400-M5-SN-I and 400-M6-SN-I	 0x00	 0x00	 0x00	 0x00	 0x20    0x40    0x0C   0x15
			800-M5-SN-I and 800-M6-SN-I	 0x00	 0x00	 0x00	 0x00	 0x20    0x40    0x0C   0x54
			400-SM-LC-M	 		 0x00	 0x00	 0x00	 0x00	 0x0A    0x00    0x01   0x15
			400-SM-LC-L	 		 0x00	 0x00	 0x00	 0x00	 0x12    0x00    0x01   0x15
			200-SM-LL-V and 100-SM-LL-V	 0x00	 0x00	 0x00	 0x00	 0x80    0x10    0x01   0x05
			1000BASE-T	 		 0x00	 0x00	 0x00	 0x08    0x00    0x00    0x00   0x00
			1000BASE-SX	 		 0x00	 0x00	 0x00	 0x01    0x00    0x00    0x00   0x00
			1000BASE-LX	 		 0x00	 0x00	 0x00	 0x02    0x00    0x00    0x00   0x00
			1000BASE-LX10	 		 0x00	 0x00	 0x00	 0x02    0x00    0x00    0x00   0x00
			10GBASE-SR	 		 0x10h	 0x00	 0x00    0x00	 0x00	 0x00    0x00	0x00
			10GBASE-LR	 		 0x20h	 0x00	 0x00    0x00	 0x00	 0x00    0x00	0x00
			OC3/STM1 SR-1	 		 0x00	 0x00	 0x01h   0x00	 0x00	 0x00    0x00	0x00
			OC12/STM4 LR-1	 		 0x00	 0x10h	 0x40h   0x00	 0x00	 0x00    0x00	0x00
			OC48/STM16 LR-2	 		 0x00	 0x0Ch	 0x00    0x00	 0x00	 0x00    0x00	0x00
			10GE Passive copper cable	 0x00	 0x00	 0x00    0x00	 0x00	 0x04h   0x00	0x00
			10GE Active cable		 0x00	 0x00	 0x00    0x00	 0x00	 0x08h   0x00	0x00
			8/4/2G Passive copper cable	 0x00	 0x00	 0x00    0x00	 0x00	 0x04h   0x00	0x54h
			8/4/2G Active cable		 0x00	 0x00	 0x00    0x00	 0x00	 0x08h   0x00	0x54h
			-----------------------------"
		::= { ommp82PlusCardGeneralDetailsEntry 114 }

	ommp82PlusSfpMaximumBitrateSupported OBJECT-TYPE		 
		SYNTAX  DisplayString
		MAX-ACCESS  read-only
		STATUS current
		DESCRIPTION
			"This property provides maximum bit rate value(Gbps)
			supported by the SFP
			-----------------------------
			ommp82PlusInterfaceNumber:
			1 to 8 - CLIENT-1 to CLIENT-8
			-----------------------------
			Values: 2.7
			-----------------------------"
		::= { ommp82PlusCardGeneralDetailsEntry 115 }

	ommp82PlusSfpNominalBitrateSupported OBJECT-TYPE		 
		SYNTAX  DisplayString
		MAX-ACCESS  read-only
		STATUS current
		DESCRIPTION
			"This property provides maximum bit rate value(Gbps)
			supported by the SFP
			-----------------------------
			ommp82PlusInterfaceNumber:
			1 to 8 - CLIENT-1 to CLIENT-8
			-----------------------------
			Values: 2.5
			-----------------------------"
		::= { ommp82PlusCardGeneralDetailsEntry 116 }

	ommp82PlusSfpMinimumBitrateSupported OBJECT-TYPE		 
		SYNTAX  DisplayString
		MAX-ACCESS  read-only
		STATUS current
		DESCRIPTION
			"This property provides minimum bit rate value(Gbps)
			supported by the SFP
			-----------------------------
			ommp82PlusInterfaceNumber:
			1 to 8 - CLIENT-1 to CLIENT-8
			-----------------------------
			Values: 2.3
			-----------------------------"
		::= { ommp82PlusCardGeneralDetailsEntry 117 }

	ommp82PlusCardGeneralDetailsTableRowStatus OBJECT-TYPE
              SYNTAX      RowStatus
              MAX-ACCESS  read-write
              STATUS      current
              DESCRIPTION
			"*****************************
			This is MIB realted property,
			NOT to be considered as a card property
			*****************************"
              ::= { ommp82PlusCardGeneralDetailsEntry 118 }	

--*****************************************************************************
--				   CONFIGURATION
--*****************************************************************************

	ommp82PlusConfigurationTable OBJECT-TYPE
		SYNTAX  SEQUENCE OF Ommp82PlusConfigurationEntry 
		MAX-ACCESS  not-accessible
		STATUS  current
		DESCRIPTION
		      "Contains configuration queries of the OMMP82-PLUS card"
		::= { ommp82PlusConfiguration 1 }

	ommp82PlusConfigurationEntry  OBJECT-TYPE
              SYNTAX  Ommp82PlusConfigurationEntry 
              MAX-ACCESS  not-accessible
              STATUS  current
              DESCRIPTION 
              	""
		INDEX   { node, rack, subRack, slot, ommp82PlusInterfaceNumber }
		::= { ommp82PlusConfigurationTable 1 }
	
	Ommp82PlusConfigurationEntry  ::= 
		SEQUENCE {
				ommp82PlusCardSoftwareUpgrade					DisplayString,
				ommp82PlusCardSignalMonitorState				INTEGER,
				ommp82PlusCardOpticalMonitorState				INTEGER,
				ommp82PlusCardSoftReset						INTEGER,
				ommp82PlusCardFactoryReset					INTEGER,
				ommp82PlusCardAccessStatus					INTEGER,
				ommp82PlusSyncSystemTimeWithNtpServer			DisplayString,
				ommp82PlusSyncRtcWithNtpServer					DisplayString,
				ommp82PlusSyncRtcWithSystemTime					DisplayString,
				ommp82PlusUpdateGivenTimeIntoSystem				DisplayString,
				ommp82PlusUpdateGivenTimeIntoRtc				DisplayString,
				ommp82PlusSystemTimeAndRtcTime					DisplayString,
				ommp82PlusApsLinePathSwitchingMode				INTEGER,
				ommp82PlusApsUserChoiceOfLinePath				INTEGER,
				ommp82PlusApsCurrentOperationalLinePath				INTEGER,
--				ommp82PlusTrafficConfiguration					DisplayString,
				ommp82PlusTrafficConfiguration					INTEGER,
				ommp82PlusLoopbackState						INTEGER,
				ommp82PlusPortSignalMonitorState				INTEGER,
				ommp82PlusPortOpticalMonitorState				INTEGER,
				ommp82PlusClearSignalPerformance				INTEGER,
				ommp82PlusAlsState						INTEGER,
				ommp82PlusAlsPulseRepetitionTime				INTEGER,
				ommp82PlusOtuFecConfiguration					INTEGER,
				ommp82PlusOtuSignalFailThreshold				INTEGER,
				ommp82PlusOtuSignalDegradeThreshold				INTEGER,
				ommp82PlusOtuAlarmIndicationSignalAlarmInsertion		INTEGER,
				ommp82PlusOtuSapiTransmitTraceMessage				DisplayString,
				ommp82PlusOtuDapiTransmitTraceMessage				DisplayString,
				ommp82PlusOtuOperatorSpecificTransmitTraceMessage		DisplayString,
				ommp82PlusOtuSapiExpectedTraceMessage				DisplayString,
				ommp82PlusOtuDapiExpectedTraceMessage				DisplayString,
				ommp82PlusOtuOperatorSpecificExpectedTraceMessage		DisplayString,
				ommp82PlusOtuSapiReceivedTraceMessage				DisplayString,
				ommp82PlusOtuDapiReceivedTraceMessage				DisplayString,
				ommp82PlusOtuOperatorSpecificReceivedTraceMessage		DisplayString,
				ommp82PlusOduSignalFailThreshold				INTEGER,
				ommp82PlusOduSignalDegradeThreshold				INTEGER,
				ommp82PlusOduAlarmIndicationSignalAlarmInsertion		INTEGER,
				ommp82PlusOduLockedDefectAlarmInsertion				INTEGER,
				ommp82PlusOduOpenConnectionIndicationAlarmInsertion		INTEGER,
				ommp82PlusOduSapiTransmitTraceMessage				DisplayString,
				ommp82PlusOduDapiTransmitTraceMessage				DisplayString,
				ommp82PlusOduOperatorSpecificTransmitTraceMessage		DisplayString,
				ommp82PlusOduSapiExpectedTraceMessage				DisplayString,
				ommp82PlusOduDapiExpectedTraceMessage				DisplayString,
				ommp82PlusOduOperatorSpecificExpectedTraceMessage		DisplayString,
				ommp82PlusOduSapiReceivedTraceMessage				DisplayString,
				ommp82PlusOduDapiReceivedTraceMessage				DisplayString,
				ommp82PlusOduOperatorSpecificReceivedTraceMessage		DisplayString,
				ommp82PlusOpuTransmitPayloadType				INTEGER,
				ommp82PlusOpuReceivedPayloadType				INTEGER,
				ommp82PlusSdhMsB2ExcessiveErrorThreshold			INTEGER,
				ommp82PlusSdhMsB2SignalDegradeThreshold				INTEGER,
				ommp82PlusEthernetAutoNegotiation				INTEGER,
				ommp82PlusCalibrateHyphyXfiSerdes				INTEGER,
				ommp82PlusTunableXfpLaserWavelength				INTEGER,
				ommp82PlusTunableXfpLaserChannelNumber				INTEGER,
				ommp82PlusXfpLaserState						INTEGER,
				ommp82PlusXfpReset						INTEGER,
				ommp82PlusXfpPowerDownMode					INTEGER,
				ommp82PlusXfpLineLoopback					INTEGER,
				ommp82PlusXfpXfiLoopback					INTEGER,
				ommp82PlusXfpAmplitudeThresholdOfReceiverForFecControl		INTEGER,
				ommp82PlusXfpPhaseInEyeDiagramForFecControl			INTEGER,
				ommp82PlusXfpSystemReportingBer					INTEGER,
				ommp82PlusXfpHighTemperatureAlarmThreshold			DisplayString,
				ommp82PlusXfpLowTemperatureAlarmThreshold			DisplayString,
				ommp82PlusXfpHighTemperatureWarningThreshold			DisplayString,
				ommp82PlusXfpLowTemperatureWarningThreshold			DisplayString,
				ommp82PlusXfpHighBiasCurrentAlarmThreshold			DisplayString,
				ommp82PlusXfpLowBiasCurrentAlarmThreshold			DisplayString,
				ommp82PlusXfpHighBiasCurrentWarningThreshold			DisplayString,
				ommp82PlusXfpLowBiasCurrentWarningThreshold			DisplayString,
				ommp82PlusXfpInputHighPowerAlarmThreshold			DisplayString,
				ommp82PlusXfpInputLowPowerAlarmThreshold			DisplayString,
				ommp82PlusXfpInputHighPowerWarningThreshold			DisplayString,
				ommp82PlusXfpInputLowPowerWarningThreshold			DisplayString,
				ommp82PlusXfpOutputHighPowerAlarmThreshold			DisplayString,
				ommp82PlusXfpOutputLowPowerAlarmThreshold			DisplayString,
				ommp82PlusXfpOutputHighPowerWarningThreshold			DisplayString,
				ommp82PlusXfpOutputLowPowerWarningThreshold			DisplayString,
				ommp82PlusXfpHighSupplyVoltageAlarmThreshold			DisplayString,
				ommp82PlusXfpLowSupplyVoltageAlarmThreshold			DisplayString,
				ommp82PlusXfpHighSupplyVoltageWarningThreshold			DisplayString,
				ommp82PlusXfpLowSupplyVoltageWarningThreshold			DisplayString,
				ommp82PlusSfpLaserState						INTEGER,
				ommp82PlusSfpHighTemperatureAlarmThreshold			DisplayString,
				ommp82PlusSfpLowTemperatureAlarmThreshold			DisplayString,
				ommp82PlusSfpHighTemperatureWarningThreshold			DisplayString,
				ommp82PlusSfpLowTemperatureWarningThreshold			DisplayString,
				ommp82PlusSfpHighBiasCurrentAlarmThreshold			DisplayString,
				ommp82PlusSfpLowBiasCurrentAlarmThreshold			DisplayString,
				ommp82PlusSfpHighBiasCurrentWarningThreshold			DisplayString,
				ommp82PlusSfpLowBiasCurrentWarningThreshold			DisplayString,
				ommp82PlusSfpInputHighPowerAlarmThreshold			DisplayString,
				ommp82PlusSfpInputLowPowerAlarmThreshold			DisplayString,
				ommp82PlusSfpInputHighPowerWarningThreshold			DisplayString,
				ommp82PlusSfpInputLowPowerWarningThreshold			DisplayString,
				ommp82PlusSfpOutputHighPowerAlarmThreshold			DisplayString,
				ommp82PlusSfpOutputLowPowerAlarmThreshold			DisplayString,
				ommp82PlusSfpOutputHighPowerWarningThreshold			DisplayString,
				ommp82PlusSfpOutputLowPowerWarningThreshold			DisplayString,
				ommp82PlusSfpHighSupplyVoltageAlarmThreshold			DisplayString,
				ommp82PlusSfpLowSupplyVoltageAlarmThreshold			DisplayString,
				ommp82PlusSfpHighSupplyVoltageWarningThreshold			DisplayString,
				ommp82PlusSfpLowSupplyVoltageWarningThreshold			DisplayString,
				ommp82PlusXfpInputPowerFailureAlarmInhibit			INTEGER,
				ommp82PlusXfpOutputPowerFailureAlarmInhibit			INTEGER,
				ommp82PlusXfpHighTemperatureAlarmInhibit			INTEGER,
				ommp82PlusXfpLowTemperatureAlarmInhibit				INTEGER,
				ommp82PlusXfpHighTemperatureWarningInhibit			INTEGER,
				ommp82PlusXfpLowTemperatureWarningInhibit			INTEGER,
				ommp82PlusXfpHighBiasCurrentAlarmInhibit			INTEGER,
				ommp82PlusXfpLowBiasCurrentAlarmInhibit				INTEGER,
				ommp82PlusXfpHighBiasCurrentWarningInhibit			INTEGER,
				ommp82PlusXfpLowBiasCurrentWarningInhibit			INTEGER,
				ommp82PlusXfpInputHighPowerAlarmInhibit				INTEGER,
				ommp82PlusXfpInputLowPowerAlarmInhibit				INTEGER,
				ommp82PlusXfpInputHighPowerWarningInhibit			INTEGER,
				ommp82PlusXfpInputLowPowerWarningInhibit			INTEGER,
				ommp82PlusXfpOutputHighPowerAlarmInhibit			INTEGER,
				ommp82PlusXfpOutputLowPowerAlarmInhibit				INTEGER,
				ommp82PlusXfpOutputHighPowerWarningInhibit			INTEGER,
				ommp82PlusXfpOutputLowPowerWarningInhibit			INTEGER,
				ommp82PlusXfpHighSupplyVoltageAlarmInhibit			INTEGER,
				ommp82PlusXfpLowSupplyVoltageAlarmInhibit			INTEGER,
				ommp82PlusXfpHighSupplyVoltageWarningInhibit			INTEGER,
				ommp82PlusXfpLowSupplyVoltageWarningInhibit			INTEGER,
				ommp82PlusXfpPresenceAbsenceNotificationInhibit			INTEGER,
				ommp82PlusSfpInputPowerFailureAlarmInhibit			INTEGER,
				ommp82PlusSfpOutputPowerFailureAlarmInhibit			INTEGER,
				ommp82PlusSfpHighTemperatureAlarmInhibit			INTEGER,
				ommp82PlusSfpLowTemperatureAlarmInhibit				INTEGER,
				ommp82PlusSfpHighTemperatureWarningInhibit			INTEGER,
				ommp82PlusSfpLowTemperatureWarningInhibit			INTEGER,
				ommp82PlusSfpHighBiasCurrentAlarmInhibit			INTEGER,
				ommp82PlusSfpLowBiasCurrentAlarmInhibit				INTEGER,
				ommp82PlusSfpHighBiasCurrentWarningInhibit			INTEGER,
				ommp82PlusSfpLowBiasCurrentWarningInhibit			INTEGER,
				ommp82PlusSfpInputHighPowerAlarmInhibit				INTEGER,
				ommp82PlusSfpInputLowPowerAlarmInhibit				INTEGER,
				ommp82PlusSfpInputHighPowerWarningInhibit			INTEGER,
				ommp82PlusSfpInputLowPowerWarningInhibit			INTEGER,
				ommp82PlusSfpOutputHighPowerAlarmInhibit			INTEGER,
				ommp82PlusSfpOutputLowPowerAlarmInhibit				INTEGER,
				ommp82PlusSfpOutputHighPowerWarningInhibit			INTEGER,
				ommp82PlusSfpOutputLowPowerWarningInhibit			INTEGER,
				ommp82PlusSfpHighSupplyVoltageAlarmInhibit			INTEGER,
				ommp82PlusSfpLowSupplyVoltageAlarmInhibit			INTEGER,
				ommp82PlusSfpHighSupplyVoltageWarningInhibit			INTEGER,
				ommp82PlusSfpLowSupplyVoltageWarningInhibit			INTEGER,
				ommp82PlusSfpPresenceAbsenceNotificationInhibit			INTEGER,
				ommp82PlusSfpTransmitFaultPresenceAlarmInhibit			INTEGER,
				ommp82PlusOtuLossOfSignalAlarmInhibit				INTEGER,
				ommp82PlusOtuLossOfFrameAlarmInhibit				INTEGER,
				ommp82PlusOtuOutOfFrameAlarmInhibit				INTEGER,
				ommp82PlusOtuLossOfMultiFrameAlarmInhibit			INTEGER,
				ommp82PlusOtuOutOfMultiFrameAlarmInhibit			INTEGER,
				ommp82PlusOtuSignalFailAlarmInhibit				INTEGER,
				ommp82PlusOtuSignalDegradeAlarmInhibit				INTEGER,
				ommp82PlusOtuAlarmIndicationSignalAlarmInhibit			INTEGER,
				ommp82PlusOtuIncomingAlignmentErrorAlarmInhibit			INTEGER,
				ommp82PlusOtuTraceIdentifierMismatchAlarmInhibit		INTEGER,
				ommp82PlusOtuBackwardIncomingAlignmentErrorAlarmInhibit		INTEGER,
				ommp82PlusOtuBackwardDefectIndicationAlarmInhibit		INTEGER,
				ommp82PlusOduSignalFailAlarmInhibit				INTEGER,
				ommp82PlusOduSignalDegradeAlarmInhibit				INTEGER,
				ommp82PlusOduAlarmIndicationSignalAlarmInhibit			INTEGER,
				ommp82PlusOduTcm1IncomingAlignmentErrorAlarmInhibit		INTEGER,
				ommp82PlusOduTcm2IncomingAlignmentErrorAlarmInhibit		INTEGER,
				ommp82PlusOduTcm3IncomingAlignmentErrorAlarmInhibit		INTEGER,
				ommp82PlusOduTcm4IncomingAlignmentErrorAlarmInhibit		INTEGER,
				ommp82PlusOduTcm5IncomingAlignmentErrorAlarmInhibit		INTEGER,
				ommp82PlusOduTcm6IncomingAlignmentErrorAlarmInhibit		INTEGER,
				ommp82PlusOduTraceIdentifierMismatchAlarmInhibit		INTEGER,
				ommp82PlusOduLockedDefectAlarmInhibit				INTEGER,
				ommp82PlusOduOpenConnectionIndicationAlarmInhibit		INTEGER,
				ommp82PlusOduBackwardDefectIndicationAlarmInhibit		INTEGER,
				ommp82PlusOduTcm1BackwardIncomingAlignmentErrorAlarmInhibit	INTEGER,
				ommp82PlusOduTcm2BackwardIncomingAlignmentErrorAlarmInhibit	INTEGER,
				ommp82PlusOduTcm3BackwardIncomingAlignmentErrorAlarmInhibit	INTEGER,
				ommp82PlusOduTcm4BackwardIncomingAlignmentErrorAlarmInhibit	INTEGER,
				ommp82PlusOduTcm5BackwardIncomingAlignmentErrorAlarmInhibit	INTEGER,
				ommp82PlusOduTcm6BackwardIncomingAlignmentErrorAlarmInhibit	INTEGER,
				ommp82PlusOduLossOfFrameLossOfMultiframeAlarmInhibit		INTEGER,
				ommp82PlusOpuPayloadMismatchAlarmInhibit			INTEGER,
				ommp82PlusOchLossOfPayloadAlarmInhibit				INTEGER,
				ommp82PlusSdhLossOfSignalAlarmInhibit				INTEGER,
				ommp82PlusSdhOutOfFrameAlarmInhibit				INTEGER,
				ommp82PlusSdhLossOfFrameAlarmInhibit				INTEGER,
				ommp82PlusSdhRsAlarmIndicationSignalAlarmInhibit		INTEGER,
				ommp82PlusSdhRsTraceIdentifierMismatchAlarmInhibit		INTEGER,
				ommp82PlusSdhAuAlarmIndicationSignalAlarmInhibit		INTEGER,
				ommp82PlusSdhAuLossOfPointerAlarmInhibit			INTEGER,
				ommp82PlusSdhMsAlarmIndicationSignalAlarmInhibit		INTEGER,
				ommp82PlusSdhMsRemoteErrorIndicationAlarmInhibit		INTEGER,
				ommp82PlusSdhMsRemoteDefectIndicationAlarmInhibit		INTEGER,
				ommp82PlusSdhMsRemoteFailureIndicationAlarmInhibit		INTEGER,
				ommp82PlusSdhMsB2ExcessiveErrorAlarmInhibit			INTEGER,
				ommp82PlusSdhMsB2SignalDegradeAlarmInhibit			INTEGER,
				ommp82PlusSdhLossOfSequenceSynchronisationAlarmInhibit		INTEGER,
				ommp82PlusSdhLowerOrderPathPayloadLabelMismatchAlarmInhibit	INTEGER,
				ommp82PlusSdhLowerOrderPathUnequippedAlarmInhibit		INTEGER,
				ommp82PlusEthernetLossOfSignalAlarmInhibit			INTEGER,
				ommp82PlusEthernetLossOfSignalSyncAlarmInhibit			INTEGER,
				ommp82PlusEthernetLinkFailureAlarmInhibit			INTEGER,
				ommp82PlusEthernetAutoNegotiationAlarmInhibit			INTEGER,
				ommp82PlusEthernetFrameCheckSequenceAlarmInhibit		INTEGER,
				ommp82PlusEthernetCarrierStatusAlarmInhibit			INTEGER,
				ommp82PlusEthernetHighBerAlarmInhibit				INTEGER,
				ommp82PlusEthernetLocalFaultAlarmInhibit			INTEGER,
				ommp82PlusEthernetRemoteFaultAlarmInhibit			INTEGER,
				ommp82PlusFcTransmitDisparityInversionDefectAlarmInhibit	INTEGER,
				ommp82PlusFcTransmitDigitalLossOfLinkDefectAlarmInhibit		INTEGER,
				ommp82PlusFcTrasnmitLossOfSynchronizationDefectAlarmInhibit	INTEGER,
				ommp82PlusFcReceiveDigitalLossOfLinkDefectAlarmInhibit		INTEGER,
				ommp82PlusFcReceiveLossOfSynchronizationDefectAlarmInhibit	INTEGER,
				ommp82PlusFcReceiveTransitionDetectDefectAlarmInhibit		INTEGER,
				ommp82PlusFcReceiveAnalogLossOfSignalDefectAlarmInhibit		INTEGER,
				ommp82PlusFcReceiveLineCodeViolationDefectAlarmInhibit		INTEGER,
				ommp82PlusGfpCsfSignalFailAlarmInhibit				INTEGER,
				ommp82PlusGfpCsfLinkFailAlarmInhibit				INTEGER,
				ommp82PlusGfpCoreHeaderErrorAlarmInhibit			INTEGER,
				ommp82PlusGfpExtentionHeaderErrorAlarmInhibit			INTEGER,
				ommp82PlusXfpInputPowerFailureAlarmSeverity			DisplayString,
				ommp82PlusXfpOutputPowerFailureAlarmSeverity			DisplayString,
				ommp82PlusXfpHighTemperatureAlarmSeverity			DisplayString,
				ommp82PlusXfpLowTemperatureAlarmSeverity			DisplayString,
				ommp82PlusXfpHighTemperatureWarningSeverity			DisplayString,
				ommp82PlusXfpLowTemperatureWarningSeverity			DisplayString,
				ommp82PlusXfpHighBiasCurrentAlarmSeverity			DisplayString,
				ommp82PlusXfpLowBiasCurrentAlarmSeverity			DisplayString,
				ommp82PlusXfpHighBiasCurrentWarningSeverity			DisplayString,
				ommp82PlusXfpLowBiasCurrentWarningSeverity			DisplayString,
				ommp82PlusXfpInputHighPowerAlarmSeverity			DisplayString,
				ommp82PlusXfpInputLowPowerAlarmSeverity				DisplayString,
				ommp82PlusXfpInputHighPowerWarningSeverity			DisplayString,
				ommp82PlusXfpInputLowPowerWarningSeverity			DisplayString,
				ommp82PlusXfpOutputHighPowerAlarmSeverity			DisplayString,
				ommp82PlusXfpOutputLowPowerAlarmSeverity			DisplayString,
				ommp82PlusXfpOutputHighPowerWarningSeverity			DisplayString,
				ommp82PlusXfpOutputLowPowerWarningSeverity			DisplayString,
				ommp82PlusXfpHighSupplyVoltageAlarmSeverity			DisplayString,
				ommp82PlusXfpLowSupplyVoltageAlarmSeverity			DisplayString,
				ommp82PlusXfpHighSupplyVoltageWarningSeverity			DisplayString,
				ommp82PlusXfpLowSupplyVoltageWarningSeverity			DisplayString,
				ommp82PlusXfpPresenceAbsenceNotificationSeverity		DisplayString,
				ommp82PlusSfpInputPowerFailureAlarmSeverity			DisplayString,
				ommp82PlusSfpOutputPowerFailureAlarmSeverity			DisplayString,
				ommp82PlusSfpHighTemperatureAlarmSeverity			DisplayString,
				ommp82PlusSfpLowTemperatureAlarmSeverity			DisplayString,
				ommp82PlusSfpHighTemperatureWarningSeverity			DisplayString,
				ommp82PlusSfpLowTemperatureWarningSeverity			DisplayString,
				ommp82PlusSfpHighBiasCurrentAlarmSeverity			DisplayString,
				ommp82PlusSfpLowBiasCurrentAlarmSeverity			DisplayString,
				ommp82PlusSfpHighBiasCurrentWarningSeverity			DisplayString,
				ommp82PlusSfpLowBiasCurrentWarningSeverity			DisplayString,
				ommp82PlusSfpInputHighPowerAlarmSeverity			DisplayString,
				ommp82PlusSfpInputLowPowerAlarmSeverity				DisplayString,
				ommp82PlusSfpInputHighPowerWarningSeverity			DisplayString,
				ommp82PlusSfpInputLowPowerWarningSeverity			DisplayString,
				ommp82PlusSfpOutputHighPowerAlarmSeverity			DisplayString,
				ommp82PlusSfpOutputLowPowerAlarmSeverity			DisplayString,
				ommp82PlusSfpOutputHighPowerWarningSeverity			DisplayString,
				ommp82PlusSfpOutputLowPowerWarningSeverity			DisplayString,
				ommp82PlusSfpHighSupplyVoltageAlarmSeverity			DisplayString,
				ommp82PlusSfpLowSupplyVoltageAlarmSeverity			DisplayString,
				ommp82PlusSfpHighSupplyVoltageWarningSeverity			DisplayString,
				ommp82PlusSfpLowSupplyVoltageWarningSeverity			DisplayString,
				ommp82PlusSfpPresenceAbsenceNotificationSeverity		DisplayString,
				ommp82PlusSfpTransmitFaultPresenceAlarmSeverity			DisplayString,
				ommp82PlusOtuLossOfSignalAlarmSeverity				DisplayString,
				ommp82PlusOtuLossOfFrameAlarmSeverity				DisplayString,
				ommp82PlusOtuOutOfFrameAlarmSeverity				DisplayString,
				ommp82PlusOtuLossOfMultiFrameAlarmSeverity			DisplayString,
				ommp82PlusOtuOutOfMultiFrameAlarmSeverity			DisplayString,
				ommp82PlusOtuSignalFailAlarmSeverity				DisplayString,
				ommp82PlusOtuSignalDegradeAlarmSeverity				DisplayString,
				ommp82PlusOtuAlarmIndicationSignalAlarmSeverity			DisplayString,
				ommp82PlusOtuIncomingAlignmentErrorAlarmSeverity		DisplayString,
				ommp82PlusOtuTraceIdentifierMismatchAlarmSeverity		DisplayString,
				ommp82PlusOtuBackwardIncomingAlignmentErrorAlarmSeverity	DisplayString,
				ommp82PlusOtuBackwardDefectIndicationAlarmSeverity		DisplayString,
				ommp82PlusOduSignalFailAlarmSeverity				DisplayString,
				ommp82PlusOduSignalDegradeAlarmSeverity				DisplayString,
				ommp82PlusOduAlarmIndicationSignalAlarmSeverity			DisplayString,
				ommp82PlusOduTcm1IncomingAlignmentErrorAlarmSeverity		DisplayString,
				ommp82PlusOduTcm2IncomingAlignmentErrorAlarmSeverity		DisplayString,
				ommp82PlusOduTcm3IncomingAlignmentErrorAlarmSeverity		DisplayString,
				ommp82PlusOduTcm4IncomingAlignmentErrorAlarmSeverity		DisplayString,
				ommp82PlusOduTcm5IncomingAlignmentErrorAlarmSeverity		DisplayString,
				ommp82PlusOduTcm6IncomingAlignmentErrorAlarmSeverity		DisplayString,
				ommp82PlusOduTraceIdentifierMismatchAlarmSeverity		DisplayString,
				ommp82PlusOduLockedDefectAlarmSeverity				DisplayString,
				ommp82PlusOduOpenConnectionIndicationAlarmSeverity		DisplayString,
				ommp82PlusOduBackwardDefectIndicationAlarmSeverity		DisplayString,
				ommp82PlusOduTcm1BackwardIncomingAlignmentErrorAlarmSeverity	DisplayString,
				ommp82PlusOduTcm2BackwardIncomingAlignmentErrorAlarmSeverity	DisplayString,
				ommp82PlusOduTcm3BackwardIncomingAlignmentErrorAlarmSeverity	DisplayString,
				ommp82PlusOduTcm4BackwardIncomingAlignmentErrorAlarmSeverity	DisplayString,
				ommp82PlusOduTcm5BackwardIncomingAlignmentErrorAlarmSeverity	DisplayString,
				ommp82PlusOduTcm6BackwardIncomingAlignmentErrorAlarmSeverity	DisplayString,
				ommp82PlusOduLossOfFrameLossOfMultiframeAlarmSeverity		DisplayString,
				ommp82PlusOpuPayloadMismatchAlarmSeverity			DisplayString,
				ommp82PlusOchLossOfPayloadAlarmSeverity				DisplayString,
				ommp82PlusSdhLossOfSignalAlarmSeverity				DisplayString,
				ommp82PlusSdhOutOfFrameAlarmSeverity				DisplayString,
				ommp82PlusSdhLossOfFrameAlarmSeverity				DisplayString,
				ommp82PlusSdhRsAlarmIndicationSignalAlarmSeverity		DisplayString,
				ommp82PlusSdhRsTraceIdentifierMismatchAlarmSeverity		DisplayString,
				ommp82PlusSdhAuAlarmIndicationSignalAlarmSeverity		DisplayString,
				ommp82PlusSdhAuLossOfPointerAlarmSeverity			DisplayString,
				ommp82PlusSdhMsAlarmIndicationSignalAlarmSeverity		DisplayString,
				ommp82PlusSdhMsRemoteErrorIndicationAlarmSeverity		DisplayString,
				ommp82PlusSdhMsRemoteDefectIndicationAlarmSeverity		DisplayString,
				ommp82PlusSdhMsRemoteFailureIndicationAlarmSeverity		DisplayString,
				ommp82PlusSdhMsB2ExcessiveErrorAlarmSeverity			DisplayString,
				ommp82PlusSdhMsB2SignalDegradeAlarmSeverity			DisplayString,
				ommp82PlusSdhLossOfSequenceSynchronisationAlarmSeverity		DisplayString,
				ommp82PlusSdhLowerOrderPathPayloadLabelMismatchAlarmSeverity	DisplayString,
				ommp82PlusSdhLowerOrderPathUnequippedAlarmSeverity		DisplayString,
				ommp82PlusEthernetLossOfSignalAlarmSeverity			DisplayString,
				ommp82PlusEthernetLossOfSignalSyncAlarmSeverity			DisplayString,
				ommp82PlusEthernetLinkFailureAlarmSeverity			DisplayString,
				ommp82PlusEthernetAutoNegotiationAlarmSeverity			DisplayString,
				ommp82PlusEthernetFrameCheckSequenceAlarmSeverity		DisplayString,
				ommp82PlusEthernetCarrierStatusAlarmSeverity			DisplayString,
				ommp82PlusEthernetHighBerAlarmSeverity				DisplayString,
				ommp82PlusEthernetLocalFaultAlarmSeverity			DisplayString,
				ommp82PlusEthernetRemoteFaultAlarmSeverity			DisplayString,
				ommp82PlusFcTransmitDisparityInversionDefectAlarmSeverity	DisplayString,
				ommp82PlusFcTransmitDigitalLossOfLinkDefectAlarmSeverity	DisplayString,
				ommp82PlusFcTrasnmitLossOfSynchronizationDefectAlarmSeverity	DisplayString,
				ommp82PlusFcReceiveDigitalLossOfLinkDefectAlarmSeverity		DisplayString,
				ommp82PlusFcReceiveLossOfSynchronizationDefectAlarmSeverity	DisplayString,
				ommp82PlusFcReceiveTransitionDetectDefectAlarmSeverity		DisplayString,
				ommp82PlusFcReceiveAnalogLossOfSignalDefectAlarmSeverity	DisplayString,
				ommp82PlusFcReceiveLineCodeViolationDefectAlarmSeverity		DisplayString,
				ommp82PlusGfpCsfSignalFailAlarmSeverity				DisplayString,
				ommp82PlusGfpCsfLinkFailAlarmSeverity				DisplayString,
				ommp82PlusGfpCoreHeaderErrorAlarmSeverity			DisplayString,
				ommp82PlusGfpExtentionHeaderErrorAlarmSeverity			DisplayString,
				ommp82PlusConfigurationTableRowStatus				RowStatus
			}
		
	ommp82PlusCardSoftwareUpgrade OBJECT-TYPE		 
		SYNTAX  DisplayString
		MAX-ACCESS read-write
		STATUS current
		DESCRIPTION
			"Valid only as SET command.
			This property upgrades the software of the OMMP82-PLUS card
			It takes the path of the software release as
			a value
			-----------------------------
			ommp82PlusInterfaceNumber: 0
			-----------------------------
			Values:
			eg: /root/home/rel-2.0.0.tar.gz
			-----------------------------"
		::= { ommp82PlusConfigurationEntry 1 }

	ommp82PlusCardSignalMonitorState OBJECT-TYPE		 
		SYNTAX  INTEGER
		MAX-ACCESS read-write
		STATUS current
		DESCRIPTION
			"This property sets or gets the card's signal
			monitoring state. Disabling card signal monitoring 
			will not provide any signal alarms and performances
			information to the user.
			-----------------------------
			ommp82PlusInterfaceNumber: 0
			-----------------------------
			Values:
			1 - Card Signal Monitoring is enabled
			0 - Card Signal Monitoring is disabled
			-----------------------------"
		::= { ommp82PlusConfigurationEntry 2 }

	ommp82PlusCardOpticalMonitorState OBJECT-TYPE		 
		SYNTAX  INTEGER
		MAX-ACCESS read-write
		STATUS current
		DESCRIPTION
			"This property sets or gets the card's optical
			monitoring state. Disabling card signal monitoring 
			will not provide any signal alarms and performances
			information to the user.
			-----------------------------
			ommp82PlusInterfaceNumber: 0
			-----------------------------
			Values:
			1 - Card Optical Monitoring is enabled
			0 - Card Optical Monitoring is disabled
			-----------------------------"
		::= { ommp82PlusConfigurationEntry 3 }

	ommp82PlusCardSoftReset OBJECT-TYPE		 
		SYNTAX  INTEGER
		MAX-ACCESS read-write
		STATUS current
		DESCRIPTION
			"Valid only as a SET command.
			Reboots the Card, Reconfigures the Card 
			i.e All Configuration Parameter	like Laser State,
			Traffic configuration, Loopback, FEC, optical and 
			signal thresholds, switching mode,
			user choice of line path, auto-negotiation, 
			TTI messages will be restored to previous state
			-----------------------------
			ommp82PlusInterfaceNumber: 0
			-----------------------------
			Values:
			Dont care, any value
			eg: 0
			-----------------------------"
		::= { ommp82PlusConfigurationEntry 4 }

	ommp82PlusCardFactoryReset OBJECT-TYPE		 
		SYNTAX  INTEGER
		MAX-ACCESS read-write
		STATUS current
		DESCRIPTION
			"Valid only as a SET command.
			Sets the Card To Factory Default State
			i.e All User Configuration Parameters like Laser State,
			Traffic configuration, Loopback, FEC, optical and 
			signal thresholds, switching mode,
			user choice of line path, auto-negotiation, TTI messages
			will be set to default state
			-----------------------------
			ommp82PlusInterfaceNumber: 0
			-----------------------------
			Values:
			Dont care, any value
			eg: 0
			-----------------------------"
		::= { ommp82PlusConfigurationEntry 5 }

	ommp82PlusCardAccessStatus OBJECT-TYPE		 
		SYNTAX  INTEGER
		MAX-ACCESS read-write
		STATUS current
		DESCRIPTION
			"This property will tell whether the card is 
			accessible from EMS/LCT or not. Turning off the
			accessbility to the card, will not allow the user
			to access any configuration, alarm or performance
			of the card and also turns off fast alarm
			triggering, global alarm led indication
			-----------------------------
			ommp82PlusInterfaceNumber: 0
			-----------------------------
			Values:
			1 - Card is accessible from EMS/LCT
			0 - Card is inaccessible from EMS/LCT
			-----------------------------"
		::= { ommp82PlusConfigurationEntry 6 }

	ommp82PlusSyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that ilarticular server. 
					If we are not providing NTP server IP address 
					then the system will be synced with the NTP server 
					which is already been registered with card. 
					If both are absent then error message will be returned
					-----------------------------
						Interface : 0
					-----------------------------
						If we want to provide NTP server IP address then
						Value should be a valid IP address as shown below
						: 192.168.21.25
						
						If we don't want to provide NTP server address then no
						need to pass any value. 
					---------------------------"
  						
  		::= { ommp82PlusConfigurationEntry 7 }
  		
  	ommp82PlusSyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 192.168.21.25
							
						If we don't want to provide NTP server address, then no
						need to ilass any value. 
						---------------------------"
  						
  		::= { ommp82PlusConfigurationEntry 8 }
  		
  	ommp82PlusSyncRtcWithSystemTime	 OBJECT-TYPE
		SYNTAX  		DisplayString
  		MAX-ACCESS  	read-write
  		STATUS  		current
  		DESCRIPTION	 	" when we want to manually sync the time value
  						present in RTC with the time value in linux kernel
  						we can use this OID. With this set operation, 
  						the time available with linux kernel will be updated
  						into RTC. It is not required to provide any value for 
  						this operation"
  						
  		::= { ommp82PlusConfigurationEntry 9 }
  		
  	ommp82PlusUpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2017-10-31 15:20:44
						---------------------------"
						
  		::= { ommp82PlusConfigurationEntry 10 }
  		
  	ommp82PlusUpdateGivenTimeIntoRtc	 OBJECT-TYPE
		SYNTAX  		DisplayString
  		MAX-ACCESS  	read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD H:M:S
						
						Example: 2017-10-31 15:20:44
						---------------------------"
						
  		::= { ommp82PlusConfigurationEntry 11 }
  		
  	ommp82PlusSystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { ommp82PlusConfigurationEntry 12 }

	ommp82PlusApsLinePathSwitchingMode OBJECT-TYPE		 
		SYNTAX  INTEGER
		MAX-ACCESS read-write
		STATUS current
		DESCRIPTION
			"Set or Get the line path switching mode.
			-----------------------------
			ommp82PlusInterfaceNumber: 0
			-----------------------------
			Values:
			1 - Automatic mode of switching
			Keeps monitoring for OTU2-LOF/OTU2-AIS/ODU2-AIS 
			periodically and switch to the secondary line path once
			any of the mentioned alarms are detected on the primary
			line path
			2 - Manual mode of switching
			The working path will be as per the user's choice
			of line path. Does not switch to the alternate path
			even though any alarm is present.
			-----------------------------"
		::= { ommp82PlusConfigurationEntry 21 }

	ommp82PlusApsUserChoiceOfLinePath OBJECT-TYPE		 
		SYNTAX  INTEGER
		MAX-ACCESS read-write
		STATUS current
		DESCRIPTION
			"Set or Get the user's choice of line path.
			Valid only when 'ommp82PlusSwitchingModeOfLinePath' is set to
			Manual Mode. In manual mode, user has the previlege to
			set the LINE-1/LINE-2 as the working path
			-----------------------------
			ommp82PlusInterfaceNumber: 0
			-----------------------------
			Values:
			9 - LINE-1 as working path
			10 - LINE-2 as working path
			-----------------------------"
		::= { ommp82PlusConfigurationEntry 22 }

	ommp82PlusApsCurrentOperationalLinePath OBJECT-TYPE		 
		SYNTAX  INTEGER
		MAX-ACCESS read-only
		STATUS current
		DESCRIPTION
			"Get the currently operational working path
			among LINE-1/LINE-2
			-----------------------------
			ommp82PlusInterfaceNumber: 0
			-----------------------------
			Values:
			9 - LINE-1 as working path
			10 - LINE-2 as working path
			-----------------------------"
		::= { ommp82PlusConfigurationEntry 23 }

--	ommp82PlusTrafficConfiguration OBJECT-TYPE		 
--		SYNTAX  DisplayString
--		MAX-ACCESS read-write
--		STATUS current
--		DESCRIPTION
--			"Set or get Traffic configuration for all ports
--			-----------------------------
--			ommp82PlusInterfaceNumber: 0
--			-----------------------------			
--			Value: 
--			At any instant to perform traffic configuration operation,
--			the traffic configuration values need to be passed for
--			all 8 client ports. The following are the traffic
--			configuration values, followed by an example:
--			00 - Un-configure 
--			01 - STM16
--			02 - STM4
--			03 - STM1
--			04 - GE-GFP-T
--			05 - GE-GFP-F
--			06 - FE-GFP-T
--			07 - FE-GFP-F
--			08 - FC-100
--			09 - FC-200
--			10 - OTU-1
--			eg: To set STM16, GE-GFP-F for CLIENT-1, CLIENT-2
--			repectively, the following value needs to be passed,
--			1,2,0,0,0,0,0,0 as a string in which the position
--			represents the port number
--			-----------------------------"
--		::= { ommp82PlusConfigurationEntry 41 }
		
	ommp82PlusTrafficConfiguration OBJECT-TYPE		 
		SYNTAX  INTEGER
		MAX-ACCESS read-write
		STATUS current
		DESCRIPTION
			"Set or get Traffic configuration for all ports
			-----------------------------
			ommp82PlusInterfaceNumber:
			1 to 8 - CLIENT-1 to CLIENT-8
			-----------------------------			
			Value: 
			00 - Un-configure 
			01 - STM16
			02 - STM4
			03 - STM1
			04 - GE-GFP-T
			05 - GE-GFP-F
			06 - FE-GFP-T
			07 - FE-GFP-F
			08 - FC-100
			09 - FC-200
			10 - OTU-1
			-----------------------------"
		::= { ommp82PlusConfigurationEntry 41 }

	ommp82PlusLoopbackState OBJECT-TYPE		 
		SYNTAX  INTEGER
		MAX-ACCESS read-write
		STATUS current
		DESCRIPTION
			"Set or get the loopback state for the
			requested port
			-----------------------------
			ommp82PlusInterfaceNumber:
			1 to 8 - CLIENT-1 to CLIENT-8
			9 - LINE-1
			10 - LINE-2
			-----------------------------
			Values: 
			00 - No Loopback   
			01 - Near End Loopback
			02 - Far End Loopback
			-----------------------------"
		::= { ommp82PlusConfigurationEntry 42 }

	ommp82PlusPortSignalMonitorState OBJECT-TYPE		 
		SYNTAX  INTEGER
		MAX-ACCESS read-write
		STATUS current
		DESCRIPTION
			"This property sets or gets the port's signal
			monitoring state. Disabling port signal monitoring 
			will not provide any signal alarms and performances
			information to the user.
			-----------------------------
			ommp82PlusInterfaceNumber:
			1 to 8 - CLIENT-1 to CLIENT-8
			9 - LINE-1
			10 - LINE-2
			-----------------------------
			Values:
			1 - Port Signal Monitoring is enabled
			0 - Port Signal Monitoring is disabled
			-----------------------------"
		::= { ommp82PlusConfigurationEntry 43 }

	ommp82PlusPortOpticalMonitorState OBJECT-TYPE		 
		SYNTAX  INTEGER
		MAX-ACCESS read-write
		STATUS current
		DESCRIPTION
			"This property sets or gets the port's optical
			monitoring state. Disabling port optical monitoring 
			will not provide any optical alarms and performances
			information to the user.
			-----------------------------
			ommp82PlusInterfaceNumber:
			1 to 8 - CLIENT-1 to CLIENT-8
			9 - LINE-1
			10 - LINE-2
			-----------------------------
			Values:
			1 - Port Optical Monitoring is enabled
			0 - Port Optical Monitoring is disabled
			-----------------------------"
		::= { ommp82PlusConfigurationEntry 44 }

	ommp82PlusClearSignalPerformance OBJECT-TYPE		 
		SYNTAX  INTEGER
		MAX-ACCESS read-write
		STATUS current
		DESCRIPTION
			"Valid only as a SET command.
			Clears signal performance for the requested port
			-----------------------------
			ommp82PlusInterfaceNumber:
			1 to 8 - CLIENT-1 to CLIENT-8
			9 - LINE-1
			10 - LINE-2
			-----------------------------
			Values:
			Dont care, any value
			eg: 0
			-----------------------------"
		::= { ommp82PlusConfigurationEntry 45 }

	ommp82PlusAlsState OBJECT-TYPE		 
		SYNTAX  INTEGER
		MAX-ACCESS read-write
		STATUS current
		DESCRIPTION
			"Set the Automatic Laser Switching(ALS) mode for
			for requested port. Based on the RX LOS state of the
			port, the transmit LASER state will be controlled
			according to the algorithm defined for ALS in
			ITUT 664 Standard
			-----------------------------
			ommp82PlusInterfaceNumber:
			1 to 8 - CLIENT-1 to CLIENT-8
			9 - LINE-1
			10 - LINE-2
			-----------------------------
			Values: 
			1 - Enable ALS state
			0 - Disable ALS state
			-----------------------------" 
		::= { ommp82PlusConfigurationEntry 46 }

	ommp82PlusAlsPulseRepetitionTime OBJECT-TYPE		 
		SYNTAX  INTEGER
		MAX-ACCESS read-write
		STATUS current
		DESCRIPTION
			"Pulse repetition time is the time for automatic 
			restart of XFP LASER once the ALS algorithm starts.
			-----------------------------
			ommp82PlusInterfaceNumber:
			1 to 8 - CLIENT-1 to CLIENT-8
			9 - LINE-1
			10 - LINE-2
			-----------------------------
			Values: 
			100 seconds to 300 seconds
			-----------------------------"
		::= { ommp82PlusConfigurationEntry 47 }

	ommp82PlusOtuFecConfiguration OBJECT-TYPE		 
		SYNTAX  INTEGER
		MAX-ACCESS read-write
		STATUS current
		DESCRIPTION
			"Set or Get FEC type for requested port configured with
			 OTU2/OTU1 traffic.  
			-----------------------------
			ommp82PlusInterfaceNumber:
			1 to 8 - CLIENT-1 to CLIENT-8
			9 - LINE-1
			10 - LINE-2
			-----------------------------
			Values: 
			00 - Zero FEC 
			01 - Reed-Solomon GFEC
			03 - UFEC(I.7 FEC, applicable for line port only)
			-----------------------------"
		::= { ommp82PlusConfigurationEntry 61 }

	ommp82PlusOtuSignalFailThreshold OBJECT-TYPE		 
		SYNTAX  INTEGER
		MAX-ACCESS read-write
		STATUS current
		DESCRIPTION
			"Set or Get SM Signal Failure 
			Threshold value for the requested port configured with 
			OTU2/OTU1 traffic.
			-----------------------------
			ommp82PlusInterfaceNumber:
			1 to 8 - CLIENT-1 to CLIENT-8
			9 - LINE-1
			10 - LINE-2
			-----------------------------
			Values: 
			03 - 1.E -03
			04 - 1.E -04
			05 - 1.E -05
			-----------------------------" 
		::= { ommp82PlusConfigurationEntry 62 }

	ommp82PlusOtuSignalDegradeThreshold OBJECT-TYPE		 
		SYNTAX  INTEGER
		MAX-ACCESS read-write
		STATUS current
		DESCRIPTION
			"Set or Get SM Signal Degrade 
			Threshold value for the requested port configured with 
			OTU2/OTU1 traffic.
			-----------------------------
			ommp82PlusInterfaceNumber:
			1 to 8 - CLIENT-1 to CLIENT-8
			9 - LINE-1
			10 - LINE-2
			-----------------------------
			Values:
			06 - 1.E -06
			07 - 1.E -07
			08 - 1.E -08
			09 - 1.E -09
			10 - 1.E -10(for line only)
			-----------------------------"
		::= { ommp82PlusConfigurationEntry 63 }

	ommp82PlusOtuAlarmIndicationSignalAlarmInsertion OBJECT-TYPE		 
		SYNTAX  INTEGER
		MAX-ACCESS read-write
		STATUS current
		DESCRIPTION
			"Inserts OTU-AIS maitainance signal for the requested
			port configured with OTU2/OTU1 traffic.
			-----------------------------
			ommp82PlusInterfaceNumber:
			1 to 8 - CLIENT-1 to CLIENT-8
			9 - LINE-1
			10 - LINE-2
			-----------------------------
			Values: 
			1 - Enable Insertion
			0 - Disable Insertion  
			-----------------------------"
		::= { ommp82PlusConfigurationEntry 64 }

	ommp82PlusOtuSapiTransmitTraceMessage OBJECT-TYPE
		SYNTAX DisplayString
		MAX-ACCESS read-write
		STATUS current
		DESCRIPTION
			"Set or get the 15 characters SAPI Transmit TTI message
			which is put into the outgoing OTU2/OTU1 frame. 
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 65 }

	ommp82PlusOtuDapiTransmitTraceMessage OBJECT-TYPE
		SYNTAX DisplayString
		MAX-ACCESS read-write
		STATUS current
		DESCRIPTION
			"Set or get the 15 characters DAPI Transmit TTI message
			which is put into the outgoing OTU2/OTU1 frame. 
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 66 }
		
	ommp82PlusOtuOperatorSpecificTransmitTraceMessage OBJECT-TYPE
		SYNTAX DisplayString
		MAX-ACCESS read-write
		STATUS current
		DESCRIPTION
			"Set or get the 32 characters Operator Specific Transmit
			TTI message which is put into the outgoing OTU2/OTU1
			frame. 
			-----------------------------
			ommp82PlusInterfaceNumber:
			1 to 8 - CLIENT-1 to CLIENT-8
			9 - LINE-1
			10 - LINE-2
			-----------------------------
			Values:
			eg: 12345123451234512345123451234500
			-----------------------------" 
		::= { ommp82PlusConfigurationEntry 67 }
		
	ommp82PlusOtuSapiExpectedTraceMessage OBJECT-TYPE
		SYNTAX DisplayString
		MAX-ACCESS read-write
		STATUS current
		DESCRIPTION
			"15 characters SM SAPI Expected TTI message - Message
			set here is used for comparison with the message present
			in SM SAPI field of the incoming OTU2/OTU1 frames.
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 68 }
		
	ommp82PlusOtuDapiExpectedTraceMessage OBJECT-TYPE
		SYNTAX DisplayString
		MAX-ACCESS read-write
		STATUS current
		DESCRIPTION
			"15 characters SM DAPI Expected TTI message - Message
			set here is used for comparison with the message present
			in SM DAPI field of the incoming OTU2/OTU1 frames.
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 69 }

	ommp82PlusOtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU2/OTU1 frames.
			-----------------------------
			ommp82PlusInterfaceNumber:
			1 to 8 - CLIENT-1 to CLIENT-8
			9 - LINE-1
			10 - LINE-2
			-----------------------------
			Values:
			eg: 12345123451234512345123451234500
			-----------------------------" 
		::= { ommp82PlusConfigurationEntry 70 }

	ommp82PlusOtuSapiReceivedTraceMessage OBJECT-TYPE
		SYNTAX DisplayString
		MAX-ACCESS read-only
		STATUS current
		DESCRIPTION
			"Gets the 15 characters SAPI TTI message
			which is extracted from the incoming OTU2/OTU1
			data stream.
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 71 }

	ommp82PlusOtuDapiReceivedTraceMessage OBJECT-TYPE
		SYNTAX DisplayString
		MAX-ACCESS read-only
		STATUS current
		DESCRIPTION
			"Gets the 15 characters DAPI TTI message
			which is extracted from the incoming OTU2/OTU1 data
			stream.
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 72 }
		
	ommp82PlusOtuOperatorSpecificReceivedTraceMessage OBJECT-TYPE
		SYNTAX DisplayString
		MAX-ACCESS read-only
		STATUS current
		DESCRIPTION
			"Gets the 32 characters DAPI TTI message
			which is extracted from the incoming OTU2/OTU1 data
			stream. 
			-----------------------------
			ommp82PlusInterfaceNumber:
			1 to 8 - CLIENT-1 to CLIENT-8
			9 - LINE-1
			10 - LINE-2
			-----------------------------
			Values:
			eg: 12345123451234512345123451234500
			-----------------------------" 
		::= { ommp82PlusConfigurationEntry 73 }

	ommp82PlusOduSignalFailThreshold OBJECT-TYPE		 
		SYNTAX  INTEGER
		MAX-ACCESS read-write
		STATUS current
		DESCRIPTION
			"Set or Get PM Signal Failure 
			Threshold value for the requested port configured with 
			OTU2/OTU1 traffic.
			-----------------------------
			ommp82PlusInterfaceNumber:
			1 to 8 - CLIENT-1 to CLIENT-8
			9 - LINE-1
			10 - LINE-2
			-----------------------------
			Values: 
			03 - 1.E -03
			04 - 1.E -04
			05 - 1.E -05
			-----------------------------" 
		::= { ommp82PlusConfigurationEntry 81 }

	ommp82PlusOduSignalDegradeThreshold OBJECT-TYPE		 
		SYNTAX  INTEGER
		MAX-ACCESS read-write
		STATUS current
		DESCRIPTION
			"Set or Get PM Signal Degrade 
			Threshold value for the requested port configured with 
			OTU2/OTU1 traffic.
			-----------------------------
			ommp82PlusInterfaceNumber:
			1 to 8 - CLIENT-1 to CLIENT-8
			9 - LINE-1
			10 - LINE-2
			-----------------------------
			Values: 
			06 - 1.E -06
			07 - 1.E -07
			08 - 1.E -08
			09 - 1.E -09
			10 - 1.E -10(for line only)
			-----------------------------" 
		::= { ommp82PlusConfigurationEntry 82 }

	ommp82PlusOduAlarmIndicationSignalAlarmInsertion OBJECT-TYPE		 
		SYNTAX  INTEGER
		MAX-ACCESS read-write
		STATUS current
		DESCRIPTION
			"Inserts ODU-AIS maintenance signal for the requested 
			port configured with OTU2/OTU1 traffic.
			-----------------------------
			ommp82PlusInterfaceNumber:
			1 to 8 - CLIENT-1 to CLIENT-8
			9 - LINE-1
			10 - LINE-2
			-----------------------------
			Values: 
			1 - Enable Insertion
			0 - Disable Insertion  
			-----------------------------"
		::= { ommp82PlusConfigurationEntry 83 }

	ommp82PlusOduLockedDefectAlarmInsertion OBJECT-TYPE		 
		SYNTAX  INTEGER
		MAX-ACCESS read-write
		STATUS current
		DESCRIPTION
			"Inserts ODU-LCK maintenance signal for the requested 
			port configured with OTU2/OTU1 traffic.
			-----------------------------
			ommp82PlusInterfaceNumber:
			1 to 8 - CLIENT-1 to CLIENT-8
			9 - LINE-1
			10 - LINE-2
			-----------------------------
			Values: 
			1 - Enable Insertion
			0 - Disable Insertion  
			-----------------------------"
		::= { ommp82PlusConfigurationEntry 84 }

	ommp82PlusOduOpenConnectionIndicationAlarmInsertion OBJECT-TYPE		 
		SYNTAX  INTEGER
		MAX-ACCESS read-write
		STATUS current
		DESCRIPTION
			"Inserts ODU-OCI maintenance signal for the requested 
			port configured with OTU2/OTU1 traffic.
			-----------------------------
			ommp82PlusInterfaceNumber:
			1 to 8 - CLIENT-1 to CLIENT-8
			9 - LINE-1
			10 - LINE-2
			-----------------------------
			Values: 
			1 - Enable Insertion
			0 - Disable Insertion  
			-----------------------------"
		::= { ommp82PlusConfigurationEntry 85 }

	ommp82PlusOduSapiTransmitTraceMessage OBJECT-TYPE
		SYNTAX DisplayString
		MAX-ACCESS read-write
		STATUS current
		DESCRIPTION
			"Set or get the 15 characters SAPI Transmit TTI message
			which is put into the outgoing OTU2/OTU1
			frame at the PM level. 
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 86 }
		
	ommp82PlusOduDapiTransmitTraceMessage OBJECT-TYPE
		SYNTAX DisplayString
		MAX-ACCESS read-write
		STATUS current
		DESCRIPTION
			"Set or get the 15 characters DAPI Transmit TTI message
			which is put into the outgoing OTU2/OTU1
			frame at the PM level. 
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 87 }
		
	ommp82PlusOduOperatorSpecificTransmitTraceMessage OBJECT-TYPE
		SYNTAX DisplayString
		MAX-ACCESS read-write
		STATUS current
		DESCRIPTION
			"Set or get the 32 characters Operator Specific Transmit
			TTI message which is put into the outgoing OTU2/OTU1
			frame at the PM level. 
			-----------------------------
			ommp82PlusInterfaceNumber:
			1 to 8 - CLIENT-1 to CLIENT-8
			9 - LINE-1
			10 - LINE-2
			-----------------------------
			Values:
			eg: 12345123451234512345123451234500
			-----------------------------" 
		::= { ommp82PlusConfigurationEntry 88 }
		
	ommp82PlusOduSapiExpectedTraceMessage OBJECT-TYPE
		SYNTAX DisplayString
		MAX-ACCESS read-write
		STATUS current
		DESCRIPTION
			"15 characters PM SAPI Expected TTI message - Message
			set here is used for comparison with the message present
			in PM SAPI field of the incoming OTU2/OTU1 frames.
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 89 }

	ommp82PlusOduDapiExpectedTraceMessage OBJECT-TYPE
		SYNTAX DisplayString
		MAX-ACCESS read-write
		STATUS current
		DESCRIPTION
			"15 characters PM DAPI Expected TTI message - Message
			set here is used for comparison with the message present
			in PM DAPI field of the incoming OTU2/OTU1 frames.
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 90 }
		
	ommp82PlusOduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU2/OTU1 frames.
			-----------------------------
			ommp82PlusInterfaceNumber:
			1 to 8 - CLIENT-1 to CLIENT-8
			9 - LINE-1
			10 - LINE-2
			-----------------------------
			Values:
			eg: 12345123451234512345123451234500
			-----------------------------" 
		::= { ommp82PlusConfigurationEntry 91 }

	ommp82PlusOduSapiReceivedTraceMessage OBJECT-TYPE
		SYNTAX DisplayString
		MAX-ACCESS read-only
		STATUS current
		DESCRIPTION
			"Gets the 15 characters SAPI TTI message
			which is extracted from the incoming OTU2/OTU1 data
			stream.
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 92 }

	ommp82PlusOduDapiReceivedTraceMessage OBJECT-TYPE
		SYNTAX DisplayString
		MAX-ACCESS read-only
		STATUS current
		DESCRIPTION
			"Gets the 15 characters DAPI TTI message
			which is extracted from the incoming OTU2/OTU1
			data stream.
			-----------------------------
			ommp82PlusInterfaceNumber:
			1 to 8 - CLIENT-1 to CLIENT-8
			9 - LINE-1
			10 - LINE-2
			-----------------------------
			Values:
			eg: 123451234512345
			-----------------------------" 
		::= { ommp82PlusConfigurationEntry 93 }
		
	ommp82PlusOduOperatorSpecificReceivedTraceMessage OBJECT-TYPE
		SYNTAX DisplayString
		MAX-ACCESS read-only
		STATUS current
		DESCRIPTION
			"Gets the 32 characters DAPI TTI message
			which is extracted from the incoming OTU2/OTU1
			data stream.
			-----------------------------
			ommp82PlusInterfaceNumber:
			1 to 8 - CLIENT-1 to CLIENT-8
			9 - LINE-1
			10 - LINE-2
			-----------------------------
			Values:
			eg: 12345123451234512345123451234500
			-----------------------------" 
		::= { ommp82PlusConfigurationEntry 94 }

	ommp82PlusOpuTransmitPayloadType OBJECT-TYPE
		SYNTAX INTEGER
		MAX-ACCESS read-only
		STATUS current
		DESCRIPTION
			"A one-byte payload type signal is defined in the PSI[0]
			byte of the payload structure identifier to indicate the
			composition of the OPUk signal. Gets the payload type
			that is put into the outgoing OTU2/OTU1 datastream.
			-----------------------------
			ommp82PlusInterfaceNumber:
			1 to 8 - CLIENT-1 to CLIENT-8
			9 - LINE-1
			10 - LINE-2
			-----------------------------
			Values:
			eg: 20
			-----------------------------" 
		::= { ommp82PlusConfigurationEntry 95 }

	ommp82PlusOpuReceivedPayloadType OBJECT-TYPE		 
		SYNTAX  INTEGER
		MAX-ACCESS read-only
		STATUS current
		DESCRIPTION
			"A one-byte payload type signal is defined in the PSI[0]
			byte of the payload structure identifier to indicate the
			composition of the OPUk signal. Gets the payload type
			extracted from the incoming OTU2/OTU1 datastream.
			-----------------------------
			ommp82PlusInterfaceNumber:
			1 to 8 - CLIENT-1 to CLIENT-8
			9 - LINE-1
			10 - LINE-2
			-----------------------------
			Values:
			eg: 20
			-----------------------------"
		::= { ommp82PlusConfigurationEntry 96 }
		
	ommp82PlusSdhMsB2ExcessiveErrorThreshold OBJECT-TYPE		 
		SYNTAX  INTEGER
		MAX-ACCESS read-write
		STATUS current
		DESCRIPTION
			"Set or Get B2 Signal Failure Threshold value for the 
			requested port configured with STM-1/4/16 traffic.
			-----------------------------
			ommp82PlusInterfaceNumber:
			1 to 8 - CLIENT-1 to CLIENT-8
			-----------------------------
			Values:
			03 - 1.E -03
			04 - 1.E -04
			05 - 1.E -05
			-----------------------------"
		::= { ommp82PlusConfigurationEntry 101 }

	ommp82PlusSdhMsB2SignalDegradeThreshold OBJECT-TYPE		 
		SYNTAX  INTEGER
		MAX-ACCESS read-write
		STATUS current
		DESCRIPTION
			"Set or Get B2 Signal Degrade Threshold value for the 
			requested port configured with STM-1/4/16 traffic.
			-----------------------------
			ommp82PlusInterfaceNumber:
			1 to 8 - CLIENT-1 to CLIENT-8
			-----------------------------
			Values:
			06 - 1.E -06
			07 - 1.E -07
			08 - 1.E -08
			09 - 1.E -09
			10 - 1.E -10
			11 - 1.E -11
			-----------------------------"
		::= { ommp82PlusConfigurationEntry 102 }

	ommp82PlusEthernetAutoNegotiation OBJECT-TYPE		 
		SYNTAX  INTEGER
		MAX-ACCESS read-write
		STATUS current
		DESCRIPTION
			"Set or Get the Auto-negotiation mode for the
			requested port configured with GE-GFP-F/GE-GFP-T traffic.
			Enabling auto negotiation will automatically establish
			the link between link-partners on basis of speed,
			flow-control and duplexity.
			If disabled, the link status between the link-partners
			cannot be restored after the link is broken.
			-----------------------------
			ommp82PlusInterfaceNumber:
			1 to 8 - CLIENT-1 to CLIENT-8
			-----------------------------
			Value:
			1 - Enable Auto-Negotiation
			0 - Disable Auto-negotiation
			-----------------------------"
		::= { ommp82PlusConfigurationEntry 111 }
		
	ommp82PlusCalibrateHyphyXfiSerdes OBJECT-TYPE		 
		SYNTAX  INTEGER
		MAX-ACCESS read-write
		STATUS current
		DESCRIPTION
			"Valid only as SET command.
			For every card which is come freshly manufactured from
			the factory, the XFI serdes of the line ports need to
			be calibrated in hyphy w.r.t to OTU2 signal, since the
			serdes in all the mapper chips will not be the same.
			-----------------------------
			ommp82PlusInterfaceNumber:0
			-----------------------------
			Values:
			9 - LINE-1
			10 - LINE-2
			-----------------------------"
		::= { ommp82PlusConfigurationEntry 121 }			

	ommp82PlusTunableXfpLaserWavelength OBJECT-TYPE		 
		SYNTAX  INTEGER
		MAX-ACCESS read-write
		STATUS current
		DESCRIPTION
			"Set or Get the XFP wavelength for the requested port
			-----------------------------
			ommp82PlusInterfaceNumber:
			9 - LINE-1
			10 - LINE-2
			-----------------------------
			Values:
			eg: 1529.944
			-----------------------------"
		::= { ommp82PlusConfigurationEntry 131 }

	ommp82PlusTunableXfpLaserChannelNumber OBJECT-TYPE		 
		SYNTAX  INTEGER
		MAX-ACCESS read-write
		STATUS current
		DESCRIPTION
			"Set or Get the XFP Channel Number for the the requested
			port
			-----------------------------
			ommp82PlusInterfaceNumber:
			9 - LINE-1
			10 - LINE-2
			-----------------------------
			Values:
			eg: 10
			-----------------------------"
		::= { ommp82PlusConfigurationEntry 132 }

	ommp82PlusXfpLaserState OBJECT-TYPE		 
		SYNTAX  INTEGER
		MAX-ACCESS read-write
		STATUS current
		DESCRIPTION
			"Set or Get the XFP LASER state for the the requested
			port
			-----------------------------
			ommp82PlusInterfaceNumber:
			9 - LINE-1
			10 - LINE-2
			-----------------------------
			Values: 
			00 - Laser OFF
			01 - Laser ON
			-----------------------------"
		::= { ommp82PlusConfigurationEntry 133 }

	ommp82PlusXfpReset OBJECT-TYPE		 
		SYNTAX  INTEGER
		MAX-ACCESS read-write
		STATUS current
		DESCRIPTION
			"Valid only as a SET command.
			Resets the XFP.
			-----------------------------
			ommp82PlusInterfaceNumber:
			9 - LINE-1
			10 - LINE-2
			-----------------------------
			Values: 
			Dont care, any value
			eg: 0
			-----------------------------"
		::= { ommp82PlusConfigurationEntry 134 }

	ommp82PlusXfpPowerDownMode OBJECT-TYPE		 
		SYNTAX  INTEGER
		MAX-ACCESS read-write
		STATUS current
		DESCRIPTION
			"Valid only as a SET command.
			Sets the XFP in the Power Down mode i.e. low power 
			consumption mode.
			-----------------------------
			ommp82PlusInterfaceNumber:
			9 - LINE-1
			10 - LINE-2
			-----------------------------
			Values: 
			01 - power down XFP
			-----------------------------"
		::= { ommp82PlusConfigurationEntry 135 }

	ommp82PlusXfpLineLoopback OBJECT-TYPE		 
		SYNTAX  INTEGER
		MAX-ACCESS read-write
		STATUS current
		DESCRIPTION
			"Set or Get line loopback in XFP			
			----------------------------
			ommp82PlusInterfaceNumber:
			9 - LINE-1
			10 - LINE-2
			-----------------------------
			Values: 
			1 - Enable XFP Line Loopback
			0 - Disable XFP Line Loopback
			-----------------------------"
		::= { ommp82PlusConfigurationEntry 136 }

	ommp82PlusXfpXfiLoopback OBJECT-TYPE		 
		SYNTAX  INTEGER
		MAX-ACCESS read-write
		STATUS current
		DESCRIPTION
			"Set or Get Xfi loopback in XFP			
			----------------------------
			ommp82PlusInterfaceNumber:
			9 - LINE-1
			10 - LINE-2
			-----------------------------
			Values: 
			1 - Enable XFP Xfi Loopback
			0 - Disable XFP Xfi Loopback
			-----------------------------"
		::= { ommp82PlusConfigurationEntry 137 }

	ommp82PlusXfpAmplitudeThresholdOfReceiverForFecControl OBJECT-TYPE		 
		SYNTAX  INTEGER
		MAX-ACCESS read-write
		STATUS current
		DESCRIPTION
			"Set or Get amplitude threshold of receiver for FEC control			
			----------------------------
			ommp82PlusInterfaceNumber:
			9 - LINE-1
			10 - LINE-2
			-----------------------------
			Values: 
			eg: Reserved for further study
			-----------------------------"
		::= { ommp82PlusConfigurationEntry 138 }

	ommp82PlusXfpPhaseInEyeDiagramForFecControl OBJECT-TYPE		 
		SYNTAX  INTEGER
		MAX-ACCESS read-write
		STATUS current
		DESCRIPTION
			"Set or Get XFP phase in eye diagram for FEC control			
			----------------------------
			ommp82PlusInterfaceNumber:
			9 - LINE-1
			10 - LINE-2
			-----------------------------
			Values: 
			eg: Reserved for further study
			-----------------------------"
		::= { ommp82PlusConfigurationEntry 139 }

	ommp82PlusXfpSystemReportingBer OBJECT-TYPE		 
		SYNTAX  INTEGER
		MAX-ACCESS read-write
		STATUS current
		DESCRIPTION
			"Set or Get XFP system reporting BER			
			----------------------------
			ommp82PlusInterfaceNumber:
			9 - LINE-1
			10 - LINE-2
			-----------------------------
			Values: 
			eg: Reserved for further study
			-----------------------------"
		::= { ommp82PlusConfigurationEntry 140 }

	ommp82PlusXfpHighTemperatureAlarmThreshold OBJECT-TYPE
		SYNTAX DisplayString
		MAX-ACCESS read-write
		STATUS current
		DESCRIPTION
			"Set or Get High Temperature Alarm Threshold
			(in degree celsius) for the requested port
			-----------------------------
			ommp82PlusInterfaceNumber:
			9 - LINE-1
			10 - LINE-2
			-----------------------------
			Values: 
			eg: 65 
			-----------------------------" 
		::= { ommp82PlusConfigurationEntry 141 }
		
	ommp82PlusXfpLowTemperatureAlarmThreshold OBJECT-TYPE
		SYNTAX DisplayString
		MAX-ACCESS read-write
		STATUS current
		DESCRIPTION
			"Set or Get Low Temperature Alarm Threshold
			(in degree celsius) for the requested port
			-----------------------------
			ommp82PlusInterfaceNumber:
			9 - LINE-1
			10 - LINE-2
			-----------------------------
			Values: 
			eg: 5 
			-----------------------------" 
		::= { ommp82PlusConfigurationEntry 142 }
		
	ommp82PlusXfpHighTemperatureWarningThreshold OBJECT-TYPE
		SYNTAX DisplayString
		MAX-ACCESS read-write
		STATUS current
		DESCRIPTION
			"Set or Get High Temperature Warning Threshold
			(in degree celsius) for the requested port
			-----------------------------
			ommp82PlusInterfaceNumber:
			9 - LINE-1
			10 - LINE-2
			-----------------------------
			Values: 
			eg: 60 
			-----------------------------"
		::= { ommp82PlusConfigurationEntry 143 }
		
	ommp82PlusXfpLowTemperatureWarningThreshold OBJECT-TYPE
		SYNTAX DisplayString
		MAX-ACCESS read-write
		STATUS current
		DESCRIPTION
			"Set or Get Low Temperature Warning Threshold
			(in degree celsius) for the requested port
			-----------------------------
			ommp82PlusInterfaceNumber:
			9 - LINE-1
			10 - LINE-2
			-----------------------------
			Values: 
			eg: 10 
			-----------------------------"
		::= { ommp82PlusConfigurationEntry 144 }

	ommp82PlusXfpHighBiasCurrentAlarmThreshold OBJECT-TYPE
		SYNTAX DisplayString
		MAX-ACCESS read-write
		STATUS current
		DESCRIPTION
			"Set or Get High Bias Current Alarm Threshold
			(in milli ampere) for the requested port
			-----------------------------
			ommp82PlusInterfaceNumber:
			9 - LINE-1
			10 - LINE-2
			-----------------------------
			Values:
			eg: 35.6
			-----------------------------"			
		::= { ommp82PlusConfigurationEntry 145 }
		
	ommp82PlusXfpLowBiasCurrentAlarmThreshold OBJECT-TYPE
		SYNTAX DisplayString
		MAX-ACCESS read-write
		STATUS current
		DESCRIPTION
			"Set or Get Low Bias Current Alarm Threshold
			(in milli ampere) for the requested port
			-----------------------------
			ommp82PlusInterfaceNumber:
			9 - LINE-1
			10 - LINE-2
			-----------------------------
			Values:
			eg: 31.1
			-----------------------------"
		::= { ommp82PlusConfigurationEntry 146 }
		
	ommp82PlusXfpHighBiasCurrentWarningThreshold OBJECT-TYPE
		SYNTAX DisplayString
		MAX-ACCESS read-write
		STATUS current
		DESCRIPTION
			"Set or Get High Bias Current Warning Threshold
			(in milli ampere) for the requested port
			-----------------------------
			ommp82PlusInterfaceNumber:
			9 - LINE-1
			10 - LINE-2
			-----------------------------
			Values:
			eg: 34.5
			-----------------------------"
		::= { ommp82PlusConfigurationEntry 147 }
		
	ommp82PlusXfpLowBiasCurrentWarningThreshold OBJECT-TYPE
		SYNTAX DisplayString
		MAX-ACCESS read-write
		STATUS current
		DESCRIPTION
			"Set or Get Low Bias Current Warning Threshold
			(in milli ampere) for the requested port
			-----------------------------
			ommp82PlusInterfaceNumber:
			9 - LINE-1
			10 - LINE-2
			-----------------------------
			Values:
			eg: 32.8
			-----------------------------"
		::= { ommp82PlusConfigurationEntry 148 }
		
	ommp82PlusXfpInputHighPowerAlarmThreshold OBJECT-TYPE
		SYNTAX DisplayString
		MAX-ACCESS read-write
		STATUS current
		DESCRIPTION
			"Set or Get Input High Power Alarm Threshold
			(in dbm) for the requested port
			-----------------------------
			ommp82PlusInterfaceNumber:
			9 - LINE-1
			10 - LINE-2
			-----------------------------
			Values:
			eg: -9.1
			-----------------------------"
		::= { ommp82PlusConfigurationEntry 149 }

	ommp82PlusXfpInputLowPowerAlarmThreshold OBJECT-TYPE
		SYNTAX DisplayString
		MAX-ACCESS read-write
		STATUS current
		DESCRIPTION
			"Set or Get Input Low Power Alarm Threshold
			(in dbm) for the requested port
			-----------------------------
			ommp82PlusInterfaceNumber:
			9 - LINE-1
			10 - LINE-2
			-----------------------------
			Values:
			eg: -35.6
			-----------------------------"
		::= { ommp82PlusConfigurationEntry 150 }
		
	ommp82PlusXfpInputHighPowerWarningThreshold OBJECT-TYPE
		SYNTAX DisplayString
		MAX-ACCESS read-write
		STATUS current
		DESCRIPTION
			"Set or Get Input High Power Warning Threshold
			(in dbm) for the requested port
			-----------------------------
			ommp82PlusInterfaceNumber:
			9 - LINE-1
			10 - LINE-2
			-----------------------------
			Values:
			eg: -11.2
			-----------------------------"
		::= { ommp82PlusConfigurationEntry 151 }
		
	ommp82PlusXfpInputLowPowerWarningThreshold OBJECT-TYPE
		SYNTAX DisplayString
		MAX-ACCESS read-write
		STATUS current
		DESCRIPTION
			"Set or Get Input Low Power Warning Threshold
			(in dbm) for the requested port
			-----------------------------
			ommp82PlusInterfaceNumber:
			9 - LINE-1
			10 - LINE-2
			-----------------------------
			Values:
			eg: -31.3
			-----------------------------"
		::= { ommp82PlusConfigurationEntry 152 }
		
	ommp82PlusXfpOutputHighPowerAlarmThreshold OBJECT-TYPE
		SYNTAX DisplayString
		MAX-ACCESS read-write
		STATUS current
		DESCRIPTION
			"Set or Get Output High Power Alarm Threshold
			(in dbm) for the requested port
			-----------------------------
			ommp82PlusInterfaceNumber:
			9 - LINE-1
			10 - LINE-2
			-----------------------------
			Values:
			eg: +2.0
			-----------------------------"
		::= { ommp82PlusConfigurationEntry 153 }

	ommp82PlusXfpOutputLowPowerAlarmThreshold OBJECT-TYPE
		SYNTAX DisplayString
		MAX-ACCESS read-write
		STATUS current
		DESCRIPTION
			"Set or Get Output Low Power Alarm Threshold
			(in dbm) for the requested port
			-----------------------------
			ommp82PlusInterfaceNumber:
			9 - LINE-1
			10 - LINE-2
			-----------------------------
			Values:
			eg: -3.5
			-----------------------------"
		::= { ommp82PlusConfigurationEntry 154 }
		
	ommp82PlusXfpOutputHighPowerWarningThreshold OBJECT-TYPE
		SYNTAX DisplayString
		MAX-ACCESS read-write
		STATUS current
		DESCRIPTION
			"Set or Get Output High Power Warning Threshold
			(in dbm) for the requested port
			-----------------------------
			ommp82PlusInterfaceNumber:
			9 - LINE-1
			10 - LINE-2
			-----------------------------
			Values:
			eg: +1.3
			-----------------------------"
		::= { ommp82PlusConfigurationEntry 155 }
		
	ommp82PlusXfpOutputLowPowerWarningThreshold OBJECT-TYPE
		SYNTAX DisplayString
		MAX-ACCESS read-write
		STATUS current
		DESCRIPTION
			"Set or Get Output Low Power Warning Threshold
			(in dbm) for the requested port
			-----------------------------
			ommp82PlusInterfaceNumber:
			9 - LINE-1
			10 - LINE-2
			-----------------------------
			Values:
			eg: -2.5
			-----------------------------"
		::= { ommp82PlusConfigurationEntry 156 }
		
	ommp82PlusXfpHighSupplyVoltageAlarmThreshold OBJECT-TYPE
		SYNTAX DisplayString
		MAX-ACCESS read-write
		STATUS current
		DESCRIPTION
			"Set or Get High Supply Voltage Alarm Threshold
			(in volts) for the requested port
			-----------------------------
			ommp82PlusInterfaceNumber:
			9 - LINE-1
			10 - LINE-2
			-----------------------------
			Values:
			eg: +3.3
			-----------------------------"
		::= { ommp82PlusConfigurationEntry 157 }

	ommp82PlusXfpLowSupplyVoltageAlarmThreshold OBJECT-TYPE
		SYNTAX DisplayString
		MAX-ACCESS read-write
		STATUS current
		DESCRIPTION
			"Set or Get Low Supply Voltage Alarm Threshold
			(in volts) for the requested port
			-----------------------------
			ommp82PlusInterfaceNumber:
			9 - LINE-1
			10 - LINE-2
			-----------------------------
			Values:
			eg: +3.0
			-----------------------------"
		::= { ommp82PlusConfigurationEntry 158 }
		
	ommp82PlusXfpHighSupplyVoltageWarningThreshold OBJECT-TYPE
		SYNTAX DisplayString
		MAX-ACCESS read-write
		STATUS current
		DESCRIPTION
			"Set or Get High Supply Voltage Warning Threshold
			(in volts) for the requested port
			-----------------------------
			ommp82PlusInterfaceNumber:
			9 - LINE-1
			10 - LINE-2
			-----------------------------
			Values:
			eg: +3.2
			-----------------------------"
		::= { ommp82PlusConfigurationEntry 159 }
		
	ommp82PlusXfpLowSupplyVoltageWarningThreshold OBJECT-TYPE
		SYNTAX DisplayString
		MAX-ACCESS read-write
		STATUS current
		DESCRIPTION
			"Set or Get Low Supply Voltage Warning Threshold
			(in volts) for the requested port
			-----------------------------
			ommp82PlusInterfaceNumber:
			9 - LINE-1
			10 - LINE-2
			-----------------------------
			Values:
			eg: +3.1
			-----------------------------"
		::= { ommp82PlusConfigurationEntry 160 }

	ommp82PlusSfpLaserState OBJECT-TYPE		 
		SYNTAX  INTEGER
		MAX-ACCESS read-write
		STATUS current
		DESCRIPTION
			"Set or Get the SFP LASER state for the the requested
			port
			-----------------------------
			ommp82PlusInterfaceNumber:
			1 to 8 - CLIENT-1 to CLIENT-8
			-----------------------------
			Values: 
			01 - Laser ON
			00 - Laser OFF
			-----------------------------" 
		::= { ommp82PlusConfigurationEntry 181 }

	ommp82PlusSfpHighTemperatureAlarmThreshold OBJECT-TYPE
		SYNTAX DisplayString
		MAX-ACCESS read-write
		STATUS current
		DESCRIPTION
			"Set or Get High Temperature Alarm Threshold
			(in degree celsius) for the requested port
			-----------------------------
			ommp82PlusInterfaceNumber:
			1 to 8 - CLIENT-1 to CLIENT-8
			-----------------------------
			Values: 
			eg: 65 
			-----------------------------" 
		::= { ommp82PlusConfigurationEntry 182 }
		
	ommp82PlusSfpLowTemperatureAlarmThreshold OBJECT-TYPE
		SYNTAX DisplayString
		MAX-ACCESS read-write
		STATUS current
		DESCRIPTION
			"Set or Get Low Temperature Alarm Threshold
			(in degree celsius) for the requested port
			-----------------------------
			ommp82PlusInterfaceNumber:
			1 to 8 - CLIENT-1 to CLIENT-8
			-----------------------------
			Values: 
			eg: 5 
			-----------------------------" 
		::= { ommp82PlusConfigurationEntry 183 }
		
	ommp82PlusSfpHighTemperatureWarningThreshold OBJECT-TYPE
		SYNTAX DisplayString
		MAX-ACCESS read-write
		STATUS current
		DESCRIPTION
			"Set or Get High Temperature Warning Threshold
			(in degree celsius) for the requested port
			-----------------------------
			ommp82PlusInterfaceNumber:
			1 to 8 - CLIENT-1 to CLIENT-8
			-----------------------------
			Values: 
			eg: 60 
			-----------------------------"
		::= { ommp82PlusConfigurationEntry 184 }
		
	ommp82PlusSfpLowTemperatureWarningThreshold OBJECT-TYPE
		SYNTAX DisplayString
		MAX-ACCESS read-write
		STATUS current
		DESCRIPTION
			"Set or Get Low Temperature Warning Threshold
			(in degree celsius) for the requested port
			-----------------------------
			ommp82PlusInterfaceNumber:
			1 to 8 - CLIENT-1 to CLIENT-8
			-----------------------------
			Values: 
			eg: 10 
			-----------------------------"
		::= { ommp82PlusConfigurationEntry 185 }

	ommp82PlusSfpHighBiasCurrentAlarmThreshold OBJECT-TYPE
		SYNTAX DisplayString
		MAX-ACCESS read-write
		STATUS current
		DESCRIPTION
			"Set or Get High Bias Current Alarm Threshold
			(in milli ampere) for the requested port
			-----------------------------
			ommp82PlusInterfaceNumber:
			1 to 8 - CLIENT-1 to CLIENT-8
			-----------------------------
			Values:
			eg: 35.6
			-----------------------------"			
		::= { ommp82PlusConfigurationEntry 186 }
		
	ommp82PlusSfpLowBiasCurrentAlarmThreshold OBJECT-TYPE
		SYNTAX DisplayString
		MAX-ACCESS read-write
		STATUS current
		DESCRIPTION
			"Set or Get Low Bias Current Alarm Threshold
			(in milli ampere) for the requested port
			-----------------------------
			ommp82PlusInterfaceNumber:
			1 to 8 - CLIENT-1 to CLIENT-8
			-----------------------------
			Values:
			eg: 31.1
			-----------------------------"
		::= { ommp82PlusConfigurationEntry 187 }
		
	ommp82PlusSfpHighBiasCurrentWarningThreshold OBJECT-TYPE
		SYNTAX DisplayString
		MAX-ACCESS read-write
		STATUS current
		DESCRIPTION
			"Set or Get High Bias Current Warning Threshold
			(in milli ampere) for the requested port
			-----------------------------
			ommp82PlusInterfaceNumber:
			1 to 8 - CLIENT-1 to CLIENT-8
			-----------------------------
			Values:
			eg: 34.5
			-----------------------------"
		::= { ommp82PlusConfigurationEntry 188 }
		
	ommp82PlusSfpLowBiasCurrentWarningThreshold OBJECT-TYPE
		SYNTAX DisplayString
		MAX-ACCESS read-write
		STATUS current
		DESCRIPTION
			"Set or Get Low Bias Current Alarm Threshold
			(in milli ampere) for the requested port
			-----------------------------
			ommp82PlusInterfaceNumber:
			1 to 8 - CLIENT-1 to CLIENT-8
			-----------------------------
			Values:
			eg: 32.8
			-----------------------------"
		::= { ommp82PlusConfigurationEntry 189 }
		
	ommp82PlusSfpInputHighPowerAlarmThreshold OBJECT-TYPE
		SYNTAX DisplayString
		MAX-ACCESS read-write
		STATUS current
		DESCRIPTION
			"Set or Get Input High Power Alarm Threshold
			(in dbm) for the requested port
			-----------------------------
			ommp82PlusInterfaceNumber:
			1 to 8 - CLIENT-1 to CLIENT-8
			-----------------------------
			Values:
			eg: -9.1
			-----------------------------"
		::= { ommp82PlusConfigurationEntry 190 }

	ommp82PlusSfpInputLowPowerAlarmThreshold OBJECT-TYPE
		SYNTAX DisplayString
		MAX-ACCESS read-write
		STATUS current
		DESCRIPTION
			"Set or Get Input Low Power Alarm Threshold
			(in dbm) for the requested port
			-----------------------------
			ommp82PlusInterfaceNumber:
			1 to 8 - CLIENT-1 to CLIENT-8
			-----------------------------
			Values:
			eg: -35.6
			-----------------------------"
		::= { ommp82PlusConfigurationEntry 191 }
		
	ommp82PlusSfpInputHighPowerWarningThreshold OBJECT-TYPE
		SYNTAX DisplayString
		MAX-ACCESS read-write
		STATUS current
		DESCRIPTION
			"Set or Get Input High Power Warning Threshold
			(in dbm) for the requested port
			-----------------------------
			ommp82PlusInterfaceNumber:
			1 to 8 - CLIENT-1 to CLIENT-8
			-----------------------------
			Values:
			eg: -11.2
			-----------------------------"
		::= { ommp82PlusConfigurationEntry 192 }
		
	ommp82PlusSfpInputLowPowerWarningThreshold OBJECT-TYPE
		SYNTAX DisplayString
		MAX-ACCESS read-write
		STATUS current
		DESCRIPTION
			"Set or Get Input Low Power Warning Threshold
			(in dbm) for the requested port
			-----------------------------
			ommp82PlusInterfaceNumber:
			1 to 8 - CLIENT-1 to CLIENT-8
			-----------------------------
			Values:
			eg: -31.3
			-----------------------------"
		::= { ommp82PlusConfigurationEntry 193 }
		
	ommp82PlusSfpOutputHighPowerAlarmThreshold OBJECT-TYPE
		SYNTAX DisplayString
		MAX-ACCESS read-write
		STATUS current
		DESCRIPTION
			"Set or Get Output High Power Alarm Threshold
			(in dbm) for the requested port
			-----------------------------
			ommp82PlusInterfaceNumber:
			1 to 8 - CLIENT-1 to CLIENT-8
			-----------------------------
			Values:
			eg: +2.0
			-----------------------------"
		::= { ommp82PlusConfigurationEntry 194 }

	ommp82PlusSfpOutputLowPowerAlarmThreshold OBJECT-TYPE
		SYNTAX DisplayString
		MAX-ACCESS read-write
		STATUS current
		DESCRIPTION
			"Set or Get Output Low Power Alarm Threshold
			(in dbm) for the requested port
			-----------------------------
			ommp82PlusInterfaceNumber:
			1 to 8 - CLIENT-1 to CLIENT-8
			-----------------------------
			Values:
			eg: -3.5
			-----------------------------"
		::= { ommp82PlusConfigurationEntry 195 }
		
	ommp82PlusSfpOutputHighPowerWarningThreshold OBJECT-TYPE
		SYNTAX DisplayString
		MAX-ACCESS read-write
		STATUS current
		DESCRIPTION
			"Set or Get Output High Power Warning Threshold
			(in dbm) for the requested port
			-----------------------------
			ommp82PlusInterfaceNumber:
			1 to 8 - CLIENT-1 to CLIENT-8
			-----------------------------
			Values:
			eg: +1.3
			-----------------------------"
		::= { ommp82PlusConfigurationEntry 196 }
		
	ommp82PlusSfpOutputLowPowerWarningThreshold OBJECT-TYPE
		SYNTAX DisplayString
		MAX-ACCESS read-write
		STATUS current
		DESCRIPTION
			"Set or Get Output Low Power Warning Threshold
			(in dbm) for the requested port
			-----------------------------
			ommp82PlusInterfaceNumber:
			1 to 8 - CLIENT-1 to CLIENT-8
			-----------------------------
			Values:
			eg: -2.5
			-----------------------------"
		::= { ommp82PlusConfigurationEntry 197 }
		
	ommp82PlusSfpHighSupplyVoltageAlarmThreshold OBJECT-TYPE
		SYNTAX DisplayString
		MAX-ACCESS read-write
		STATUS current
		DESCRIPTION
			"Set or Get High Supply Voltage Alarm Threshold
			(in volts) for the requested port
			-----------------------------
			ommp82PlusInterfaceNumber:
			1 to 8 - CLIENT-1 to CLIENT-8
			-----------------------------
			Values:
			eg: +3.3
			-----------------------------"
		::= { ommp82PlusConfigurationEntry 198 }

	ommp82PlusSfpLowSupplyVoltageAlarmThreshold OBJECT-TYPE
		SYNTAX DisplayString
		MAX-ACCESS read-write
		STATUS current
		DESCRIPTION
			"Set or Get Low Supply Voltage Alarm Threshold
			(in volts) for the requested port
			-----------------------------
			ommp82PlusInterfaceNumber:
			1 to 8 - CLIENT-1 to CLIENT-8
			-----------------------------
			Values:
			eg: +3.0
			-----------------------------"
		::= { ommp82PlusConfigurationEntry 199 }
		
	ommp82PlusSfpHighSupplyVoltageWarningThreshold OBJECT-TYPE
		SYNTAX DisplayString
		MAX-ACCESS read-write
		STATUS current
		DESCRIPTION
			"Set or Get High Supply Voltage Warning Threshold
			(in volts) for the requested port
			-----------------------------
			ommp82PlusInterfaceNumber:
			1 to 8 - CLIENT-1 to CLIENT-8
			-----------------------------
			Values:
			eg: +3.2
			-----------------------------"
		::= { ommp82PlusConfigurationEntry 200 }
		
	ommp82PlusSfpLowSupplyVoltageWarningThreshold OBJECT-TYPE
		SYNTAX DisplayString
		MAX-ACCESS read-write
		STATUS current
		DESCRIPTION
			"Set or Get Low Supply Voltage Warning Threshold
			(in volts) for the requested port
			-----------------------------
			ommp82PlusInterfaceNumber:
			1 to 8 - CLIENT-1 to CLIENT-8
			-----------------------------
			Values:
			eg: +3.1
			-----------------------------"
		::= { ommp82PlusConfigurationEntry 201 }

	ommp82PlusXfpInputPowerFailureAlarmInhibit  OBJECT-TYPE
		SYNTAX  INTEGER
		MAX-ACCESS  read-write
		STATUS  current
		DESCRIPTION
			"Inhibits OMMP82-PLUS XFP Input Power Failure Alarm
			for the requested port
			-----------------------------
			ommp82PlusInterfaceNumber:
			9 - LINE-1
			10 - LINE-2
			-----------------------------
			Value:
			1 - Inhibit
			0 - Do Not Inhibit
			-----------------------------"
	::= { ommp82PlusConfigurationEntry 301 }

	ommp82PlusXfpOutputPowerFailureAlarmInhibit  OBJECT-TYPE
		SYNTAX  INTEGER
		MAX-ACCESS  read-write
		STATUS  current
		DESCRIPTION
			"Inhibits OMMP82-PLUS XFP Output Power Failure Alarm
			for the requested port
			-----------------------------
			ommp82PlusInterfaceNumber:
			9 - LINE-1
			10 - LINE-2
			-----------------------------
			Value:
			1 - Inhibit
			0 - Do Not Inhibit
			-----------------------------"
	::= { ommp82PlusConfigurationEntry 302 }

	ommp82PlusXfpHighTemperatureAlarmInhibit  OBJECT-TYPE
		SYNTAX  INTEGER
		MAX-ACCESS  read-write
		STATUS  current
		DESCRIPTION
			"Inhibits OMMP82-PLUS XFP High Temperature Alarm
			for the requested port
			-----------------------------
			ommp82PlusInterfaceNumber:
			9 - LINE-1
			10 - LINE-2
			-----------------------------
			Value:
			1 - Inhibit
			0 - Do Not Inhibit
			-----------------------------"
	::= { ommp82PlusConfigurationEntry 303 }

	ommp82PlusXfpLowTemperatureAlarmInhibit  OBJECT-TYPE
		SYNTAX  INTEGER
		MAX-ACCESS  read-write
		STATUS  current
		DESCRIPTION
			"Inhibits OMMP82-PLUS XFP Low Temperature Alarm
			for the requested port
			-----------------------------
			ommp82PlusInterfaceNumber:
			9 - LINE-1
			10 - LINE-2
			-----------------------------
			Value:
			1 - Inhibit
			0 - Do Not Inhibit
			-----------------------------"
	::= { ommp82PlusConfigurationEntry 304 }

	ommp82PlusXfpHighTemperatureWarningInhibit  OBJECT-TYPE
		SYNTAX  INTEGER
		MAX-ACCESS  read-write
		STATUS  current
		DESCRIPTION
			"Inhibits OMMP82-PLUS XFP High Temperature Warning
			for the requested port
			-----------------------------
			ommp82PlusInterfaceNumber:
			9 - LINE-1
			10 - LINE-2
			-----------------------------
			Value:
			1 - Inhibit
			0 - Do Not Inhibit
			-----------------------------"
	::= { ommp82PlusConfigurationEntry 305 }

	ommp82PlusXfpLowTemperatureWarningInhibit  OBJECT-TYPE
		SYNTAX  INTEGER
		MAX-ACCESS  read-write
		STATUS  current
		DESCRIPTION
			"Inhibits OMMP82-PLUS XFP Low Temperature Warning
			for the requested port
			-----------------------------
			ommp82PlusInterfaceNumber:
			9 - LINE-1
			10 - LINE-2
			-----------------------------
			Value:
			1 - Inhibit
			0 - Do Not Inhibit
			-----------------------------"
	::= { ommp82PlusConfigurationEntry 306 }

	ommp82PlusXfpHighBiasCurrentAlarmInhibit  OBJECT-TYPE
		SYNTAX  INTEGER
		MAX-ACCESS  read-write
		STATUS  current
		DESCRIPTION
			"Inhibits OMMP82-PLUS XFP High Bias Current Alarm
			for the requested port
			-----------------------------
			ommp82PlusInterfaceNumber:
			9 - LINE-1
			10 - LINE-2
			-----------------------------
			Value:
			1 - Inhibit
			0 - Do Not Inhibit
			-----------------------------"
	::= { ommp82PlusConfigurationEntry 307 }

	ommp82PlusXfpLowBiasCurrentAlarmInhibit  OBJECT-TYPE
		SYNTAX  INTEGER
		MAX-ACCESS  read-write
		STATUS  current
		DESCRIPTION
			"Inhibits OMMP82-PLUS XFP Low Bias Current Alarm
			for the requested port
			-----------------------------
			ommp82PlusInterfaceNumber:
			9 - LINE-1
			10 - LINE-2
			-----------------------------
			Value:
			1 - Inhibit
			0 - Do Not Inhibit
			-----------------------------"
	::= { ommp82PlusConfigurationEntry 308 }

	ommp82PlusXfpHighBiasCurrentWarningInhibit  OBJECT-TYPE
		SYNTAX  INTEGER
		MAX-ACCESS  read-write
		STATUS  current
		DESCRIPTION
			"Inhibits OMMP82-PLUS XFP High Bias Current Warning
			for the requested port
			-----------------------------
			ommp82PlusInterfaceNumber:
			9 - LINE-1
			10 - LINE-2
			-----------------------------
			Value:
			1 - Inhibit
			0 - Do Not Inhibit
			-----------------------------"
	::= { ommp82PlusConfigurationEntry 309 }

	ommp82PlusXfpLowBiasCurrentWarningInhibit  OBJECT-TYPE
		SYNTAX  INTEGER
		MAX-ACCESS  read-write
		STATUS  current
		DESCRIPTION
			"Inhibits OMMP82-PLUS XFP Low Bias Current Warning
			for the requested port
			-----------------------------
			ommp82PlusInterfaceNumber:
			9 - LINE-1
			10 - LINE-2
			-----------------------------
			Value:
			1 - Inhibit
			0 - Do Not Inhibit
			-----------------------------"
	::= { ommp82PlusConfigurationEntry 310 }

	ommp82PlusXfpInputHighPowerAlarmInhibit  OBJECT-TYPE
		SYNTAX  INTEGER
		MAX-ACCESS  read-write
		STATUS  current
		DESCRIPTION
			"Inhibits OMMP82-PLUS XFP Input High Power Alarm
			for the requested port
			-----------------------------
			ommp82PlusInterfaceNumber:
			9 - LINE-1
			10 - LINE-2
			-----------------------------
			Value:
			1 - Inhibit
			0 - Do Not Inhibit
			-----------------------------"
	::= { ommp82PlusConfigurationEntry 311 }

	ommp82PlusXfpInputLowPowerAlarmInhibit  OBJECT-TYPE
		SYNTAX  INTEGER
		MAX-ACCESS  read-write
		STATUS  current
		DESCRIPTION
			"Inhibits OMMP82-PLUS XFP Input Low Power Alarm
			for the requested port
			-----------------------------
			ommp82PlusInterfaceNumber:
			9 - LINE-1
			10 - LINE-2
			-----------------------------
			Value:
			1 - Inhibit
			0 - Do Not Inhibit
			-----------------------------"
	::= { ommp82PlusConfigurationEntry 312 }

	ommp82PlusXfpInputHighPowerWarningInhibit  OBJECT-TYPE
		SYNTAX  INTEGER
		MAX-ACCESS  read-write
		STATUS  current
		DESCRIPTION
			"Inhibits OMMP82-PLUS XFP Input High Power Warning
			for the requested port
			-----------------------------
			ommp82PlusInterfaceNumber:
			9 - LINE-1
			10 - LINE-2
			-----------------------------
			Value:
			1 - Inhibit
			0 - Do Not Inhibit
			-----------------------------"
	::= { ommp82PlusConfigurationEntry 313 }

	ommp82PlusXfpInputLowPowerWarningInhibit  OBJECT-TYPE
		SYNTAX  INTEGER
		MAX-ACCESS  read-write
		STATUS  current
		DESCRIPTION
			"Inhibits OMMP82-PLUS XFP Input Low Power Warning
			for the requested port
			-----------------------------
			ommp82PlusInterfaceNumber:
			9 - LINE-1
			10 - LINE-2
			-----------------------------
			Value:
			1 - Inhibit
			0 - Do Not Inhibit
			-----------------------------"
	::= { ommp82PlusConfigurationEntry 314 }

	ommp82PlusXfpOutputHighPowerAlarmInhibit  OBJECT-TYPE
		SYNTAX  INTEGER
		MAX-ACCESS  read-write
		STATUS  current
		DESCRIPTION
			"Inhibits OMMP82-PLUS XFP Output High Power Alarm
			for the requested port
			-----------------------------
			ommp82PlusInterfaceNumber:
			9 - LINE-1
			10 - LINE-2
			-----------------------------
			Value:
			1 - Inhibit
			0 - Do Not Inhibit
			-----------------------------"
	::= { ommp82PlusConfigurationEntry 315 }

	ommp82PlusXfpOutputLowPowerAlarmInhibit  OBJECT-TYPE
		SYNTAX  INTEGER
		MAX-ACCESS  read-write
		STATUS  current
		DESCRIPTION
			"Inhibits OMMP82-PLUS XFP Output Low Power Alarm
			for the requested port
			-----------------------------
			ommp82PlusInterfaceNumber:
			9 - LINE-1
			10 - LINE-2
			-----------------------------
			Value:
			1 - Inhibit
			0 - Do Not Inhibit
			-----------------------------"
	::= { ommp82PlusConfigurationEntry 316 }

	ommp82PlusXfpOutputHighPowerWarningInhibit  OBJECT-TYPE
		SYNTAX  INTEGER
		MAX-ACCESS  read-write
		STATUS  current
		DESCRIPTION
			"Inhibits OMMP82-PLUS XFP Output High Power Warning
			for the requested port
			-----------------------------
			ommp82PlusInterfaceNumber:
			9 - LINE-1
			10 - LINE-2
			-----------------------------
			Value:
			1 - Inhibit
			0 - Do Not Inhibit
			-----------------------------"
	::= { ommp82PlusConfigurationEntry 317 }

	ommp82PlusXfpOutputLowPowerWarningInhibit  OBJECT-TYPE
		SYNTAX  INTEGER
		MAX-ACCESS  read-write
		STATUS  current
		DESCRIPTION
			"Inhibits OMMP82-PLUS XFP Output Low Power Warning
			for the requested port
			-----------------------------
			ommp82PlusInterfaceNumber:
			9 - LINE-1
			10 - LINE-2
			-----------------------------
			Value:
			1 - Inhibit
			0 - Do Not Inhibit
			-----------------------------"
	::= { ommp82PlusConfigurationEntry 318 }

	ommp82PlusXfpHighSupplyVoltageAlarmInhibit  OBJECT-TYPE
		SYNTAX  INTEGER
		MAX-ACCESS  read-write
		STATUS  current
		DESCRIPTION
			"Inhibits OMMP82-PLUS XFP High Supply Voltage Alarm
			for the requested port
			-----------------------------
			ommp82PlusInterfaceNumber:
			9 - LINE-1
			10 - LINE-2
			-----------------------------
			Value:
			1 - Inhibit
			0 - Do Not Inhibit
			-----------------------------"
	::= { ommp82PlusConfigurationEntry 319 }

	ommp82PlusXfpLowSupplyVoltageAlarmInhibit  OBJECT-TYPE
		SYNTAX  INTEGER
		MAX-ACCESS  read-write
		STATUS  current
		DESCRIPTION
			"Inhibits OMMP82-PLUS XFP Low Supply Voltage Alarm
			for the requested port
			-----------------------------
			ommp82PlusInterfaceNumber:
			9 - LINE-1
			10 - LINE-2
			-----------------------------
			Value:
			1 - Inhibit
			0 - Do Not Inhibit
			-----------------------------"
	::= { ommp82PlusConfigurationEntry 320 }

	ommp82PlusXfpHighSupplyVoltageWarningInhibit  OBJECT-TYPE
		SYNTAX  INTEGER
		MAX-ACCESS  read-write
		STATUS  current
		DESCRIPTION
			"Inhibits OMMP82-PLUS XFP High Supply Voltage Warning
			for the requested port
			-----------------------------
			ommp82PlusInterfaceNumber:
			9 - LINE-1
			10 - LINE-2
			-----------------------------
			Value:
			1 - Inhibit
			0 - Do Not Inhibit
			-----------------------------"
	::= { ommp82PlusConfigurationEntry 321 }

	ommp82PlusXfpLowSupplyVoltageWarningInhibit  OBJECT-TYPE
		SYNTAX  INTEGER
		MAX-ACCESS  read-write
		STATUS  current
		DESCRIPTION
			"Inhibits OMMP82-PLUS XFP Low Supply Voltage Warning
			for the requested port
			-----------------------------
			ommp82PlusInterfaceNumber:
			9 - LINE-1
			10 - LINE-2
			-----------------------------
			Value:
			1 - Inhibit
			0 - Do Not Inhibit
			-----------------------------"
	::= { ommp82PlusConfigurationEntry 322 }

	ommp82PlusXfpPresenceAbsenceNotificationInhibit  OBJECT-TYPE
		SYNTAX  INTEGER
		MAX-ACCESS  read-write
		STATUS  current
		DESCRIPTION
			"Inhibits OMMP82-PLUS XFP Presence Absence Notification
			for the requested port
			-----------------------------
			ommp82PlusInterfaceNumber:
			9 - LINE-1
			10 - LINE-2
			-----------------------------
			Value:
			1 - Inhibit
			0 - Do Not Inhibit
			-----------------------------"
	::= { ommp82PlusConfigurationEntry 323 }

	ommp82PlusSfpInputPowerFailureAlarmInhibit  OBJECT-TYPE
		SYNTAX  INTEGER
		MAX-ACCESS  read-write
		STATUS  current
		DESCRIPTION
			"Inhibits OMMP82-PLUS SFP Input Power Failure Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 341 }

	ommp82PlusSfpOutputPowerFailureAlarmInhibit  OBJECT-TYPE
		SYNTAX  INTEGER
		MAX-ACCESS  read-write
		STATUS  current
		DESCRIPTION
			"Inhibits OMMP82-PLUS SFP Output Power Failure Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 342 }

	ommp82PlusSfpHighTemperatureAlarmInhibit  OBJECT-TYPE
		SYNTAX  INTEGER
		MAX-ACCESS  read-write
		STATUS  current
		DESCRIPTION
			"Inhibits OMMP82-PLUS SFP High Temperature Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 343 }

	ommp82PlusSfpLowTemperatureAlarmInhibit  OBJECT-TYPE
		SYNTAX  INTEGER
		MAX-ACCESS  read-write
		STATUS  current
		DESCRIPTION
			"Inhibits OMMP82-PLUS SFP Low Temperature Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 344 }

	ommp82PlusSfpHighTemperatureWarningInhibit  OBJECT-TYPE
		SYNTAX  INTEGER
		MAX-ACCESS  read-write
		STATUS  current
		DESCRIPTION
			"Inhibits OMMP82-PLUS SFP High Temperature Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 345 }

	ommp82PlusSfpLowTemperatureWarningInhibit  OBJECT-TYPE
		SYNTAX  INTEGER
		MAX-ACCESS  read-write
		STATUS  current
		DESCRIPTION
			"Inhibits OMMP82-PLUS SFP Low Temperature Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 346 }

	ommp82PlusSfpHighBiasCurrentAlarmInhibit  OBJECT-TYPE
		SYNTAX  INTEGER
		MAX-ACCESS  read-write
		STATUS  current
		DESCRIPTION
			"Inhibits OMMP82-PLUS SFP High Bias Current Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 347 }

	ommp82PlusSfpLowBiasCurrentAlarmInhibit  OBJECT-TYPE
		SYNTAX  INTEGER
		MAX-ACCESS  read-write
		STATUS  current
		DESCRIPTION
			"Inhibits OMMP82-PLUS SFP Low Bias Current Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 348 }

	ommp82PlusSfpHighBiasCurrentWarningInhibit  OBJECT-TYPE
		SYNTAX  INTEGER
		MAX-ACCESS  read-write
		STATUS  current
		DESCRIPTION
			"Inhibits OMMP82-PLUS SFP High Bias Current Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 349 }

	ommp82PlusSfpLowBiasCurrentWarningInhibit  OBJECT-TYPE
		SYNTAX  INTEGER
		MAX-ACCESS  read-write
		STATUS  current
		DESCRIPTION
			"Inhibits OMMP82-PLUS SFP Low Bias Current Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 350 }

	ommp82PlusSfpInputHighPowerAlarmInhibit  OBJECT-TYPE
		SYNTAX  INTEGER
		MAX-ACCESS  read-write
		STATUS  current
		DESCRIPTION
			"Inhibits OMMP82-PLUS SFP Input High Power Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 351 }

	ommp82PlusSfpInputLowPowerAlarmInhibit  OBJECT-TYPE
		SYNTAX  INTEGER
		MAX-ACCESS  read-write
		STATUS  current
		DESCRIPTION
			"Inhibits OMMP82-PLUS SFP Input Low Power Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 352 }

	ommp82PlusSfpInputHighPowerWarningInhibit  OBJECT-TYPE
		SYNTAX  INTEGER
		MAX-ACCESS  read-write
		STATUS  current
		DESCRIPTION
			"Inhibits OMMP82-PLUS SFP Input High Power Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 353 }

	ommp82PlusSfpInputLowPowerWarningInhibit  OBJECT-TYPE
		SYNTAX  INTEGER
		MAX-ACCESS  read-write
		STATUS  current
		DESCRIPTION
			"Inhibits OMMP82-PLUS SFP Input Low Power Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 354 }

	ommp82PlusSfpOutputHighPowerAlarmInhibit  OBJECT-TYPE
		SYNTAX  INTEGER
		MAX-ACCESS  read-write
		STATUS  current
		DESCRIPTION
			"Inhibits OMMP82-PLUS SFP Output High Power Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 355 }

	ommp82PlusSfpOutputLowPowerAlarmInhibit  OBJECT-TYPE
		SYNTAX  INTEGER
		MAX-ACCESS  read-write
		STATUS  current
		DESCRIPTION
			"Inhibits OMMP82-PLUS SFP Output Low Power Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 356 }

	ommp82PlusSfpOutputHighPowerWarningInhibit  OBJECT-TYPE
		SYNTAX  INTEGER
		MAX-ACCESS  read-write
		STATUS  current
		DESCRIPTION
			"Inhibits OMMP82-PLUS SFP Output High Power Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 357 }

	ommp82PlusSfpOutputLowPowerWarningInhibit  OBJECT-TYPE
		SYNTAX  INTEGER
		MAX-ACCESS  read-write
		STATUS  current
		DESCRIPTION
			"Inhibits OMMP82-PLUS SFP Output Low Power Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 358 }

	ommp82PlusSfpHighSupplyVoltageAlarmInhibit  OBJECT-TYPE
		SYNTAX  INTEGER
		MAX-ACCESS  read-write
		STATUS  current
		DESCRIPTION
			"Inhibits OMMP82-PLUS SFP High Supply Voltage Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 359 }

	ommp82PlusSfpLowSupplyVoltageAlarmInhibit  OBJECT-TYPE
		SYNTAX  INTEGER
		MAX-ACCESS  read-write
		STATUS  current
		DESCRIPTION
			"Inhibits OMMP82-PLUS SFP Low Supply Voltage Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 360 }

	ommp82PlusSfpHighSupplyVoltageWarningInhibit  OBJECT-TYPE
		SYNTAX  INTEGER
		MAX-ACCESS  read-write
		STATUS  current
		DESCRIPTION
			"Inhibits OMMP82-PLUS SFP High Supply Voltage Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 361 }

	ommp82PlusSfpLowSupplyVoltageWarningInhibit  OBJECT-TYPE
		SYNTAX  INTEGER
		MAX-ACCESS  read-write
		STATUS  current
		DESCRIPTION
			"Inhibits OMMP82-PLUS SFP Low Supply Voltage Warning
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 362 }

	ommp82PlusSfpPresenceAbsenceNotificationInhibit  OBJECT-TYPE
		SYNTAX  INTEGER
		MAX-ACCESS  read-write
		STATUS  current
		DESCRIPTION
			"Inhibits OMMP82-PLUS SFP Presence Absence Notification
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 363 }

	ommp82PlusSfpTransmitFaultPresenceAlarmInhibit  OBJECT-TYPE
		SYNTAX  INTEGER
		MAX-ACCESS  read-write
		STATUS  current
		DESCRIPTION
			"Inhibits OMMP82-PLUS SFP Transmit Fault Presence Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 364 }

	ommp82PlusOtuLossOfSignalAlarmInhibit  OBJECT-TYPE
		SYNTAX  INTEGER
		MAX-ACCESS  read-write
		STATUS  current
		DESCRIPTION
			"Inhibits OMMP82-PLUS OTU Loss Of Signal Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 381 }

	ommp82PlusOtuLossOfFrameAlarmInhibit  OBJECT-TYPE
		SYNTAX  INTEGER
		MAX-ACCESS  read-write
		STATUS  current
		DESCRIPTION
			"Inhibits OMMP82-PLUS OTU Loss Of Frame Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 382 }

	ommp82PlusOtuOutOfFrameAlarmInhibit  OBJECT-TYPE
		SYNTAX  INTEGER
		MAX-ACCESS  read-write
		STATUS  current
		DESCRIPTION
			"Inhibits OMMP82-PLUS OTU Out Of Frame Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 383 }

	ommp82PlusOtuLossOfMultiFrameAlarmInhibit  OBJECT-TYPE
		SYNTAX  INTEGER
		MAX-ACCESS  read-write
		STATUS  current
		DESCRIPTION
			"Inhibits OMMP82-PLUS OTU Loss Of Multi Frame Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 384 }

	ommp82PlusOtuOutOfMultiFrameAlarmInhibit  OBJECT-TYPE
		SYNTAX  INTEGER
		MAX-ACCESS  read-write
		STATUS  current
		DESCRIPTION
			"Inhibits OMMP82-PLUS OTU Out Of Multi Frame Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 385 }

	ommp82PlusOtuSignalFailAlarmInhibit  OBJECT-TYPE
		SYNTAX  INTEGER
		MAX-ACCESS  read-write
		STATUS  current
		DESCRIPTION
			"Inhibits OMMP82-PLUS OTU Signal Fail Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 386 }

	ommp82PlusOtuSignalDegradeAlarmInhibit  OBJECT-TYPE
		SYNTAX  INTEGER
		MAX-ACCESS  read-write
		STATUS  current
		DESCRIPTION
			"Inhibits OMMP82-PLUS OTU Signal Degrade Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 387 }

	ommp82PlusOtuAlarmIndicationSignalAlarmInhibit  OBJECT-TYPE
		SYNTAX  INTEGER
		MAX-ACCESS  read-write
		STATUS  current
		DESCRIPTION
			"Inhibits OMMP82-PLUS OTU Alarm Indication Signal Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 388 }

	ommp82PlusOtuIncomingAlignmentErrorAlarmInhibit  OBJECT-TYPE
		SYNTAX  INTEGER
		MAX-ACCESS  read-write
		STATUS  current
		DESCRIPTION
			"Inhibits OMMP82-PLUS OTU Incoming Alignment Error Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 389 }

	ommp82PlusOtuTraceIdentifierMismatchAlarmInhibit  OBJECT-TYPE
		SYNTAX  INTEGER
		MAX-ACCESS  read-write
		STATUS  current
		DESCRIPTION
			"Inhibits OMMP82-PLUS OTU Trace Identifier Mismatch Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 390 }

	ommp82PlusOtuBackwardIncomingAlignmentErrorAlarmInhibit  OBJECT-TYPE
		SYNTAX  INTEGER
		MAX-ACCESS  read-write
		STATUS  current
		DESCRIPTION
			"Inhibits OMMP82-PLUS OTU Backward Incoming Alignment Error Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 391 }

	ommp82PlusOtuBackwardDefectIndicationAlarmInhibit  OBJECT-TYPE
		SYNTAX  INTEGER
		MAX-ACCESS  read-write
		STATUS  current
		DESCRIPTION
			"Inhibits OMMP82-PLUS OTU Backward Defect Indication Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 392 }

	ommp82PlusOduSignalFailAlarmInhibit  OBJECT-TYPE
		SYNTAX  INTEGER
		MAX-ACCESS  read-write
		STATUS  current
		DESCRIPTION
			"Inhibits OMMP82-PLUS ODU Signal Fail Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 411 }

	ommp82PlusOduSignalDegradeAlarmInhibit  OBJECT-TYPE
		SYNTAX  INTEGER
		MAX-ACCESS  read-write
		STATUS  current
		DESCRIPTION
			"Inhibits OMMP82-PLUS ODU Signal Degrade Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 412 }

	ommp82PlusOduAlarmIndicationSignalAlarmInhibit  OBJECT-TYPE
		SYNTAX  INTEGER
		MAX-ACCESS  read-write
		STATUS  current
		DESCRIPTION
			"Inhibits OMMP82-PLUS ODU Alarm Indication Signal Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 413 }

	ommp82PlusOduTcm1IncomingAlignmentErrorAlarmInhibit  OBJECT-TYPE
		SYNTAX  INTEGER
		MAX-ACCESS  read-write
		STATUS  current
		DESCRIPTION
			"Inhibits OMMP82-PLUS ODU TCM1 Incoming Alignment Error
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 414 }

	ommp82PlusOduTcm2IncomingAlignmentErrorAlarmInhibit  OBJECT-TYPE
		SYNTAX  INTEGER
		MAX-ACCESS  read-write
		STATUS  current
		DESCRIPTION
			"Inhibits OMMP82-PLUS ODU TCM2 Incoming Alignment Error
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 415 }

	ommp82PlusOduTcm3IncomingAlignmentErrorAlarmInhibit  OBJECT-TYPE
		SYNTAX  INTEGER
		MAX-ACCESS  read-write
		STATUS  current
		DESCRIPTION
			"Inhibits OMMP82-PLUS ODU TCM3 Incoming Alignment Error
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 416 }

	ommp82PlusOduTcm4IncomingAlignmentErrorAlarmInhibit  OBJECT-TYPE
		SYNTAX  INTEGER
		MAX-ACCESS  read-write
		STATUS  current
		DESCRIPTION
			"Inhibits OMMP82-PLUS ODU TCM4 Incoming Alignment Error
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 417 }

	ommp82PlusOduTcm5IncomingAlignmentErrorAlarmInhibit  OBJECT-TYPE
		SYNTAX  INTEGER
		MAX-ACCESS  read-write
		STATUS  current
		DESCRIPTION
			"Inhibits OMMP82-PLUS ODU TCM5 Incoming Alignment Error
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 418 }

	ommp82PlusOduTcm6IncomingAlignmentErrorAlarmInhibit  OBJECT-TYPE
		SYNTAX  INTEGER
		MAX-ACCESS  read-write
		STATUS  current
		DESCRIPTION
			"Inhibits OMMP82-PLUS ODU TCM6 Incoming Alignment Error
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 419 }

	ommp82PlusOduTraceIdentifierMismatchAlarmInhibit  OBJECT-TYPE
		SYNTAX  INTEGER
		MAX-ACCESS  read-write
		STATUS  current
		DESCRIPTION
			"Inhibits OMMP82-PLUS ODU Trace Identifier Mismatch
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 420 }

	ommp82PlusOduLockedDefectAlarmInhibit  OBJECT-TYPE
		SYNTAX  INTEGER
		MAX-ACCESS  read-write
		STATUS  current
		DESCRIPTION
			"Inhibits OMMP82-PLUS ODU Locked Defect Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 421 }

	ommp82PlusOduOpenConnectionIndicationAlarmInhibit  OBJECT-TYPE
		SYNTAX  INTEGER
		MAX-ACCESS  read-write
		STATUS  current
		DESCRIPTION
			"Inhibits OMMP82-PLUS ODU Open Connection Indication
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 422 }

	ommp82PlusOduBackwardDefectIndicationAlarmInhibit  OBJECT-TYPE
		SYNTAX  INTEGER
		MAX-ACCESS  read-write
		STATUS  current
		DESCRIPTION
			"Inhibits OMMP82-PLUS ODU Backward Defect Indication
			Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 423 }

	ommp82PlusOduTcm1BackwardIncomingAlignmentErrorAlarmInhibit  OBJECT-TYPE
		SYNTAX  INTEGER
		MAX-ACCESS  read-write
		STATUS  current
		DESCRIPTION
			"Inhibits OMMP82-PLUS ODU TCM1 Backward Incoming
			Alignment Error Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 424 }

	ommp82PlusOduTcm2BackwardIncomingAlignmentErrorAlarmInhibit  OBJECT-TYPE
		SYNTAX  INTEGER
		MAX-ACCESS  read-write
		STATUS  current
		DESCRIPTION
			"Inhibits OMMP82-PLUS ODU TCM2 Backward Incoming
			Alignment Error Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 425 }

	ommp82PlusOduTcm3BackwardIncomingAlignmentErrorAlarmInhibit  OBJECT-TYPE
		SYNTAX  INTEGER
		MAX-ACCESS  read-write
		STATUS  current
		DESCRIPTION
			"Inhibits OMMP82-PLUS ODU TCM3 Backward Incoming
			Alignment Error Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 426 }

	ommp82PlusOduTcm4BackwardIncomingAlignmentErrorAlarmInhibit  OBJECT-TYPE
		SYNTAX  INTEGER
		MAX-ACCESS  read-write
		STATUS  current
		DESCRIPTION
			"Inhibits OMMP82-PLUS ODU TCM4 Backward Incoming
			Alignment Error Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 427 }

	ommp82PlusOduTcm5BackwardIncomingAlignmentErrorAlarmInhibit  OBJECT-TYPE
		SYNTAX  INTEGER
		MAX-ACCESS  read-write
		STATUS  current
		DESCRIPTION
			"Inhibits OMMP82-PLUS ODU TCM5 Backward Incoming
			Alignment Error Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 428 }

	ommp82PlusOduTcm6BackwardIncomingAlignmentErrorAlarmInhibit  OBJECT-TYPE
		SYNTAX  INTEGER
		MAX-ACCESS  read-write
		STATUS  current
		DESCRIPTION
			"Inhibits OMMP82-PLUS ODU TCM6 Backward Incoming
			Alignment Error Alarm for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 429 }

	ommp82PlusOduLossOfFrameLossOfMultiframeAlarmInhibit  OBJECT-TYPE
		SYNTAX  INTEGER
		MAX-ACCESS  read-write
		STATUS  current
		DESCRIPTION
			"Inhibits OMMP82-PLUS ODU Loss Of Frame Loss Of
			Multiframe Alarm for the requested port
			-----------------------------
			ommp82PlusInterfaceNumber:
			1, 2, 3, 4 - Slice number
			-----------------------------
			Value:
			1 - Inhibit
			0 - Do Not Inhibit
			-----------------------------"
	::= { ommp82PlusConfigurationEntry 430 }

	ommp82PlusOpuPayloadMismatchAlarmInhibit  OBJECT-TYPE
		SYNTAX  INTEGER
		MAX-ACCESS  read-write
		STATUS  current
		DESCRIPTION
			"Inhibits OMMP82-PLUS OPU Payload Mismatch Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 435 }

	ommp82PlusOchLossOfPayloadAlarmInhibit  OBJECT-TYPE
		SYNTAX  INTEGER
		MAX-ACCESS  read-write
		STATUS  current
		DESCRIPTION
			"Inhibits OMMP82-PLUS OCH Loss Of Payload Alarm
			for the requested port
			-----------------------------
			ommp82PlusInterfaceNumber:
			1 to 8 - CLIENT-1 to CLIENT-8
			9 - LINE-1
			10 - LINE-2
			-----------------------------
			Value:
			1 - Inhibit
			0 - Do Not Inhibit
			-----------------------------"
	::= { ommp82PlusConfigurationEntry 436 }

	ommp82PlusSdhLossOfSignalAlarmInhibit  OBJECT-TYPE
		SYNTAX  INTEGER
		MAX-ACCESS  read-write
		STATUS  current
		DESCRIPTION
			"Inhibits OMMP82-PLUS SDH Loss Of Signal Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 441 }

	ommp82PlusSdhOutOfFrameAlarmInhibit  OBJECT-TYPE
		SYNTAX  INTEGER
		MAX-ACCESS  read-write
		STATUS  current
		DESCRIPTION
			"Inhibits OMMP82-PLUS SDH Out Of Frame Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 442 }

	ommp82PlusSdhLossOfFrameAlarmInhibit  OBJECT-TYPE
		SYNTAX  INTEGER
		MAX-ACCESS  read-write
		STATUS  current
		DESCRIPTION
			"Inhibits OMMP82-PLUS SDH Loss Of Frame Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 443 }

	ommp82PlusSdhRsAlarmIndicationSignalAlarmInhibit  OBJECT-TYPE
		SYNTAX  INTEGER
		MAX-ACCESS  read-write
		STATUS  current
		DESCRIPTION
			"Inhibits OMMP82-PLUS SDH Rs Alarm Indication Signal
			Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 444 }

	ommp82PlusSdhRsTraceIdentifierMismatchAlarmInhibit  OBJECT-TYPE
		SYNTAX  INTEGER
		MAX-ACCESS  read-write
		STATUS  current
		DESCRIPTION
			"Inhibits OMMP82-PLUS SDH Rs Trace Identifier
			Mismatch Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 445 }

	ommp82PlusSdhAuAlarmIndicationSignalAlarmInhibit  OBJECT-TYPE
		SYNTAX  INTEGER
		MAX-ACCESS  read-write
		STATUS  current
		DESCRIPTION
			"Inhibits OMMP82-PLUS SDH Au Alarm Indication Signal
			Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 446 }

	ommp82PlusSdhAuLossOfPointerAlarmInhibit  OBJECT-TYPE
		SYNTAX  INTEGER
		MAX-ACCESS  read-write
		STATUS  current
		DESCRIPTION
			"Inhibits OMMP82-PLUS SDH Au Loss Of Pointer Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 447 }

	ommp82PlusSdhMsAlarmIndicationSignalAlarmInhibit  OBJECT-TYPE
		SYNTAX  INTEGER
		MAX-ACCESS  read-write
		STATUS  current
		DESCRIPTION
			"Inhibits OMMP82-PLUS SDH Ms Alarm Indication Signal
			Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 448 }

	ommp82PlusSdhMsRemoteErrorIndicationAlarmInhibit  OBJECT-TYPE
		SYNTAX  INTEGER
		MAX-ACCESS  read-write
		STATUS  current
		DESCRIPTION
			"Inhibits OMMP82-PLUS SDH Ms Remote Error Indication
			Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 449 }

	ommp82PlusSdhMsRemoteDefectIndicationAlarmInhibit  OBJECT-TYPE
		SYNTAX  INTEGER
		MAX-ACCESS  read-write
		STATUS  current
		DESCRIPTION
			"Inhibits OMMP82-PLUS SDH Ms Remote Defect Indication
			Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 450 }

	ommp82PlusSdhMsRemoteFailureIndicationAlarmInhibit  OBJECT-TYPE
		SYNTAX  INTEGER
		MAX-ACCESS  read-write
		STATUS  current
		DESCRIPTION
			"Inhibits OMMP82-PLUS SDH Ms Remote Failure Indication
			Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 451 }

	ommp82PlusSdhMsB2ExcessiveErrorAlarmInhibit  OBJECT-TYPE
		SYNTAX  INTEGER
		MAX-ACCESS  read-write
		STATUS  current
		DESCRIPTION
			"Inhibits OMMP82-PLUS SDH Ms B2 Signal Fail Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 452 }

	ommp82PlusSdhMsB2SignalDegradeAlarmInhibit  OBJECT-TYPE
		SYNTAX  INTEGER
		MAX-ACCESS  read-write
		STATUS  current
		DESCRIPTION
			"Inhibits OMMP82-PLUS SDH Ms B2 Signal Degrade Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 453 }

	ommp82PlusSdhLossOfSequenceSynchronisationAlarmInhibit  OBJECT-TYPE
		SYNTAX  INTEGER
		MAX-ACCESS  read-write
		STATUS  current
		DESCRIPTION
			"Inhibits OMMP82-PLUS SDH Loss Of Sequence 
			Synchronisation Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 454 }

	ommp82PlusSdhLowerOrderPathPayloadLabelMismatchAlarmInhibit  OBJECT-TYPE
		SYNTAX  INTEGER
		MAX-ACCESS  read-write
		STATUS  current
		DESCRIPTION
			"Inhibits OMMP82-PLUS SDH Lower Order Path Payload
			Label Mismatch Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 455 }

	ommp82PlusSdhLowerOrderPathUnequippedAlarmInhibit  OBJECT-TYPE
		SYNTAX  INTEGER
		MAX-ACCESS  read-write
		STATUS  current
		DESCRIPTION
			"Inhibits OMMP82-PLUS SDH Lower Order Path Unequipped
			Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 456 }

	ommp82PlusEthernetLossOfSignalAlarmInhibit  OBJECT-TYPE
		SYNTAX  INTEGER
		MAX-ACCESS  read-write
		STATUS  current
		DESCRIPTION
			"Inhibits OMMP82-PLUS Ethernet Loss Of Signal Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 471 }

	ommp82PlusEthernetLossOfSignalSyncAlarmInhibit  OBJECT-TYPE
		SYNTAX  INTEGER
		MAX-ACCESS  read-write
		STATUS  current
		DESCRIPTION
			"Inhibits OMMP82-PLUS Ethernet Loss Of Signal Sync Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 472 }

	ommp82PlusEthernetLinkFailureAlarmInhibit  OBJECT-TYPE
		SYNTAX  INTEGER
		MAX-ACCESS  read-write
		STATUS  current
		DESCRIPTION
			"Inhibits OMMP82-PLUS Ethernet Link Failure Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 473 }

	ommp82PlusEthernetAutoNegotiationAlarmInhibit  OBJECT-TYPE
		SYNTAX  INTEGER
		MAX-ACCESS  read-write
		STATUS  current
		DESCRIPTION
			"Inhibits OMMP82-PLUS Ethernet Auto Negotiation Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 474 }

	ommp82PlusEthernetFrameCheckSequenceAlarmInhibit  OBJECT-TYPE
		SYNTAX  INTEGER
		MAX-ACCESS  read-write
		STATUS  current
		DESCRIPTION
			"Inhibits OMMP82-PLUS Ethernet Frame Check Sequence Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 475 }

	ommp82PlusEthernetCarrierStatusAlarmInhibit  OBJECT-TYPE
		SYNTAX  INTEGER
		MAX-ACCESS  read-write
		STATUS  current
		DESCRIPTION
			"Inhibits OMMP82-PLUS Ethernet Carrier Status Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 476 }

	ommp82PlusEthernetHighBerAlarmInhibit  OBJECT-TYPE
		SYNTAX  INTEGER
		MAX-ACCESS  read-write
		STATUS  current
		DESCRIPTION
			"Inhibits OMMP82-PLUS Ethernet High Ber Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 477 }

	ommp82PlusEthernetLocalFaultAlarmInhibit  OBJECT-TYPE
		SYNTAX  INTEGER
		MAX-ACCESS  read-write
		STATUS  current
		DESCRIPTION
			"Inhibits OMMP82-PLUS Ethernet Local Fault Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 478 }

	ommp82PlusEthernetRemoteFaultAlarmInhibit  OBJECT-TYPE
		SYNTAX  INTEGER
		MAX-ACCESS  read-write
		STATUS  current
		DESCRIPTION
			"Inhibits OMMP82-PLUS Ethernet Remote Fault Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 479 }

	ommp82PlusFcTransmitDisparityInversionDefectAlarmInhibit  OBJECT-TYPE
		SYNTAX  INTEGER
		MAX-ACCESS  read-write
		STATUS  current
		DESCRIPTION
			"Inhibits OMMP82-PLUS FC Transmit Disparity Inversion 
			Defect Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 491 }

	ommp82PlusFcTransmitDigitalLossOfLinkDefectAlarmInhibit  OBJECT-TYPE
		SYNTAX  INTEGER
		MAX-ACCESS  read-write
		STATUS  current
		DESCRIPTION
			"Inhibits OMMP82-PLUS FC Transmit Digital Loss Of Link
			Defect Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 492 }

	ommp82PlusFcTrasnmitLossOfSynchronizationDefectAlarmInhibit  OBJECT-TYPE
		SYNTAX  INTEGER
		MAX-ACCESS  read-write
		STATUS  current
		DESCRIPTION
			"Inhibits OMMP82-PLUS FC Transmit Loss of 
			Synchronization Defect Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 493 }

	ommp82PlusFcReceiveDigitalLossOfLinkDefectAlarmInhibit  OBJECT-TYPE
		SYNTAX  INTEGER
		MAX-ACCESS  read-write
		STATUS  current
		DESCRIPTION
			"Inhibits OMMP82-PLUS FC Receive Digital Loss of 
			Link Defect Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 494 }

	ommp82PlusFcReceiveLossOfSynchronizationDefectAlarmInhibit  OBJECT-TYPE
		SYNTAX  INTEGER
		MAX-ACCESS  read-write
		STATUS  current
		DESCRIPTION
			"Inhibits OMMP82-PLUS FC Receive Loss Of Synchronization
			Defect Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 495 }

	ommp82PlusFcReceiveTransitionDetectDefectAlarmInhibit  OBJECT-TYPE
		SYNTAX  INTEGER
		MAX-ACCESS  read-write
		STATUS  current
		DESCRIPTION
			"Inhibits OMMP82-PLUS FC Receive Transition Detect 
			Defect Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 496 }

	ommp82PlusFcReceiveAnalogLossOfSignalDefectAlarmInhibit  OBJECT-TYPE
		SYNTAX  INTEGER
		MAX-ACCESS  read-write
		STATUS  current
		DESCRIPTION
			"Inhibits OMMP82-PLUS FC Receive Analog Loss Of Signal 
			Defect Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 497 }

	ommp82PlusFcReceiveLineCodeViolationDefectAlarmInhibit  OBJECT-TYPE
		SYNTAX  INTEGER
		MAX-ACCESS  read-write
		STATUS  current
		DESCRIPTION
			"Inhibits OMMP82-PLUS FC Receive Line Code Violation 
			Defect Alarm for the requested port
			-----------------------------
			ommp82PlusInterfaceNumber:
			1 to 8 - CLIENT-1 to CLIENT-8
			-----------------------------
			Value:
			1 - Inhibit
			0 - Do Not Inhibit
			-----------------------------"
	::= { ommp82PlusConfigurationEntry 498 }

	ommp82PlusGfpCsfSignalFailAlarmInhibit  OBJECT-TYPE
		SYNTAX  INTEGER
		MAX-ACCESS  read-write
		STATUS  current
		DESCRIPTION
			"Inhibits OMMP82-PLUS GFP Csf Signal Failure Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 511 }

	ommp82PlusGfpCsfLinkFailAlarmInhibit  OBJECT-TYPE
		SYNTAX  INTEGER
		MAX-ACCESS  read-write
		STATUS  current
		DESCRIPTION
			"Inhibits OMMP82-PLUS GFP Csf Link Failure Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 512 }

	ommp82PlusGfpCoreHeaderErrorAlarmInhibit  OBJECT-TYPE
		SYNTAX  INTEGER
		MAX-ACCESS  read-write
		STATUS  current
		DESCRIPTION
			"Inhibits OMMP82-PLUS GFP Core Header Error Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 513 }

	ommp82PlusGfpExtentionHeaderErrorAlarmInhibit  OBJECT-TYPE
		SYNTAX  INTEGER
		MAX-ACCESS  read-write
		STATUS  current
		DESCRIPTION
			"Inhibits OMMP82-PLUS GFP Extention Header Error Alarm
			for the requested port
			-----------------------------
			ommp82PlusInterfaceNumber:
			1 to 8 - CLIENT-1 to CLIENT-8
			-----------------------------
			Value:
			1 - Inhibit
			0 - Do Not Inhibit
			-----------------------------"
	::= { ommp82PlusConfigurationEntry 514 }

	ommp82PlusXfpInputPowerFailureAlarmSeverity OBJECT-TYPE
		SYNTAX  DisplayString
		MAX-ACCESS  read-write
		STATUS  current
		DESCRIPTION
			"Set or Get the alarm severity level of the
			OMMP82-PLUS XFP Input Power Failure Alarm   
			for requested port
			-----------------------------
			ommp82PlusInterfaceNumber:
			9 - LINE-1
			10 - LINE-2
			-----------------------------
			Value:
			critical
			major
			minor
			deferred
			---------------------------"
	::= { ommp82PlusConfigurationEntry 601 }

	ommp82PlusXfpOutputPowerFailureAlarmSeverity OBJECT-TYPE
		SYNTAX  DisplayString
		MAX-ACCESS  read-write
		STATUS  current
		DESCRIPTION
			"Set or Get the alarm severity level of the
			OMMP82-PLUS XFP Output Power Failure Alarm   
			for requested port
			-----------------------------
			ommp82PlusInterfaceNumber:
			9 - LINE-1
			10 - LINE-2
			-----------------------------
			Value:
			critical
			major
			minor
			deferred
			---------------------------"
	::= { ommp82PlusConfigurationEntry 602 }

	ommp82PlusXfpHighTemperatureAlarmSeverity OBJECT-TYPE
		SYNTAX  DisplayString
		MAX-ACCESS  read-write
		STATUS  current
		DESCRIPTION
			"Set or Get the alarm severity level of the
			OMMP82-PLUS XFP High Temperature Alarm   
			for requested port
			-----------------------------
			ommp82PlusInterfaceNumber:
			9 - LINE-1
			10 - LINE-2
			-----------------------------
			Value:
			critical
			major
			minor
			deferred
			---------------------------"
	::= { ommp82PlusConfigurationEntry 603 }

	ommp82PlusXfpLowTemperatureAlarmSeverity OBJECT-TYPE
		SYNTAX  DisplayString
		MAX-ACCESS  read-write
		STATUS  current
		DESCRIPTION
			"Set or Get the alarm severity level of the
			OMMP82-PLUS XFP Low Temperature Alarm   
			for requested port
			-----------------------------
			ommp82PlusInterfaceNumber:
			9 - LINE-1
			10 - LINE-2
			-----------------------------
			Value:
			critical
			major
			minor
			deferred
			---------------------------"
	::= { ommp82PlusConfigurationEntry 604 }

	ommp82PlusXfpHighTemperatureWarningSeverity OBJECT-TYPE
		SYNTAX  DisplayString
		MAX-ACCESS  read-write
		STATUS  current
		DESCRIPTION
			"Set or Get the alarm severity level of the
			OMMP82-PLUS XFP High Temperature Warning   
			for requested port
			-----------------------------
			ommp82PlusInterfaceNumber:
			9 - LINE-1
			10 - LINE-2
			-----------------------------
			Value:
			critical
			major
			minor
			deferred
			---------------------------"
	::= { ommp82PlusConfigurationEntry 605 }

	ommp82PlusXfpLowTemperatureWarningSeverity OBJECT-TYPE
		SYNTAX  DisplayString
		MAX-ACCESS  read-write
		STATUS  current
		DESCRIPTION
			"Set or Get the alarm severity level of the
			OMMP82-PLUS XFP Low Temperature Warning   
			for requested port
			-----------------------------
			ommp82PlusInterfaceNumber:
			9 - LINE-1
			10 - LINE-2
			-----------------------------
			Value:
			critical
			major
			minor
			deferred
			---------------------------"
	::= { ommp82PlusConfigurationEntry 606 }

	ommp82PlusXfpHighBiasCurrentAlarmSeverity OBJECT-TYPE
		SYNTAX  DisplayString
		MAX-ACCESS  read-write
		STATUS  current
		DESCRIPTION
			"Set or Get the alarm severity level of the
			OMMP82-PLUS XFP High Bias Current Alarm   
			for requested port
			-----------------------------
			ommp82PlusInterfaceNumber:
			9 - LINE-1
			10 - LINE-2
			-----------------------------
			Value:
			critical
			major
			minor
			deferred
			---------------------------"
	::= { ommp82PlusConfigurationEntry 607 }

	ommp82PlusXfpLowBiasCurrentAlarmSeverity OBJECT-TYPE
		SYNTAX  DisplayString
		MAX-ACCESS  read-write
		STATUS  current
		DESCRIPTION
			"Set or Get the alarm severity level of the
			OMMP82-PLUS XFP Low Bias Current Alarm   
			for requested port
			-----------------------------
			ommp82PlusInterfaceNumber:
			9 - LINE-1
			10 - LINE-2
			-----------------------------
			Value:
			critical
			major
			minor
			deferred
			---------------------------"
	::= { ommp82PlusConfigurationEntry 608 }

	ommp82PlusXfpHighBiasCurrentWarningSeverity OBJECT-TYPE
		SYNTAX  DisplayString
		MAX-ACCESS  read-write
		STATUS  current
		DESCRIPTION
			"Set or Get the alarm severity level of the
			OMMP82-PLUS XFP High Bias Current Warning   
			for requested port
			-----------------------------
			ommp82PlusInterfaceNumber:
			9 - LINE-1
			10 - LINE-2
			-----------------------------
			Value:
			critical
			major
			minor
			deferred
			---------------------------"
	::= { ommp82PlusConfigurationEntry 609 }

	ommp82PlusXfpLowBiasCurrentWarningSeverity OBJECT-TYPE
		SYNTAX  DisplayString
		MAX-ACCESS  read-write
		STATUS  current
		DESCRIPTION
			"Set or Get the alarm severity level of the
			OMMP82-PLUS XFP Low Bias Current Warning   
			for requested port
			-----------------------------
			ommp82PlusInterfaceNumber:
			9 - LINE-1
			10 - LINE-2
			-----------------------------
			Value:
			critical
			major
			minor
			deferred
			---------------------------"
	::= { ommp82PlusConfigurationEntry 610 }

	ommp82PlusXfpInputHighPowerAlarmSeverity OBJECT-TYPE
		SYNTAX  DisplayString
		MAX-ACCESS  read-write
		STATUS  current
		DESCRIPTION
			"Set or Get the alarm severity level of the
			OMMP82-PLUS XFP Input High Power Alarm   
			for requested port
			-----------------------------
			ommp82PlusInterfaceNumber:
			9 - LINE-1
			10 - LINE-2
			-----------------------------
			Value:
			critical
			major
			minor
			deferred
			---------------------------"
	::= { ommp82PlusConfigurationEntry 611 }

	ommp82PlusXfpInputLowPowerAlarmSeverity OBJECT-TYPE
		SYNTAX  DisplayString
		MAX-ACCESS  read-write
		STATUS  current
		DESCRIPTION
			"Set or Get the alarm severity level of the
			OMMP82-PLUS XFP Input Low Power Alarm   
			for requested port
			-----------------------------
			ommp82PlusInterfaceNumber:
			9 - LINE-1
			10 - LINE-2
			-----------------------------
			Value:
			critical
			major
			minor
			deferred
			---------------------------"
	::= { ommp82PlusConfigurationEntry 612 }

	ommp82PlusXfpInputHighPowerWarningSeverity OBJECT-TYPE
		SYNTAX  DisplayString
		MAX-ACCESS  read-write
		STATUS  current
		DESCRIPTION
			"Set or Get the alarm severity level of the
			OMMP82-PLUS XFP Input High Power Warning   
			for requested port
			-----------------------------
			ommp82PlusInterfaceNumber:
			9 - LINE-1
			10 - LINE-2
			-----------------------------
			Value:
			critical
			major
			minor
			deferred
			---------------------------"
	::= { ommp82PlusConfigurationEntry 613 }

	ommp82PlusXfpInputLowPowerWarningSeverity OBJECT-TYPE
		SYNTAX  DisplayString
		MAX-ACCESS  read-write
		STATUS  current
		DESCRIPTION
			"Set or Get the alarm severity level of the
			OMMP82-PLUS XFP Input Low Power Warning   
			for requested port
			-----------------------------
			ommp82PlusInterfaceNumber:
			9 - LINE-1
			10 - LINE-2
			-----------------------------
			Value:
			critical
			major
			minor
			deferred
			---------------------------"
	::= { ommp82PlusConfigurationEntry 614 }

	ommp82PlusXfpOutputHighPowerAlarmSeverity OBJECT-TYPE
		SYNTAX  DisplayString
		MAX-ACCESS  read-write
		STATUS  current
		DESCRIPTION
			"Set or Get the alarm severity level of the
			OMMP82-PLUS XFP Output High Power Alarm   
			for requested port
			-----------------------------
			ommp82PlusInterfaceNumber:
			9 - LINE-1
			10 - LINE-2
			-----------------------------
			Value:
			critical
			major
			minor
			deferred
			---------------------------"
	::= { ommp82PlusConfigurationEntry 615 }

	ommp82PlusXfpOutputLowPowerAlarmSeverity OBJECT-TYPE
		SYNTAX  DisplayString
		MAX-ACCESS  read-write
		STATUS  current
		DESCRIPTION
			"Set or Get the alarm severity level of the
			OMMP82-PLUS XFP Output Low Power Alarm   
			for requested port
			-----------------------------
			ommp82PlusInterfaceNumber:
			9 - LINE-1
			10 - LINE-2
			-----------------------------
			Value:
			critical
			major
			minor
			deferred
			---------------------------"
	::= { ommp82PlusConfigurationEntry 616 }

	ommp82PlusXfpOutputHighPowerWarningSeverity OBJECT-TYPE
		SYNTAX  DisplayString
		MAX-ACCESS  read-write
		STATUS  current
		DESCRIPTION
			"Set or Get the alarm severity level of the
			OMMP82-PLUS XFP Output High Power Warning   
			for requested port
			-----------------------------
			ommp82PlusInterfaceNumber:
			9 - LINE-1
			10 - LINE-2
			-----------------------------
			Value:
			critical
			major
			minor
			deferred
			---------------------------"
	::= { ommp82PlusConfigurationEntry 617 }

	ommp82PlusXfpOutputLowPowerWarningSeverity OBJECT-TYPE
		SYNTAX  DisplayString
		MAX-ACCESS  read-write
		STATUS  current
		DESCRIPTION
			"Set or Get the alarm severity level of the
			OMMP82-PLUS XFP Output Low Power Warning   
			for requested port
			-----------------------------
			ommp82PlusInterfaceNumber:
			9 - LINE-1
			10 - LINE-2
			-----------------------------
			Value:
			critical
			major
			minor
			deferred
			---------------------------"
	::= { ommp82PlusConfigurationEntry 618 }

	ommp82PlusXfpHighSupplyVoltageAlarmSeverity OBJECT-TYPE
		SYNTAX  DisplayString
		MAX-ACCESS  read-write
		STATUS  current
		DESCRIPTION
			"Set or Get the alarm severity level of the
			OMMP82-PLUS XFP High Supply Voltage Alarm   
			for requested port
			-----------------------------
			ommp82PlusInterfaceNumber:
			9 - LINE-1
			10 - LINE-2
			-----------------------------
			Value:
			critical
			major
			minor
			deferred
			---------------------------"
	::= { ommp82PlusConfigurationEntry 619 }

	ommp82PlusXfpLowSupplyVoltageAlarmSeverity OBJECT-TYPE
		SYNTAX  DisplayString
		MAX-ACCESS  read-write
		STATUS  current
		DESCRIPTION
			"Set or Get the alarm severity level of the
			OMMP82-PLUS XFP Low Supply Voltage Alarm   
			for requested port
			-----------------------------
			ommp82PlusInterfaceNumber:
			9 - LINE-1
			10 - LINE-2
			-----------------------------
			Value:
			critical
			major
			minor
			deferred
			---------------------------"
	::= { ommp82PlusConfigurationEntry 620 }

	ommp82PlusXfpHighSupplyVoltageWarningSeverity OBJECT-TYPE
		SYNTAX  DisplayString
		MAX-ACCESS  read-write
		STATUS  current
		DESCRIPTION
			"Set or Get the alarm severity level of the
			OMMP82-PLUS XFP High Supply Voltage Warning   
			for requested port
			-----------------------------
			ommp82PlusInterfaceNumber:
			9 - LINE-1
			10 - LINE-2
			-----------------------------
			Value:
			critical
			major
			minor
			deferred
			---------------------------"
	::= { ommp82PlusConfigurationEntry 621 }

	ommp82PlusXfpLowSupplyVoltageWarningSeverity OBJECT-TYPE
		SYNTAX  DisplayString
		MAX-ACCESS  read-write
		STATUS  current
		DESCRIPTION
			"Set or Get the alarm severity level of the
			OMMP82-PLUS XFP Low Supply Voltage Warning   
			for requested port
			-----------------------------
			ommp82PlusInterfaceNumber:
			9 - LINE-1
			10 - LINE-2
			-----------------------------
			Value:
			critical
			major
			minor
			deferred
			---------------------------"
	::= { ommp82PlusConfigurationEntry 622 }

	ommp82PlusXfpPresenceAbsenceNotificationSeverity OBJECT-TYPE
		SYNTAX  DisplayString
		MAX-ACCESS  read-write
		STATUS  current
		DESCRIPTION
			"Set or Get the alarm severity level of the
			OMMP82-PLUS XFP Presence Absence Notification   
			for requested port
			-----------------------------
			ommp82PlusInterfaceNumber:
			9 - LINE-1
			10 - LINE-2
			-----------------------------
			Value:
			critical
			major
			minor
			deferred
			---------------------------"
	::= { ommp82PlusConfigurationEntry 623 }

	ommp82PlusSfpInputPowerFailureAlarmSeverity OBJECT-TYPE
		SYNTAX  DisplayString
		MAX-ACCESS  read-write
		STATUS  current
		DESCRIPTION
			"Set or Get the alarm severity level of the
			OMMP82-PLUS SFP Input Power Failure Alarm   
			for requested port
			-----------------------------
			ommp82PlusInterfaceNumber:
			1 to 8 - CLIENT-1 to CLIENT-8
			-----------------------------
			Value:
			critical
			major
			minor
			deferred
			---------------------------"
	::= { ommp82PlusConfigurationEntry 641 }

	ommp82PlusSfpOutputPowerFailureAlarmSeverity OBJECT-TYPE
		SYNTAX  DisplayString
		MAX-ACCESS  read-write
		STATUS  current
		DESCRIPTION
			"Set or Get the alarm severity level of the
			OMMP82-PLUS SFP Output Power Failure Alarm   
			for requested port
			-----------------------------
			ommp82PlusInterfaceNumber:
			1 to 8 - CLIENT-1 to CLIENT-8
			-----------------------------
			Value:
			critical
			major
			minor
			deferred
			---------------------------"
	::= { ommp82PlusConfigurationEntry 642 }

	ommp82PlusSfpHighTemperatureAlarmSeverity OBJECT-TYPE
		SYNTAX  DisplayString
		MAX-ACCESS  read-write
		STATUS  current
		DESCRIPTION
			"Set or Get the alarm severity level of the
			OMMP82-PLUS SFP High Temperature Alarm   
			for requested port
			-----------------------------
			ommp82PlusInterfaceNumber:
			1 to 8 - CLIENT-1 to CLIENT-8
			-----------------------------
			Value:
			critical
			major
			minor
			deferred
			---------------------------"
	::= { ommp82PlusConfigurationEntry 643 }

	ommp82PlusSfpLowTemperatureAlarmSeverity OBJECT-TYPE
		SYNTAX  DisplayString
		MAX-ACCESS  read-write
		STATUS  current
		DESCRIPTION
			"Set or Get the alarm severity level of the
			OMMP82-PLUS SFP Low Temperature Alarm   
			for requested port
			-----------------------------
			ommp82PlusInterfaceNumber:
			1 to 8 - CLIENT-1 to CLIENT-8
			-----------------------------
			Value:
			critical
			major
			minor
			deferred
			---------------------------"
	::= { ommp82PlusConfigurationEntry 644 }

	ommp82PlusSfpHighTemperatureWarningSeverity OBJECT-TYPE
		SYNTAX  DisplayString
		MAX-ACCESS  read-write
		STATUS  current
		DESCRIPTION
			"Set or Get the alarm severity level of the
			OMMP82-PLUS SFP High Temperature Warning   
			for requested port
			-----------------------------
			ommp82PlusInterfaceNumber:
			1 to 8 - CLIENT-1 to CLIENT-8
			-----------------------------
			Value:
			critical
			major
			minor
			deferred
			---------------------------"
	::= { ommp82PlusConfigurationEntry 645 }

	ommp82PlusSfpLowTemperatureWarningSeverity OBJECT-TYPE
		SYNTAX  DisplayString
		MAX-ACCESS  read-write
		STATUS  current
		DESCRIPTION
			"Set or Get the alarm severity level of the
			OMMP82-PLUS SFP Low Temperature Warning   
			for requested port
			-----------------------------
			ommp82PlusInterfaceNumber:
			1 to 8 - CLIENT-1 to CLIENT-8
			-----------------------------
			Value:
			critical
			major
			minor
			deferred
			---------------------------"
	::= { ommp82PlusConfigurationEntry 646 }

	ommp82PlusSfpHighBiasCurrentAlarmSeverity OBJECT-TYPE
		SYNTAX  DisplayString
		MAX-ACCESS  read-write
		STATUS  current
		DESCRIPTION
			"Set or Get the alarm severity level of the
			OMMP82-PLUS SFP High Bias Current Alarm   
			for requested port
			-----------------------------
			ommp82PlusInterfaceNumber:
			1 to 8 - CLIENT-1 to CLIENT-8
			-----------------------------
			Value:
			critical
			major
			minor
			deferred
			---------------------------"
	::= { ommp82PlusConfigurationEntry 647 }

	ommp82PlusSfpLowBiasCurrentAlarmSeverity OBJECT-TYPE
		SYNTAX  DisplayString
		MAX-ACCESS  read-write
		STATUS  current
		DESCRIPTION
			"Set or Get the alarm severity level of the
			OMMP82-PLUS SFP Low Bias Current Alarm   
			for requested port
			-----------------------------
			ommp82PlusInterfaceNumber:
			1 to 8 - CLIENT-1 to CLIENT-8
			-----------------------------
			Value:
			critical
			major
			minor
			deferred
			---------------------------"
	::= { ommp82PlusConfigurationEntry 648 }

	ommp82PlusSfpHighBiasCurrentWarningSeverity OBJECT-TYPE
		SYNTAX  DisplayString
		MAX-ACCESS  read-write
		STATUS  current
		DESCRIPTION
			"Set or Get the alarm severity level of the
			OMMP82-PLUS SFP High Bias Current Warning   
			for requested port
			-----------------------------
			ommp82PlusInterfaceNumber:
			1 to 8 - CLIENT-1 to CLIENT-8
			-----------------------------
			Value:
			critical
			major
			minor
			deferred
			---------------------------"
	::= { ommp82PlusConfigurationEntry 649 }

	ommp82PlusSfpLowBiasCurrentWarningSeverity OBJECT-TYPE
		SYNTAX  DisplayString
		MAX-ACCESS  read-write
		STATUS  current
		DESCRIPTION
			"Set or Get the alarm severity level of the
			OMMP82-PLUS SFP Low Bias Current Warning   
			for requested port
			-----------------------------
			ommp82PlusInterfaceNumber:
			1 to 8 - CLIENT-1 to CLIENT-8
			-----------------------------
			Value:
			critical
			major
			minor
			deferred
			---------------------------"
	::= { ommp82PlusConfigurationEntry 650 }

	ommp82PlusSfpInputHighPowerAlarmSeverity OBJECT-TYPE
		SYNTAX  DisplayString
		MAX-ACCESS  read-write
		STATUS  current
		DESCRIPTION
			"Set or Get the alarm severity level of the
			OMMP82-PLUS SFP Input High Power Alarm   
			for requested port
			-----------------------------
			ommp82PlusInterfaceNumber:
			1 to 8 - CLIENT-1 to CLIENT-8
			-----------------------------
			Value:
			critical
			major
			minor
			deferred
			---------------------------"
	::= { ommp82PlusConfigurationEntry 651 }

	ommp82PlusSfpInputLowPowerAlarmSeverity OBJECT-TYPE
		SYNTAX  DisplayString
		MAX-ACCESS  read-write
		STATUS  current
		DESCRIPTION
			"Set or Get the alarm severity level of the
			OMMP82-PLUS SFP Input Low Power Alarm   
			for requested port
			-----------------------------
			ommp82PlusInterfaceNumber:
			1 to 8 - CLIENT-1 to CLIENT-8
			-----------------------------
			Value:
			critical
			major
			minor
			deferred
			---------------------------"
	::= { ommp82PlusConfigurationEntry 652 }

	ommp82PlusSfpInputHighPowerWarningSeverity OBJECT-TYPE
		SYNTAX  DisplayString
		MAX-ACCESS  read-write
		STATUS  current
		DESCRIPTION
			"Set or Get the alarm severity level of the
			OMMP82-PLUS SFP Input High Power Warning   
			for requested port
			-----------------------------
			ommp82PlusInterfaceNumber:
			1 to 8 - CLIENT-1 to CLIENT-8
			-----------------------------
			Value:
			critical
			major
			minor
			deferred
			---------------------------"
	::= { ommp82PlusConfigurationEntry 653 }

	ommp82PlusSfpInputLowPowerWarningSeverity OBJECT-TYPE
		SYNTAX  DisplayString
		MAX-ACCESS  read-write
		STATUS  current
		DESCRIPTION
			"Set or Get the alarm severity level of the
			OMMP82-PLUS SFP Input Low Power Warning   
			for requested port
			-----------------------------
			ommp82PlusInterfaceNumber:
			1 to 8 - CLIENT-1 to CLIENT-8
			-----------------------------
			Value:
			critical
			major
			minor
			deferred
			---------------------------"
	::= { ommp82PlusConfigurationEntry 654 }

	ommp82PlusSfpOutputHighPowerAlarmSeverity OBJECT-TYPE
		SYNTAX  DisplayString
		MAX-ACCESS  read-write
		STATUS  current
		DESCRIPTION
			"Set or Get the alarm severity level of the
			OMMP82-PLUS SFP Output High Power Alarm   
			for requested port
			-----------------------------
			ommp82PlusInterfaceNumber:
			1 to 8 - CLIENT-1 to CLIENT-8
			-----------------------------
			Value:
			critical
			major
			minor
			deferred
			---------------------------"
	::= { ommp82PlusConfigurationEntry 655 }

	ommp82PlusSfpOutputLowPowerAlarmSeverity OBJECT-TYPE
		SYNTAX  DisplayString
		MAX-ACCESS  read-write
		STATUS  current
		DESCRIPTION
			"Set or Get the alarm severity level of the
			OMMP82-PLUS SFP Output Low Power Alarm   
			for requested port
			-----------------------------
			ommp82PlusInterfaceNumber:
			1 to 8 - CLIENT-1 to CLIENT-8
			-----------------------------
			Value:
			critical
			major
			minor
			deferred
			---------------------------"
	::= { ommp82PlusConfigurationEntry 656 }

	ommp82PlusSfpOutputHighPowerWarningSeverity OBJECT-TYPE
		SYNTAX  DisplayString
		MAX-ACCESS  read-write
		STATUS  current
		DESCRIPTION
			"Set or Get the alarm severity level of the
			OMMP82-PLUS SFP Output High Power Warning   
			for requested port
			-----------------------------
			ommp82PlusInterfaceNumber:
			1 to 8 - CLIENT-1 to CLIENT-8
			-----------------------------
			Value:
			critical
			major
			minor
			deferred
			---------------------------"
	::= { ommp82PlusConfigurationEntry 657 }

	ommp82PlusSfpOutputLowPowerWarningSeverity OBJECT-TYPE
		SYNTAX  DisplayString
		MAX-ACCESS  read-write
		STATUS  current
		DESCRIPTION
			"Set or Get the alarm severity level of the
			OMMP82-PLUS SFP Output Low Power Warning   
			for requested port
			-----------------------------
			ommp82PlusInterfaceNumber:
			1 to 8 - CLIENT-1 to CLIENT-8
			-----------------------------
			Value:
			critical
			major
			minor
			deferred
			---------------------------"
	::= { ommp82PlusConfigurationEntry 658 }

	ommp82PlusSfpHighSupplyVoltageAlarmSeverity OBJECT-TYPE
		SYNTAX  DisplayString
		MAX-ACCESS  read-write
		STATUS  current
		DESCRIPTION
			"Set or Get the alarm severity level of the
			OMMP82-PLUS SFP High Supply Voltage Alarm   
			for requested port
			-----------------------------
			ommp82PlusInterfaceNumber:
			1 to 8 - CLIENT-1 to CLIENT-8
			-----------------------------
			Value:
			critical
			major
			minor
			deferred
			---------------------------"
	::= { ommp82PlusConfigurationEntry 659 }

	ommp82PlusSfpLowSupplyVoltageAlarmSeverity OBJECT-TYPE
		SYNTAX  DisplayString
		MAX-ACCESS  read-write
		STATUS  current
		DESCRIPTION
			"Set or Get the alarm severity level of the
			OMMP82-PLUS SFP Low Supply Voltage Alarm   
			for requested port
			-----------------------------
			ommp82PlusInterfaceNumber:
			1 to 8 - CLIENT-1 to CLIENT-8
			-----------------------------
			Value:
			critical
			major
			minor
			deferred
			---------------------------"
	::= { ommp82PlusConfigurationEntry 660 }

	ommp82PlusSfpHighSupplyVoltageWarningSeverity OBJECT-TYPE
		SYNTAX  DisplayString
		MAX-ACCESS  read-write
		STATUS  current
		DESCRIPTION
			"Set or Get the alarm severity level of the
			OMMP82-PLUS SFP High Supply Voltage Warning   
			for requested port
			-----------------------------
			ommp82PlusInterfaceNumber:
			1 to 8 - CLIENT-1 to CLIENT-8
			-----------------------------
			Value:
			critical
			major
			minor
			deferred
			---------------------------"
	::= { ommp82PlusConfigurationEntry 661 }

	ommp82PlusSfpLowSupplyVoltageWarningSeverity OBJECT-TYPE
		SYNTAX  DisplayString
		MAX-ACCESS  read-write
		STATUS  current
		DESCRIPTION
			"Set or Get the alarm severity level of the
			OMMP82-PLUS SFP Low Supply Voltage Warning   
			for requested port
			-----------------------------
			ommp82PlusInterfaceNumber:
			1 to 8 - CLIENT-1 to CLIENT-8
			-----------------------------
			Value:
			critical
			major
			minor
			deferred
			---------------------------"
	::= { ommp82PlusConfigurationEntry 662 }

	ommp82PlusSfpPresenceAbsenceNotificationSeverity OBJECT-TYPE
		SYNTAX  DisplayString
		MAX-ACCESS  read-write
		STATUS  current
		DESCRIPTION
			"Set or Get the alarm severity level of the
			OMMP82-PLUS SFP Presence Absence Notification   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 663 }

	ommp82PlusSfpTransmitFaultPresenceAlarmSeverity OBJECT-TYPE
		SYNTAX  DisplayString
		MAX-ACCESS  read-write
		STATUS  current
		DESCRIPTION
			"Set or Get the alarm severity level of the
			OMMP82-PLUS SFP Transmit Fault Presence Alarm   
			for requested port
			-----------------------------
			ommp82PlusInterfaceNumber:
			1 to 8 - CLIENT-1 to CLIENT-8
			-----------------------------
			Value:
			critical
			major
			minor
			deferred
			---------------------------"
	::= { ommp82PlusConfigurationEntry 664 }

	ommp82PlusOtuLossOfSignalAlarmSeverity OBJECT-TYPE
		SYNTAX  DisplayString
		MAX-ACCESS  read-write
		STATUS  current
		DESCRIPTION
			"Set or Get the alarm severity level of the
			OMMP82-PLUS OTU Loss Of Signal Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 681 }

	ommp82PlusOtuLossOfFrameAlarmSeverity OBJECT-TYPE
		SYNTAX  DisplayString
		MAX-ACCESS  read-write
		STATUS  current
		DESCRIPTION
			"Set or Get the alarm severity level of the
			OMMP82-PLUS OTU Loss Of Frame Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 682 }

	ommp82PlusOtuOutOfFrameAlarmSeverity OBJECT-TYPE
		SYNTAX  DisplayString
		MAX-ACCESS  read-write
		STATUS  current
		DESCRIPTION
			"Set or Get the alarm severity level of the
			OMMP82-PLUS OTU Out Of Frame Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 683 }

	ommp82PlusOtuLossOfMultiFrameAlarmSeverity OBJECT-TYPE
		SYNTAX  DisplayString
		MAX-ACCESS  read-write
		STATUS  current
		DESCRIPTION
			"Set or Get the alarm severity level of the
			OMMP82-PLUS OTU Loss Of Multi Frame Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 684 }

	ommp82PlusOtuOutOfMultiFrameAlarmSeverity OBJECT-TYPE
		SYNTAX  DisplayString
		MAX-ACCESS  read-write
		STATUS  current
		DESCRIPTION
			"Set or Get the alarm severity level of the
			OMMP82-PLUS OTU Out Of Multi Frame Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 685 }

	ommp82PlusOtuSignalFailAlarmSeverity OBJECT-TYPE
		SYNTAX  DisplayString
		MAX-ACCESS  read-write
		STATUS  current
		DESCRIPTION
			"Set or Get the alarm severity level of the
			OMMP82-PLUS OTU Signal Fail Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 686 }

	ommp82PlusOtuSignalDegradeAlarmSeverity OBJECT-TYPE
		SYNTAX  DisplayString
		MAX-ACCESS  read-write
		STATUS  current
		DESCRIPTION
			"Set or Get the alarm severity level of the
			OMMP82-PLUS OTU Signal Degrade Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 687 }

	ommp82PlusOtuAlarmIndicationSignalAlarmSeverity OBJECT-TYPE
		SYNTAX  DisplayString
		MAX-ACCESS  read-write
		STATUS  current
		DESCRIPTION
			"Set or Get the alarm severity level of the
			OMMP82-PLUS OTU Alarm Indication Signal Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 688 }

	ommp82PlusOtuIncomingAlignmentErrorAlarmSeverity OBJECT-TYPE
		SYNTAX  DisplayString
		MAX-ACCESS  read-write
		STATUS  current
		DESCRIPTION
			"Set or Get the alarm severity level of the
			OMMP82-PLUS OTU Incoming Alignment Error Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 689 }

	ommp82PlusOtuTraceIdentifierMismatchAlarmSeverity OBJECT-TYPE
		SYNTAX  DisplayString
		MAX-ACCESS  read-write
		STATUS  current
		DESCRIPTION
			"Set or Get the alarm severity level of the
			OMMP82-PLUS OTU Trace Identifier Mismatch Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 690 }

	ommp82PlusOtuBackwardIncomingAlignmentErrorAlarmSeverity OBJECT-TYPE
		SYNTAX  DisplayString
		MAX-ACCESS  read-write
		STATUS  current
		DESCRIPTION
			"Set or Get the alarm severity level of the
			OMMP82-PLUS OTU Backward Incoming Alignment Error Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 691 }

	ommp82PlusOtuBackwardDefectIndicationAlarmSeverity OBJECT-TYPE
		SYNTAX  DisplayString
		MAX-ACCESS  read-write
		STATUS  current
		DESCRIPTION
			"Set or Get the alarm severity level of the
			OMMP82-PLUS OTU Backward Defect Indication Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 692 }

	ommp82PlusOduSignalFailAlarmSeverity OBJECT-TYPE
		SYNTAX  DisplayString
		MAX-ACCESS  read-write
		STATUS  current
		DESCRIPTION
			"Set or Get the alarm severity level of the
			OMMP82-PLUS ODU Signal Fail Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 711 }

	ommp82PlusOduSignalDegradeAlarmSeverity OBJECT-TYPE
		SYNTAX  DisplayString
		MAX-ACCESS  read-write
		STATUS  current
		DESCRIPTION
			"Set or Get the alarm severity level of the
			OMMP82-PLUS ODU Signal Degrade Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 712 }

	ommp82PlusOduAlarmIndicationSignalAlarmSeverity OBJECT-TYPE
		SYNTAX  DisplayString
		MAX-ACCESS  read-write
		STATUS  current
		DESCRIPTION
			"Set or Get the alarm severity level of the
			OMMP82-PLUS ODU Alarm Indication Signal Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 713 }

	ommp82PlusOduTcm1IncomingAlignmentErrorAlarmSeverity OBJECT-TYPE
		SYNTAX  DisplayString
		MAX-ACCESS  read-write
		STATUS  current
		DESCRIPTION
			"Set or Get the alarm severity level of the
			OMMP82-PLUS ODU TCM1 Incoming Alignment Error Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 714 }

	ommp82PlusOduTcm2IncomingAlignmentErrorAlarmSeverity OBJECT-TYPE
		SYNTAX  DisplayString
		MAX-ACCESS  read-write
		STATUS  current
		DESCRIPTION
			"Set or Get the alarm severity level of the
			OMMP82-PLUS ODU TCM2 Incoming Alignment Error Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 715 }

	ommp82PlusOduTcm3IncomingAlignmentErrorAlarmSeverity OBJECT-TYPE
		SYNTAX  DisplayString
		MAX-ACCESS  read-write
		STATUS  current
		DESCRIPTION
			"Set or Get the alarm severity level of the
			OMMP82-PLUS ODU TCM3 Incoming Alignment Error Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 716 }

	ommp82PlusOduTcm4IncomingAlignmentErrorAlarmSeverity OBJECT-TYPE
		SYNTAX  DisplayString
		MAX-ACCESS  read-write
		STATUS  current
		DESCRIPTION
			"Set or Get the alarm severity level of the
			OMMP82-PLUS ODU TCM4 Incoming Alignment Error Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 717 }

	ommp82PlusOduTcm5IncomingAlignmentErrorAlarmSeverity OBJECT-TYPE
		SYNTAX  DisplayString
		MAX-ACCESS  read-write
		STATUS  current
		DESCRIPTION
			"Set or Get the alarm severity level of the
			OMMP82-PLUS ODU TCM5 Incoming Alignment Error Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 718 }

	ommp82PlusOduTcm6IncomingAlignmentErrorAlarmSeverity OBJECT-TYPE
		SYNTAX  DisplayString
		MAX-ACCESS  read-write
		STATUS  current
		DESCRIPTION
			"Set or Get the alarm severity level of the
			OMMP82-PLUS ODU TCM6 Incoming Alignment Error Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 719 }

	ommp82PlusOduTraceIdentifierMismatchAlarmSeverity OBJECT-TYPE
		SYNTAX  DisplayString
		MAX-ACCESS  read-write
		STATUS  current
		DESCRIPTION
			"Set or Get the alarm severity level of the
			OMMP82-PLUS ODU Trace Identifier Mismatch Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 720 }

	ommp82PlusOduLockedDefectAlarmSeverity OBJECT-TYPE
		SYNTAX  DisplayString
		MAX-ACCESS  read-write
		STATUS  current
		DESCRIPTION
			"Set or Get the alarm severity level of the
			OMMP82-PLUS ODU Locked Defect Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 721 }

	ommp82PlusOduOpenConnectionIndicationAlarmSeverity OBJECT-TYPE
		SYNTAX  DisplayString
		MAX-ACCESS  read-write
		STATUS  current
		DESCRIPTION
			"Set or Get the alarm severity level of the
			OMMP82-PLUS ODU Open Connection Indication Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 722 }

	ommp82PlusOduBackwardDefectIndicationAlarmSeverity OBJECT-TYPE
		SYNTAX  DisplayString
		MAX-ACCESS  read-write
		STATUS  current
		DESCRIPTION
			"Set or Get the alarm severity level of the
			OMMP82-PLUS ODU Backward Defect Indication Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 723 }

	ommp82PlusOduTcm1BackwardIncomingAlignmentErrorAlarmSeverity OBJECT-TYPE
		SYNTAX  DisplayString
		MAX-ACCESS  read-write
		STATUS  current
		DESCRIPTION
			"Set or Get the alarm severity level of the
			OMMP82-PLUS ODU TCM1 Backward Incoming Alignment Error
			Alarm for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 724 }

	ommp82PlusOduTcm2BackwardIncomingAlignmentErrorAlarmSeverity OBJECT-TYPE
		SYNTAX  DisplayString
		MAX-ACCESS  read-write
		STATUS  current
		DESCRIPTION
			"Set or Get the alarm severity level of the
			OMMP82-PLUS ODU TCM2 Backward Incoming Alignment Error
			Alarm for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 725 }

	ommp82PlusOduTcm3BackwardIncomingAlignmentErrorAlarmSeverity OBJECT-TYPE
		SYNTAX  DisplayString
		MAX-ACCESS  read-write
		STATUS  current
		DESCRIPTION
			"Set or Get the alarm severity level of the
			OMMP82-PLUS ODU TCM3 Backward Incoming Alignment Error
			Alarm for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 726 }

	ommp82PlusOduTcm4BackwardIncomingAlignmentErrorAlarmSeverity OBJECT-TYPE
		SYNTAX  DisplayString
		MAX-ACCESS  read-write
		STATUS  current
		DESCRIPTION
			"Set or Get the alarm severity level of the
			OMMP82-PLUS ODU TCM4 Backward Incoming Alignment Error
			Alarm for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 727 }

	ommp82PlusOduTcm5BackwardIncomingAlignmentErrorAlarmSeverity OBJECT-TYPE
		SYNTAX  DisplayString
		MAX-ACCESS  read-write
		STATUS  current
		DESCRIPTION
			"Set or Get the alarm severity level of the
			OMMP82-PLUS ODU TCM5 Backward Incoming Alignment Error
			Alarm for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 728 }

	ommp82PlusOduTcm6BackwardIncomingAlignmentErrorAlarmSeverity OBJECT-TYPE
		SYNTAX  DisplayString
		MAX-ACCESS  read-write
		STATUS  current
		DESCRIPTION
			"Set or Get the alarm severity level of the
			OMMP82-PLUS ODU TCM6 Backward Incoming Alignment Error
			Alarm for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 729 }

	ommp82PlusOduLossOfFrameLossOfMultiframeAlarmSeverity OBJECT-TYPE
		SYNTAX  DisplayString
		MAX-ACCESS  read-write
		STATUS  current
		DESCRIPTION
			"Set or Get the alarm severity level of the
			OMMP82-PLUS ODU Loss Of Frame Loss Of Multiframe Alarm   
			for requested port
			-----------------------------
			ommp82PlusInterfaceNumber:
			1, 2, 3, 4 - Slice number
			-----------------------------
			Value:
			critical
			major
			minor
			deferred
			---------------------------"
	::= { ommp82PlusConfigurationEntry 730 }

	ommp82PlusOpuPayloadMismatchAlarmSeverity OBJECT-TYPE
		SYNTAX  DisplayString
		MAX-ACCESS  read-write
		STATUS  current
		DESCRIPTION
			"Set or Get the alarm severity level of the
			OMMP82-PLUS OPU Payload Mismatch Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 735 }

	ommp82PlusOchLossOfPayloadAlarmSeverity OBJECT-TYPE
		SYNTAX  DisplayString
		MAX-ACCESS  read-write
		STATUS  current
		DESCRIPTION
			"Set or Get the alarm severity level of the
			OMMP82-PLUS OCH Loss Of Payload Alarm   
			for requested port
			-----------------------------
			ommp82PlusInterfaceNumber:
			1 to 8 - CLIENT-1 to CLIENT-8
			9 - LINE-1
			10 - LINE-2
			-----------------------------
			Value:
			critical
			major
			minor
			deferred
			---------------------------"
	::= { ommp82PlusConfigurationEntry 736 }

	ommp82PlusSdhLossOfSignalAlarmSeverity OBJECT-TYPE
		SYNTAX  DisplayString
		MAX-ACCESS  read-write
		STATUS  current
		DESCRIPTION
			"Set or Get the alarm severity level of the
			OMMP82-PLUS SDH Loss Of Signal Alarm   
			for requested port
			-----------------------------
			ommp82PlusInterfaceNumber:
			1 to 8 - CLIENT-1 to CLIENT-8
			-----------------------------
			Value:
			critical
			major
			minor
			deferred
			---------------------------"
	::= { ommp82PlusConfigurationEntry 741 }

	ommp82PlusSdhOutOfFrameAlarmSeverity OBJECT-TYPE
		SYNTAX  DisplayString
		MAX-ACCESS  read-write
		STATUS  current
		DESCRIPTION
			"Set or Get the alarm severity level of the
			OMMP82-PLUS SDH Out Of Frame Alarm   
			for requested port
			-----------------------------
			ommp82PlusInterfaceNumber:
			1 to 8 - CLIENT-1 to CLIENT-8,
			-----------------------------
			Value:
			critical
			major
			minor
			deferred
			---------------------------"
	::= { ommp82PlusConfigurationEntry 742 }

	ommp82PlusSdhLossOfFrameAlarmSeverity OBJECT-TYPE
		SYNTAX  DisplayString
		MAX-ACCESS  read-write
		STATUS  current
		DESCRIPTION
			"Set or Get the alarm severity level of the
			OMMP82-PLUS SDH Loss Of Frame Alarm   
			for requested port
			-----------------------------
			ommp82PlusInterfaceNumber:
			1 to 8 - CLIENT-1 to CLIENT-8
			-----------------------------
			Value:
			critical
			major
			minor
			deferred
			---------------------------"
	::= { ommp82PlusConfigurationEntry 743 }

	ommp82PlusSdhRsAlarmIndicationSignalAlarmSeverity OBJECT-TYPE
		SYNTAX  DisplayString
		MAX-ACCESS  read-write
		STATUS  current
		DESCRIPTION
			"Set or Get the alarm severity level of the
			OMMP82-PLUS SDH Rs Alarm Indication Signal Alarm   
			for requested port
			-----------------------------
			ommp82PlusInterfaceNumber:
			1 to 8 - CLIENT-1 to CLIENT-8
			-----------------------------
			Value:
			critical
			major
			minor
			deferred
			---------------------------"
	::= { ommp82PlusConfigurationEntry 744 }

	ommp82PlusSdhRsTraceIdentifierMismatchAlarmSeverity OBJECT-TYPE
		SYNTAX  DisplayString
		MAX-ACCESS  read-write
		STATUS  current
		DESCRIPTION
			"Set or Get the alarm severity level of the
			OMMP82-PLUS SDH Rs Trace Identifier Mismatch Alarm   
			for requested port
			-----------------------------
			ommp82PlusInterfaceNumber:
			1 to 8 - CLIENT-1 to CLIENT-8
			-----------------------------
			Value:
			critical
			major
			minor
			deferred
			---------------------------"
	::= { ommp82PlusConfigurationEntry 745 }

	ommp82PlusSdhAuAlarmIndicationSignalAlarmSeverity OBJECT-TYPE
		SYNTAX  DisplayString
		MAX-ACCESS  read-write
		STATUS  current
		DESCRIPTION
			"Set or Get the alarm severity level of the
			OMMP82-PLUS SDH Au Alarm Indication Signal Alarm   
			for requested port
			-----------------------------
			ommp82PlusInterfaceNumber:
			1 to 8 - CLIENT-1 to CLIENT-8
			-----------------------------
			Value:
			critical
			major
			minor
			deferred
			---------------------------"
	::= { ommp82PlusConfigurationEntry 746 }

	ommp82PlusSdhAuLossOfPointerAlarmSeverity OBJECT-TYPE
		SYNTAX  DisplayString
		MAX-ACCESS  read-write
		STATUS  current
		DESCRIPTION
			"Set or Get the alarm severity level of the
			OMMP82-PLUS SDH Au Loss Of Pointer Alarm   
			for requested port
			-----------------------------
			ommp82PlusInterfaceNumber:
			1 to 8 - CLIENT-1 to CLIENT-8
			-----------------------------
			Value:
			critical
			major
			minor
			deferred
			---------------------------"
	::= { ommp82PlusConfigurationEntry 747 }

	ommp82PlusSdhMsAlarmIndicationSignalAlarmSeverity OBJECT-TYPE
		SYNTAX  DisplayString
		MAX-ACCESS  read-write
		STATUS  current
		DESCRIPTION
			"Set or Get the alarm severity level of the
			OMMP82-PLUS SDH Ms Alarm Indication Signal Alarm   
			for requested port
			-----------------------------
			ommp82PlusInterfaceNumber:
			1 to 8 - CLIENT-1 to CLIENT-8
			-----------------------------
			Value:
			critical
			major
			minor
			deferred
			---------------------------"
	::= { ommp82PlusConfigurationEntry 748 }

	ommp82PlusSdhMsRemoteErrorIndicationAlarmSeverity OBJECT-TYPE
		SYNTAX  DisplayString
		MAX-ACCESS  read-write
		STATUS  current
		DESCRIPTION
			"Set or Get the alarm severity level of the
			OMMP82-PLUS SDH Ms Remote Error Indication Alarm   
			for requested port
			-----------------------------
			ommp82PlusInterfaceNumber:
			1 to 8 - CLIENT-1 to CLIENT-8
			-----------------------------
			Value:
			critical
			major
			minor
			deferred
			---------------------------"
	::= { ommp82PlusConfigurationEntry 749 }

	ommp82PlusSdhMsRemoteDefectIndicationAlarmSeverity OBJECT-TYPE
		SYNTAX  DisplayString
		MAX-ACCESS  read-write
		STATUS  current
		DESCRIPTION
			"Set or Get the alarm severity level of the
			OMMP82-PLUS SDH Ms Remote Defect Indication Alarm   
			for requested port
			-----------------------------
			ommp82PlusInterfaceNumber:
			1 to 8 - CLIENT-1 to CLIENT-8
			-----------------------------
			Value:
			critical
			major
			minor
			deferred
			---------------------------"
	::= { ommp82PlusConfigurationEntry 750 }

	ommp82PlusSdhMsRemoteFailureIndicationAlarmSeverity OBJECT-TYPE
		SYNTAX  DisplayString
		MAX-ACCESS  read-write
		STATUS  current
		DESCRIPTION
			"Set or Get the alarm severity level of the
			OMMP82-PLUS SDH Ms Remote Failure Indication Alarm   
			for requested port
			-----------------------------
			ommp82PlusInterfaceNumber:
			1 to 8 - CLIENT-1 to CLIENT-8
			-----------------------------
			Value:
			critical
			major
			minor
			deferred
			---------------------------"
	::= { ommp82PlusConfigurationEntry 751 }

	ommp82PlusSdhMsB2ExcessiveErrorAlarmSeverity OBJECT-TYPE
		SYNTAX  DisplayString
		MAX-ACCESS  read-write
		STATUS  current
		DESCRIPTION
			"Set or Get the alarm severity level of the
			OMMP82-PLUS SDH Ms B2 Signal Fail Alarm   
			for requested port
			-----------------------------
			ommp82PlusInterfaceNumber:
			1 to 8 - CLIENT-1 to CLIENT-8
			-----------------------------
			Value:
			critical
			major
			minor
			deferred
			---------------------------"
	::= { ommp82PlusConfigurationEntry 752 }

	ommp82PlusSdhMsB2SignalDegradeAlarmSeverity OBJECT-TYPE
		SYNTAX  DisplayString
		MAX-ACCESS  read-write
		STATUS  current
		DESCRIPTION
			"Set or Get the alarm severity level of the
			OMMP82-PLUS SDH Ms B2 Signal Degrade Alarm   
			for requested port
			-----------------------------
			ommp82PlusInterfaceNumber:
			1 to 8 - CLIENT-1 to CLIENT-8
			-----------------------------
			Value:
			critical
			major
			minor
			deferred
			---------------------------"
	::= { ommp82PlusConfigurationEntry 753 }

	ommp82PlusSdhLossOfSequenceSynchronisationAlarmSeverity OBJECT-TYPE
		SYNTAX  DisplayString
		MAX-ACCESS  read-write
		STATUS  current
		DESCRIPTION
			"Set or Get the alarm severity level of the
			OMMP82-PLUS SDH Loss Of Sequence Synchronisation Alarm   
			for requested port
			-----------------------------
			ommp82PlusInterfaceNumber:
			1 to 8 - CLIENT-1 to CLIENT-8
			-----------------------------
			Value:
			critical
			major
			minor
			deferred
			---------------------------"
	::= { ommp82PlusConfigurationEntry 754 }

	ommp82PlusSdhLowerOrderPathPayloadLabelMismatchAlarmSeverity OBJECT-TYPE
		SYNTAX  DisplayString
		MAX-ACCESS  read-write
		STATUS  current
		DESCRIPTION
			"Set or Get the alarm severity level of the
			OMMP82-PLUS SDH Lower Order Path Payload Label Mismatch Alarm   
			for requested port
			-----------------------------
			ommp82PlusInterfaceNumber:
			1 to 8 - CLIENT-1 to CLIENT-8
			-----------------------------
			Value:
			critical
			major
			minor
			deferred
			---------------------------"
	::= { ommp82PlusConfigurationEntry 755 }

	ommp82PlusSdhLowerOrderPathUnequippedAlarmSeverity OBJECT-TYPE
		SYNTAX  DisplayString
		MAX-ACCESS  read-write
		STATUS  current
		DESCRIPTION
			"Set or Get the alarm severity level of the
			OMMP82-PLUS SDH Lower Order Path Unequipped Alarm   
			for requested port
			-----------------------------
			ommp82PlusInterfaceNumber:
			1 to 8 - CLIENT-1 to CLIENT-8
			-----------------------------
			Value:
			critical
			major
			minor
			deferred
			---------------------------"
	::= { ommp82PlusConfigurationEntry 756 }

	ommp82PlusEthernetLossOfSignalAlarmSeverity OBJECT-TYPE
		SYNTAX  DisplayString
		MAX-ACCESS  read-write
		STATUS  current
		DESCRIPTION
			"Set or Get the alarm severity level of the
			OMMP82-PLUS Ethernet Loss Of Signal Alarm   
			for requested port
			-----------------------------
			ommp82PlusInterfaceNumber:
			1 to 8 - CLIENT-1 to CLIENT-8
			-----------------------------
			Value:
			critical
			major
			minor
			deferred
			---------------------------"
	::= { ommp82PlusConfigurationEntry 771 }

	ommp82PlusEthernetLossOfSignalSyncAlarmSeverity OBJECT-TYPE
		SYNTAX  DisplayString
		MAX-ACCESS  read-write
		STATUS  current
		DESCRIPTION
			"Set or Get the alarm severity level of the
			OMMP82-PLUS Ethernet Loss Of Signal Sync Alarm   
			for requested port
			-----------------------------
			ommp82PlusInterfaceNumber:
			1 to 8 - CLIENT-1 to CLIENT-8
			-----------------------------
			Value:
			critical
			major
			minor
			deferred
			---------------------------"
	::= { ommp82PlusConfigurationEntry 772 }

	ommp82PlusEthernetLinkFailureAlarmSeverity OBJECT-TYPE
		SYNTAX  DisplayString
		MAX-ACCESS  read-write
		STATUS  current
		DESCRIPTION
			"Set or Get the alarm severity level of the
			OMMP82-PLUS Ethernet Link Failure Alarm   
			for requested port
			-----------------------------
			ommp82PlusInterfaceNumber:
			1 to 8 - CLIENT-1 to CLIENT-8
			-----------------------------
			Value:
			critical
			major
			minor
			deferred
			---------------------------"
	::= { ommp82PlusConfigurationEntry 773 }

	ommp82PlusEthernetAutoNegotiationAlarmSeverity OBJECT-TYPE
		SYNTAX  DisplayString
		MAX-ACCESS  read-write
		STATUS  current
		DESCRIPTION
			"Set or Get the alarm severity level of the
			OMMP82-PLUS Ethernet Auto Negotiation Alarm   
			for requested port
			-----------------------------
			ommp82PlusInterfaceNumber:
			1 to 8 - CLIENT-1 to CLIENT-8
			-----------------------------
			Value:
			critical
			major
			minor
			deferred
			---------------------------"
	::= { ommp82PlusConfigurationEntry 774 }

	ommp82PlusEthernetFrameCheckSequenceAlarmSeverity OBJECT-TYPE
		SYNTAX  DisplayString
		MAX-ACCESS  read-write
		STATUS  current
		DESCRIPTION
			"Set or Get the alarm severity level of the
			OMMP82-PLUS Ethernet Frame Check Sequence Alarm   
			for requested port
			-----------------------------
			ommp82PlusInterfaceNumber:
			1 to 8 - CLIENT-1 to CLIENT-8
			-----------------------------
			Value:
			critical
			major
			minor
			deferred
			---------------------------"
	::= { ommp82PlusConfigurationEntry 775 }

	ommp82PlusEthernetCarrierStatusAlarmSeverity OBJECT-TYPE
		SYNTAX  DisplayString
		MAX-ACCESS  read-write
		STATUS  current
		DESCRIPTION
			"Set or Get the alarm severity level of the
			OMMP82-PLUS Ethernet Carrier Status Alarm   
			for requested port
			-----------------------------
			ommp82PlusInterfaceNumber:
			1 to 8 - CLIENT-1 to CLIENT-8
			-----------------------------
			Value:
			critical
			major
			minor
			deferred
			---------------------------"
	::= { ommp82PlusConfigurationEntry 776 }

	ommp82PlusEthernetHighBerAlarmSeverity OBJECT-TYPE
		SYNTAX  DisplayString
		MAX-ACCESS  read-write
		STATUS  current
		DESCRIPTION
			"Set or Get the alarm severity level of the
			OMMP82-PLUS Ethernet High Ber Alarm   
			for requested port
			-----------------------------
			ommp82PlusInterfaceNumber:
			1 to 8 - CLIENT-1 to CLIENT-8
			-----------------------------
			Value:
			critical
			major
			minor
			deferred
			---------------------------"
	::= { ommp82PlusConfigurationEntry 777 }

	ommp82PlusEthernetLocalFaultAlarmSeverity OBJECT-TYPE
		SYNTAX  DisplayString
		MAX-ACCESS  read-write
		STATUS  current
		DESCRIPTION
			"Set or Get the alarm severity level of the
			OMMP82-PLUS Ethernet Local Fault Alarm   
			for requested port
			-----------------------------
			ommp82PlusInterfaceNumber:
			1 to 8 - CLIENT-1 to CLIENT-8
			-----------------------------
			Value:
			critical
			major
			minor
			deferred
			---------------------------"
	::= { ommp82PlusConfigurationEntry 778 }

	ommp82PlusEthernetRemoteFaultAlarmSeverity OBJECT-TYPE
		SYNTAX  DisplayString
		MAX-ACCESS  read-write
		STATUS  current
		DESCRIPTION
			"Set or Get the alarm severity level of the
			OMMP82-PLUS Ethernet Remote Fault Alarm   
			for requested port
			-----------------------------
			ommp82PlusInterfaceNumber:
			1 to 8 - CLIENT-1 to CLIENT-8
			-----------------------------
			Value:
			critical
			major
			minor
			deferred
			---------------------------"
	::= { ommp82PlusConfigurationEntry 779 }

	ommp82PlusFcTransmitDisparityInversionDefectAlarmSeverity OBJECT-TYPE
		SYNTAX  DisplayString
		MAX-ACCESS  read-write
		STATUS  current
		DESCRIPTION
			"Set or Get the alarm severity level of the
			OMMP82-PLUS FC Transmit Disparity Inversion Defect Alarm
			for requested port
			-----------------------------
			ommp82PlusInterfaceNumber:
			1 to 8 - CLIENT-1 to CLIENT-8
			-----------------------------
			Value:
			critical
			major
			minor
			deferred
			---------------------------"
	::= { ommp82PlusConfigurationEntry 791 }

	ommp82PlusFcTransmitDigitalLossOfLinkDefectAlarmSeverity OBJECT-TYPE
		SYNTAX  DisplayString
		MAX-ACCESS  read-write
		STATUS  current
		DESCRIPTION
			"Set or Get the alarm severity level of the
			OMMP82-PLUS FC Transmit Digital Loss Of Link Defect 
			Alarm for requested port
			-----------------------------
			ommp82PlusInterfaceNumber:
			1 to 8 - CLIENT-1 to CLIENT-8
			-----------------------------
			Value:
			critical
			major
			minor
			deferred
			---------------------------"
	::= { ommp82PlusConfigurationEntry 792 }

	ommp82PlusFcTrasnmitLossOfSynchronizationDefectAlarmSeverity OBJECT-TYPE
		SYNTAX  DisplayString
		MAX-ACCESS  read-write
		STATUS  current
		DESCRIPTION
			"Set or Get the alarm severity level of the
			OMMP82-PLUS FC Transmit Loss Of Synchronization Defect 
			Alarm  for requested port
			-----------------------------
			ommp82PlusInterfaceNumber:
			1 to 8 - CLIENT-1 to CLIENT-8
			-----------------------------
			Value:
			critical
			major
			minor
			deferred
			---------------------------"
	::= { ommp82PlusConfigurationEntry 793 }

	ommp82PlusFcReceiveDigitalLossOfLinkDefectAlarmSeverity OBJECT-TYPE
		SYNTAX  DisplayString
		MAX-ACCESS  read-write
		STATUS  current
		DESCRIPTION
			"Set or Get the alarm severity level of the
			OMMP82-PLUS FC Receive Digital Loss Of Link Defect Alarm  
			for requested port
			-----------------------------
			ommp82PlusInterfaceNumber:
			1 to 8 - CLIENT-1 to CLIENT-8
			-----------------------------
			Value:
			critical
			major
			minor
			deferred
			---------------------------"
	::= { ommp82PlusConfigurationEntry 794 }

	ommp82PlusFcReceiveLossOfSynchronizationDefectAlarmSeverity OBJECT-TYPE
		SYNTAX  DisplayString
		MAX-ACCESS  read-write
		STATUS  current
		DESCRIPTION
			"Set or Get the alarm severity level of the
			OMMP82-PLUS FC Receive Loss Of Synchronization Defect
			Alarm for requested port
			-----------------------------
			ommp82PlusInterfaceNumber:
			1 to 8 - CLIENT-1 to CLIENT-8
			-----------------------------
			Value:
			critical
			major
			minor
			deferred
			---------------------------"
	::= { ommp82PlusConfigurationEntry 795 }

	ommp82PlusFcReceiveTransitionDetectDefectAlarmSeverity OBJECT-TYPE
		SYNTAX  DisplayString
		MAX-ACCESS  read-write
		STATUS  current
		DESCRIPTION
			"Set or Get the alarm severity level of the
			OMMP82-PLUS FC Receive Transition Detect Defect Alarm   
			for requested port
			-----------------------------
			ommp82PlusInterfaceNumber:
			1 to 8 - CLIENT-1 to CLIENT-8
			-----------------------------
			Value:
			critical
			major
			minor
			deferred
			---------------------------"
	::= { ommp82PlusConfigurationEntry 796 }

	ommp82PlusFcReceiveAnalogLossOfSignalDefectAlarmSeverity OBJECT-TYPE
		SYNTAX  DisplayString
		MAX-ACCESS  read-write
		STATUS  current
		DESCRIPTION
			"Set or Get the alarm severity level of the
			OMMP82-PLUS FC Receive Analog Loss Of Signal Defect
			Alarm for requested port
			-----------------------------
			ommp82PlusInterfaceNumber:
			1 to 8 - CLIENT-1 to CLIENT-8
			-----------------------------
			Value:
			critical
			major
			minor
			deferred
			---------------------------"
	::= { ommp82PlusConfigurationEntry 797 }

	ommp82PlusFcReceiveLineCodeViolationDefectAlarmSeverity OBJECT-TYPE
		SYNTAX  DisplayString
		MAX-ACCESS  read-write
		STATUS  current
		DESCRIPTION
			"Set or Get the alarm severity level of the
			OMMP82-PLUS FC Receive Line Code Violation 
			Defect Alarm for the requested port
			-----------------------------
			ommp82PlusInterfaceNumber:
			1 to 8 - CLIENT-1 to CLIENT-8
			-----------------------------
			Value:
			critical
			major
			minor
			deferred
			---------------------------"
	::= { ommp82PlusConfigurationEntry 798 }

	ommp82PlusGfpCsfSignalFailAlarmSeverity OBJECT-TYPE
		SYNTAX  DisplayString
		MAX-ACCESS  read-write
		STATUS  current
		DESCRIPTION
			"Set or Get the alarm severity level of the
			OMMP82-PLUS GFP Csf Signal Failure Alarm   
			for requested port
			-----------------------------
			ommp82PlusInterfaceNumber:
			1 to 8 - CLIENT-1 to CLIENT-8
			-----------------------------
			Value:
			critical
			major
			minor
			deferred
			---------------------------"
	::= { ommp82PlusConfigurationEntry 811 }

	ommp82PlusGfpCsfLinkFailAlarmSeverity OBJECT-TYPE
		SYNTAX  DisplayString
		MAX-ACCESS  read-write
		STATUS  current
		DESCRIPTION
			"Set or Get the alarm severity level of the
			OMMP82-PLUS GFP Csf Link Failure Alarm   
			for requested port
			-----------------------------
			ommp82PlusInterfaceNumber:
			1 to 8 - CLIENT-1 to CLIENT-8
			-----------------------------
			Value:
			critical
			major
			minor
			deferred
			---------------------------"
	::= { ommp82PlusConfigurationEntry 812 }

	ommp82PlusGfpCoreHeaderErrorAlarmSeverity OBJECT-TYPE
		SYNTAX  DisplayString
		MAX-ACCESS  read-write
		STATUS  current
		DESCRIPTION
			"Set or Get the alarm severity level of the
			OMMP82-PLUS GFP Core Header Error Alarm   
			for requested port
			-----------------------------
			ommp82PlusInterfaceNumber:
			1 to 8 - CLIENT-1 to CLIENT-8
			-----------------------------
			Value:
			critical
			major
			minor
			deferred
			---------------------------"
	::= { ommp82PlusConfigurationEntry 813 }

	ommp82PlusGfpExtentionHeaderErrorAlarmSeverity OBJECT-TYPE
		SYNTAX  DisplayString
		MAX-ACCESS  read-write
		STATUS  current
		DESCRIPTION
			"Set or Get the alarm severity level of the
			OMMP82-PLUS GFP Extention Header Error Alarm   
			for requested port
			-----------------------------
			ommp82PlusInterfaceNumber:
			1 to 8 - CLIENT-1 to CLIENT-8
			-----------------------------
			Value:
			critical
			major
			minor
			deferred
			---------------------------"
	::= { ommp82PlusConfigurationEntry 814 }

	ommp82PlusConfigurationTableRowStatus OBJECT-TYPE
              SYNTAX      RowStatus
              MAX-ACCESS  read-write
              STATUS      current
              DESCRIPTION
			"*****************************
			This is MIB realted property,
			NOT to be considered as a card property
			*****************************"
              ::= { ommp82PlusConfigurationEntry 815 }	


--*****************************************************************************
--				    ALARMS
--*****************************************************************************
                 
	ommp82PlusAlarmQueryTable OBJECT-TYPE
	      SYNTAX  SEQUENCE OF Ommp82PlusAlarmQueryEntry 
              MAX-ACCESS  not-accessible
              STATUS  current
              DESCRIPTION
                      "Gives Optical Alarms status of the OMMP82-PLUS card"
		::= { ommp82PlusAlarmQuery 1 }	

	ommp82PlusAlarmQueryEntry   OBJECT-TYPE
              SYNTAX  Ommp82PlusAlarmQueryEntry 
              MAX-ACCESS  not-accessible
              STATUS  current
              DESCRIPTION 
              	""
		INDEX   { node, rack , subRack , slot , ommp82PlusInterfaceNumber }
		::= { ommp82PlusAlarmQueryTable 1 }
	
	Ommp82PlusAlarmQueryEntry ::= 
			SEQUENCE {					
					ommp82PlusXfpInputPowerFailureAlarm					DisplayString,
					ommp82PlusXfpOutputPowerFailureAlarm					DisplayString,
					ommp82PlusXfpHighTemperatureAlarm					DisplayString,
					ommp82PlusXfpLowTemperatureAlarm					DisplayString,
					ommp82PlusXfpHighTemperatureWarning					DisplayString,
					ommp82PlusXfpLowTemperatureWarning					DisplayString,
					ommp82PlusXfpHighBiasCurrentAlarm					DisplayString,
					ommp82PlusXfpLowBiasCurrentAlarm					DisplayString,
					ommp82PlusXfpHighBiasCurrentWarning					DisplayString,
					ommp82PlusXfpLowBiasCurrentWarning					DisplayString,
					ommp82PlusXfpInputHighPowerAlarm					DisplayString,
					ommp82PlusXfpInputLowPowerAlarm						DisplayString,
					ommp82PlusXfpInputHighPowerWarning					DisplayString,
					ommp82PlusXfpInputLowPowerWarning					DisplayString,
					ommp82PlusXfpOutputHighPowerAlarm					DisplayString,
					ommp82PlusXfpOutputLowPowerAlarm					DisplayString,
					ommp82PlusXfpOutputHighPowerWarning					DisplayString,
					ommp82PlusXfpOutputLowPowerWarning					DisplayString,
					ommp82PlusXfpHighSupplyVoltageAlarm					DisplayString,
					ommp82PlusXfpLowSupplyVoltageAlarm					DisplayString,
					ommp82PlusXfpHighSupplyVoltageWarning					DisplayString,
					ommp82PlusXfpLowSupplyVoltageWarning					DisplayString,
					ommp82PlusXfpPresenceAbsenceNotification				DisplayString,
					ommp82PlusSfpInputPowerFailureAlarm					DisplayString,
					ommp82PlusSfpOutputPowerFailureAlarm					DisplayString,
					ommp82PlusSfpHighTemperatureAlarm					DisplayString,
					ommp82PlusSfpLowTemperatureAlarm					DisplayString,
					ommp82PlusSfpHighTemperatureWarning					DisplayString,
					ommp82PlusSfpLowTemperatureWarning					DisplayString,
					ommp82PlusSfpHighBiasCurrentAlarm					DisplayString,
					ommp82PlusSfpLowBiasCurrentAlarm					DisplayString,
					ommp82PlusSfpHighBiasCurrentWarning					DisplayString,
					ommp82PlusSfpLowBiasCurrentWarning					DisplayString,
					ommp82PlusSfpInputHighPowerAlarm					DisplayString,
					ommp82PlusSfpInputLowPowerAlarm						DisplayString,
					ommp82PlusSfpInputHighPowerWarning					DisplayString,
					ommp82PlusSfpInputLowPowerWarning					DisplayString,
					ommp82PlusSfpOutputHighPowerAlarm					DisplayString,
					ommp82PlusSfpOutputLowPowerAlarm					DisplayString,
					ommp82PlusSfpOutputHighPowerWarning					DisplayString,
					ommp82PlusSfpOutputLowPowerWarning					DisplayString,
					ommp82PlusSfpHighSupplyVoltageAlarm					DisplayString,
					ommp82PlusSfpLowSupplyVoltageAlarm					DisplayString,
					ommp82PlusSfpHighSupplyVoltageWarning					DisplayString,
					ommp82PlusSfpLowSupplyVoltageWarning					DisplayString,
					ommp82PlusSfpPresenceAbsenceNotification				DisplayString,
					ommp82PlusSfpTransmitFaultPresenceAlarm					DisplayString,
					ommp82PlusOtuLossOfSignalAlarm						DisplayString,
					ommp82PlusOtuLossOfFrameAlarm						DisplayString,
					ommp82PlusOtuOutOfFrameAlarm						DisplayString,
					ommp82PlusOtuLossOfMultiFrameAlarm					DisplayString,
					ommp82PlusOtuOutOfMultiFrameAlarm					DisplayString,
					ommp82PlusOtuSignalFailAlarm						DisplayString,
					ommp82PlusOtuSignalDegradeAlarm						DisplayString,
					ommp82PlusOtuAlarmIndicationSignalAlarm					DisplayString,
					ommp82PlusOtuIncomingAlignmentErrorAlarm				DisplayString,
					ommp82PlusOtuTraceIdentifierMismatchAlarm				DisplayString,
					ommp82PlusOtuBackwardIncomingAlignmentErrorAlarm			DisplayString,
					ommp82PlusOtuBackwardDefectIndicationAlarm				DisplayString,
					ommp82PlusOduSignalFailAlarm						DisplayString,
					ommp82PlusOduSignalDegradeAlarm						DisplayString,
					ommp82PlusOduAlarmIndicationSignalAlarm					DisplayString,
					ommp82PlusOduTcm1IncomingAlignmentErrorAlarm				DisplayString,
					ommp82PlusOduTcm2IncomingAlignmentErrorAlarm				DisplayString,
					ommp82PlusOduTcm3IncomingAlignmentErrorAlarm				DisplayString,
					ommp82PlusOduTcm4IncomingAlignmentErrorAlarm				DisplayString,
					ommp82PlusOduTcm5IncomingAlignmentErrorAlarm				DisplayString,
					ommp82PlusOduTcm6IncomingAlignmentErrorAlarm				DisplayString,
					ommp82PlusOduTraceIdentifierMismatchAlarm				DisplayString,
					ommp82PlusOduLockedDefectAlarm						DisplayString,
					ommp82PlusOduOpenConnectionIndicationAlarm				DisplayString,
					ommp82PlusOduBackwardDefectIndicationAlarm				DisplayString,
					ommp82PlusOduTcm1BackwardIncomingAlignmentErrorAlarm			DisplayString,
					ommp82PlusOduTcm2BackwardIncomingAlignmentErrorAlarm			DisplayString,
					ommp82PlusOduTcm3BackwardIncomingAlignmentErrorAlarm			DisplayString,
					ommp82PlusOduTcm4BackwardIncomingAlignmentErrorAlarm			DisplayString,
					ommp82PlusOduTcm5BackwardIncomingAlignmentErrorAlarm			DisplayString,
					ommp82PlusOduTcm6BackwardIncomingAlignmentErrorAlarm			DisplayString,
					ommp82PlusOduLossOfFrameLossOfMultiframeAlarm				DisplayString,
					ommp82PlusOpuPayloadMismatchAlarm					DisplayString,
					ommp82PlusOchLossOfPayloadAlarm						DisplayString,
					ommp82PlusSdhLossOfSignalAlarm						DisplayString,
					ommp82PlusSdhOutOfFrameAlarm						DisplayString,
					ommp82PlusSdhLossOfFrameAlarm						DisplayString,
					ommp82PlusSdhRsAlarmIndicationSignalAlarm				DisplayString,
					ommp82PlusSdhRsTraceIdentifierMismatchAlarm				DisplayString,
					ommp82PlusSdhAuAlarmIndicationSignalAlarm				DisplayString,
					ommp82PlusSdhAuLossOfPointerAlarm					DisplayString,
					ommp82PlusSdhMsAlarmIndicationSignalAlarm				DisplayString,
					ommp82PlusSdhMsRemoteErrorIndicationAlarm				DisplayString,
					ommp82PlusSdhMsRemoteDefectIndicationAlarm				DisplayString,
					ommp82PlusSdhMsRemoteFailureIndicationAlarm				DisplayString,
					ommp82PlusSdhMsB2ExcessiveErrorAlarm					DisplayString,
					ommp82PlusSdhMsB2SignalDegradeAlarm					DisplayString,
					ommp82PlusSdhLossOfSequenceSynchronisationAlarm				DisplayString,
					ommp82PlusSdhLowerOrderPathPayloadLabelMismatchAlarm			DisplayString,
					ommp82PlusSdhLowerOrderPathUnequippedAlarm				DisplayString,
					ommp82PlusEthernetLossOfSignalAlarm					DisplayString,
					ommp82PlusEthernetLossOfSignalSyncAlarm					DisplayString,
					ommp82PlusEthernetLinkFailureAlarm					DisplayString,
					ommp82PlusEthernetAutoNegotiationAlarm					DisplayString,
					ommp82PlusEthernetFrameCheckSequenceAlarm				DisplayString,
					ommp82PlusEthernetCarrierStatusAlarm					DisplayString,
					ommp82PlusEthernetHighBerAlarm						DisplayString,
					ommp82PlusEthernetLocalFaultAlarm					DisplayString,
					ommp82PlusEthernetRemoteFaultAlarm					DisplayString,
					ommp82PlusFcTransmitDisparityInversionDefectAlarm			DisplayString,
					ommp82PlusFcTransmitDigitalLossOfLinkDefectAlarm			DisplayString,
					ommp82PlusFcTrasnmitLossOfSynchronizationDefectAlarm			DisplayString,
					ommp82PlusFcReceiveDigitalLossOfLinkDefectAlarm				DisplayString,
					ommp82PlusFcReceiveLossOfSynchronizationDefectAlarm			DisplayString,
					ommp82PlusFcReceiveTransitionDetectDefectAlarm				DisplayString,
					ommp82PlusFcReceiveAnalogLossOfSignalDefectAlarm			DisplayString,
					ommp82PlusFcReceiveLineCodeViolationDefectAlarm				DisplayString,
					ommp82PlusGfpCsfSignalFailAlarm						DisplayString,
					ommp82PlusGfpCsfLinkFailAlarm						DisplayString,
					ommp82PlusGfpCoreHeaderErrorAlarm					DisplayString,
					ommp82PlusGfpExtentionHeaderErrorAlarm					DisplayString,
					ommp82PlusAlarmQueryTableRowStatus					RowStatus
		}

--*****************************************************************************
--				OPTICAL	ALARMS
--***************************************************************************** 

	ommp82PlusXfpInputPowerFailureAlarm OBJECT-TYPE
              SYNTAX  DisplayString
              MAX-ACCESS  read-only
              STATUS  current
              DESCRIPTION
			"If optical input power at requested interface is less than
			-20dbm, this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 1 }

	ommp82PlusXfpOutputPowerFailureAlarm OBJECT-TYPE
              SYNTAX  DisplayString
              MAX-ACCESS  read-only
              STATUS  current
              DESCRIPTION
			"If optical output power at requested interface is less than
			-10dbm, this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 2 }

	ommp82PlusXfpHighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 3 }

	ommp82PlusXfpLowTemperatureAlarm OBJECT-TYPE
              SYNTAX  DisplayString
              MAX-ACCESS  read-only
              STATUS  current
              DESCRIPTION
			"If optical temperature at requested interface is lower 
			than the Low Temperature Alarm Threshold, alarm will be 
			generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 4 }

	ommp82PlusXfpHighTemperatureWarning OBJECT-TYPE
              SYNTAX  DisplayString
              MAX-ACCESS  read-only
              STATUS  current
              DESCRIPTION
			"If optical temperature at requested interface is greater
			than the High Temperature Warning Threshold, this alarm 
			will be generated.
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 5 }

	ommp82PlusXfpLowTemperatureWarning OBJECT-TYPE
              SYNTAX  DisplayString
              MAX-ACCESS  read-only
              STATUS  current
              DESCRIPTION
			"If optical temperature at requested interface is lesser
			than the Low Temperature Warning Threshold, this alarm 
			will be generated.
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 6 }

	ommp82PlusXfpHighBiasCurrentAlarm OBJECT-TYPE
              SYNTAX  DisplayString
              MAX-ACCESS  read-only
              STATUS  current
              DESCRIPTION
			"If optical transmit bias current at requested interface
			is greater than the High Bias Current Alarm Threshold, 
			this alarm will be generated.
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 7 }

	ommp82PlusXfpLowBiasCurrentAlarm OBJECT-TYPE
              SYNTAX  DisplayString
              MAX-ACCESS  read-only
              STATUS  current
              DESCRIPTION
			"If optical transmit bias current at requested interface
			is lesser than the Low Bias Current Alarm Threshold, 
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 8 }

	ommp82PlusXfpHighBiasCurrentWarning OBJECT-TYPE
              SYNTAX  DisplayString
              MAX-ACCESS  read-only
              STATUS  current
              DESCRIPTION
			"If optical transmit bias current at requested interface
			is greater than the High Bias Current Warning Threshold,
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 9 }

	ommp82PlusXfpLowBiasCurrentWarning OBJECT-TYPE
              SYNTAX  DisplayString
              MAX-ACCESS  read-only
              STATUS  current
              DESCRIPTION
			"If optical transmit bias current at requested interface
			is lesser than the Low Bias Current Warning Threshold, 
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 10 }

	ommp82PlusXfpInputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 11 }

	ommp82PlusXfpInputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 12 }

	ommp82PlusXfpInputHighPowerWarning OBJECT-TYPE
              SYNTAX  DisplayString
              MAX-ACCESS  read-only
              STATUS  current
              DESCRIPTION
			"If optical Input power at requested interface is 
			greater than the High Input Power Warning Threshold, 
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 13 }

	ommp82PlusXfpInputLowPowerWarning OBJECT-TYPE
              SYNTAX  DisplayString
              MAX-ACCESS  read-only
              STATUS  current
              DESCRIPTION
			"If optical Input power at requested interface is lesser
			than the Low Input Power Warning Threshold, this alarm 
			will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 14 }

	ommp82PlusXfpOutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 15 }

	ommp82PlusXfpOutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 16 }

	ommp82PlusXfpOutputHighPowerWarning OBJECT-TYPE
              SYNTAX  DisplayString
              MAX-ACCESS  read-only
              STATUS  current
              DESCRIPTION
			"If optical Output power at requested interface is 
			greater than the High Output Power Warning Threshold, 
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 17 }

	ommp82PlusXfpOutputLowPowerWarning OBJECT-TYPE
              SYNTAX  DisplayString
              MAX-ACCESS  read-only
              STATUS  current
              DESCRIPTION
			"If optical Output power at requested interface is 
			lesser than the Low Output Power Warning Threshold, 
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 18 }

	ommp82PlusXfpHighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 19 }

	ommp82PlusXfpLowSupplyVoltageAlarm OBJECT-TYPE
              SYNTAX  DisplayString
              MAX-ACCESS  read-only
              STATUS  current
              DESCRIPTION
			"If optical Supply Voltage at requested interface is 
			lesser than the Low Supply Voltage Alarm Threshold, 
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 20 }

	ommp82PlusXfpHighSupplyVoltageWarning OBJECT-TYPE
              SYNTAX  DisplayString
              MAX-ACCESS  read-only
              STATUS  current
              DESCRIPTION
			"If optical Supply Voltage at requested interface is 
			higher than the High Supply Voltage Warning Threshold,
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 21 }

	ommp82PlusXfpLowSupplyVoltageWarning OBJECT-TYPE
              SYNTAX  DisplayString
              MAX-ACCESS  read-only
              STATUS  current
              DESCRIPTION
			"If optical Supply Voltage at requested interface is 
			lesser than the Low Supply Voltage Warning Threshold, 
			this alarm will be generated
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 22 }

	ommp82PlusXfpPresenceAbsenceNotification OBJECT-TYPE
              SYNTAX  DisplayString
              MAX-ACCESS  read-only
              STATUS  current
              DESCRIPTION
			"Whenever the XFP is jacked in or jacked out, this 
			notification is generated.
			-----------------------------
			ommp82PlusInterfaceNumber:
			9 - LINE-1
			10 - LINE-2
			-----------------------------
			Values :
			If Alarm is Present(module absent) - Date and Time Stamp
				    eg:2017-5-18,9:47:20.0,+5:30
			If Alarm is Absent(module present) - 0
			-----------------------------"
		::= { ommp82PlusAlarmQueryEntry 23 }

	ommp82PlusSfpInputPowerFailureAlarm OBJECT-TYPE
              SYNTAX  DisplayString
              MAX-ACCESS  read-only
              STATUS  current
              DESCRIPTION
			"If optical input power at requested interface is less than
			-20dbm, this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 41 }

	ommp82PlusSfpOutputPowerFailureAlarm OBJECT-TYPE
              SYNTAX  DisplayString
              MAX-ACCESS  read-only
              STATUS  current
              DESCRIPTION
			"If optical output power at requested interface is less than
			-10dbm, this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 42 }

	ommp82PlusSfpHighTemperatureAlarm OBJECT-TYPE
              SYNTAX  DisplayString
              MAX-ACCESS  read-only
              STATUS  current
              DESCRIPTION
			"If optical temperature at requested interface is greater 
			than the High Temperature Alarm Threshold, alarm will 
			be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 43 }

	ommp82PlusSfpLowTemperatureAlarm OBJECT-TYPE
              SYNTAX  DisplayString
              MAX-ACCESS  read-only
              STATUS  current
              DESCRIPTION
			"If optical temperature at requested interface is lesser 
			than the Low Temperature Alarm Threshold, alarm will be 
			generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 44 }

	ommp82PlusSfpHighTemperatureWarning OBJECT-TYPE
              SYNTAX  DisplayString
              MAX-ACCESS  read-only
              STATUS  current
              DESCRIPTION
			"If optical temperature at requested interface is greater
			than the High Temperature Warning Threshold, this alarm 
			will be generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 45 }

	ommp82PlusSfpLowTemperatureWarning OBJECT-TYPE
              SYNTAX  DisplayString
              MAX-ACCESS  read-only
              STATUS  current
              DESCRIPTION
			"If optical temperature at requested interface is lesser
			than the Low Temperature Warning Threshold, this alarm 
			will be generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 46 }

	ommp82PlusSfpHighBiasCurrentAlarm OBJECT-TYPE
              SYNTAX  DisplayString
              MAX-ACCESS  read-only
              STATUS  current
              DESCRIPTION
			"If optical transmit bias current at requested interface
			is greater than the High Bias Current Alarm Threshold, 
			this alarm will be generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 47 }

	ommp82PlusSfpLowBiasCurrentAlarm OBJECT-TYPE
              SYNTAX  DisplayString
              MAX-ACCESS  read-only
              STATUS  current
              DESCRIPTION
			"If optical transmit bias current at requested interface
			is lesser than the Low Bias Current Alarm Threshold, 
			this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 48 }

	ommp82PlusSfpHighBiasCurrentWarning OBJECT-TYPE
              SYNTAX  DisplayString
              MAX-ACCESS  read-only
              STATUS  current
              DESCRIPTION
			"If optical transmit bias current at requested interface
			is greater than the High Bias Current Warning Threshold,
			this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 49 }

	ommp82PlusSfpLowBiasCurrentWarning OBJECT-TYPE
              SYNTAX  DisplayString
              MAX-ACCESS  read-only
              STATUS  current
              DESCRIPTION
			"If optical transmit bias current at requested interface
			is lesser than the Low Bias Current Warning Threshold, 
			this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 50 }

	ommp82PlusSfpInputHighPowerAlarm OBJECT-TYPE
              SYNTAX  DisplayString
              MAX-ACCESS  read-only
              STATUS  current
              DESCRIPTION
			"If optical Input power at requested interface is 
			greater than the High Input Power Alarm Threshold, this 
			alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 51 }

	ommp82PlusSfpInputLowPowerAlarm OBJECT-TYPE
              SYNTAX  DisplayString
              MAX-ACCESS  read-only
              STATUS  current
              DESCRIPTION
			"If optical Input power at requested interface is lesser
			than the Low Input Power Alarm Threshold, this alarm 
			will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 52 }

	ommp82PlusSfpInputHighPowerWarning OBJECT-TYPE
              SYNTAX  DisplayString
              MAX-ACCESS  read-only
              STATUS  current
              DESCRIPTION
			"If optical Input power at requested interface is 
			greater than the High Input Power Warning Threshold, 
			this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 53 }

	ommp82PlusSfpInputLowPowerWarning OBJECT-TYPE
              SYNTAX  DisplayString
              MAX-ACCESS  read-only
              STATUS  current
              DESCRIPTION
			"If optical Input power at requested interface is lesser
			than the Low Input Power Warning Threshold, this alarm 
			will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 54 }

	ommp82PlusSfpOutputHighPowerAlarm OBJECT-TYPE
              SYNTAX  DisplayString
              MAX-ACCESS  read-only
              STATUS  current
              DESCRIPTION
			"If optical Output power at requested interface is 
			greater than the High Output Power Alarm Threshold, this
			alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 55 }

	ommp82PlusSfpOutputLowPowerAlarm OBJECT-TYPE
              SYNTAX  DisplayString
              MAX-ACCESS  read-only
              STATUS  current
              DESCRIPTION
			"If optical Output power at requested interface is 
			lesser than the Low Output Power Alarm Threshold, this 
			alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 56 }

	ommp82PlusSfpOutputHighPowerWarning OBJECT-TYPE
              SYNTAX  DisplayString
              MAX-ACCESS  read-only
              STATUS  current
              DESCRIPTION
			"If optical Output power at requested interface is 
			greater than the High Output Power Warning Threshold, 
			this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 57 }

	ommp82PlusSfpOutputLowPowerWarning OBJECT-TYPE
              SYNTAX  DisplayString
              MAX-ACCESS  read-only
              STATUS  current
              DESCRIPTION
			"If optical Output power at requested interface is 
			lesser than the Low Output Power Warning Threshold, this
			alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 58 }

	ommp82PlusSfpHighSupplyVoltageAlarm OBJECT-TYPE
              SYNTAX  DisplayString
              MAX-ACCESS  read-only
              STATUS  current
              DESCRIPTION
			"If optical Supply Voltage at requested interface is 
			greater than the High Supply Voltage Alarm Threshold, 
			this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 59 }

	ommp82PlusSfpLowSupplyVoltageAlarm OBJECT-TYPE
              SYNTAX  DisplayString
              MAX-ACCESS  read-only
              STATUS  current
              DESCRIPTION
			"If optical Supply Voltage at requested interface is 
			lesser than the Low Supply Voltage Alarm Threshold, this
			alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 60 }

	ommp82PlusSfpHighSupplyVoltageWarning OBJECT-TYPE
              SYNTAX  DisplayString
              MAX-ACCESS  read-only
              STATUS  current
              DESCRIPTION
			"If optical Supply Voltage at requested interface is 
			greater than the High Supply Voltage Warning Threshold, 
			this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 61 }

	ommp82PlusSfpLowSupplyVoltageWarning OBJECT-TYPE
              SYNTAX  DisplayString
              MAX-ACCESS  read-only
              STATUS  current
              DESCRIPTION
			"If optical Supply Voltage at requested interface is 
			lesser than the Low Supply Voltage Warning Threshold, 
			this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 62 }

	ommp82PlusSfpPresenceAbsenceNotification OBJECT-TYPE
              SYNTAX  DisplayString
              MAX-ACCESS  read-only
              STATUS  current
              DESCRIPTION
			"Whenever the SFP is jacked in or jacked out, this 
			notification is generated.
			-----------------------------
			ommp82PlusInterfaceNumber:
			1 to 8 - CLIENT-1 to CLIENT-8
			-----------------------------
			Values :
			If Alarm is Present(module absent) - Date and Time Stamp
				    eg:2017-5-18,9:47:20.0,+5:30
			If Alarm is Absent(module present) - 0
			-----------------------------"
		::= { ommp82PlusAlarmQueryEntry 63 }

	ommp82PlusSfpTransmitFaultPresenceAlarm OBJECT-TYPE
              SYNTAX  DisplayString
              MAX-ACCESS  read-only
              STATUS  current
              DESCRIPTION
			"Whenever the SFP laser is unable to generate
			any data this alarm will be generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 64 }

	ommp82PlusOtuLossOfSignalAlarm OBJECT-TYPE
              SYNTAX  DisplayString
              MAX-ACCESS  read-only
              STATUS  current
              DESCRIPTION
			"For port configured with OTU2/OTU1 traffic,
			if there is no signal received then OTU-LOS Alarm
			is generated.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 81 }

	ommp82PlusOtuLossOfFrameAlarm OBJECT-TYPE
              SYNTAX  DisplayString
              MAX-ACCESS  read-only
              STATUS  current
              DESCRIPTION
			"For port configured with OTU2/OTU1 traffic, if
			OTU2/OTU1 frame received are in out-of-frame (OOF)
			state for 3 ms, then OTU-LOF Alarm is generated
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 82 }

	ommp82PlusOtuOutOfFrameAlarm OBJECT-TYPE
              SYNTAX  DisplayString
              MAX-ACCESS  read-only
              STATUS  current
              DESCRIPTION
			"For port configured with OTU2/OTU1 traffic, if 5
			consecutive OTU2/OTU1 frames are received with
			invalid framing patterns then OOF Alarm is
			generated
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 83 }

	ommp82PlusOtuLossOfMultiFrameAlarm OBJECT-TYPE
              SYNTAX  DisplayString
              MAX-ACCESS  read-only
              STATUS  current
              DESCRIPTION
			"For port configured with OTU2/OTU1 traffic, if 
			OTU2/OTU1 frame received are in Out-of-multiframe
			(OOM) state for 3 ms then LOM Alarm is generated.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 84 }

	ommp82PlusOtuOutOfMultiFrameAlarm OBJECT-TYPE
              SYNTAX  DisplayString
              MAX-ACCESS  read-only
              STATUS  current
              DESCRIPTION
			"For port configured with OTU2/OTU1 traffic, if the
			received MFAS does not match with the expected multi
			frame number for five consecutive frames then
			OOM Alarm is generated.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 85 }

	ommp82PlusOtuSignalFailAlarm OBJECT-TYPE
              SYNTAX  DisplayString
              MAX-ACCESS  read-only
              STATUS  current
              DESCRIPTION
			"For port configured with OTU2/OTU1 traffic, 
			OTU SF alarm is generated when BIP errors evaluated by 
			SM field of OTU2/OTU1 frame exceeds the 
			'ommp82PlusOtuSignalFailThreshold' threshold
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 86 }

	ommp82PlusOtuSignalDegradeAlarm OBJECT-TYPE
              SYNTAX  DisplayString
              MAX-ACCESS  read-only
              STATUS  current
              DESCRIPTION
			"For port configured with OTU2/OTU1 traffic, 
			OTU SD alarm is generated when BIP errors evaluated by 
			SM field of OTU2/OTU1 frame exceeds the 
			'ommp82PlusOtuSignalDegradeThreshold' threshold.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 87 }

	ommp82PlusOtuAlarmIndicationSignalAlarm OBJECT-TYPE
              SYNTAX  DisplayString
              MAX-ACCESS  read-only
              STATUS  current
              DESCRIPTION
			"For port configured with OTU2/OTU1 traffic,
			OTU-AIS is generated and transmitted in forward 
			direction, when LOS has been detected at far-end port.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 88 }

	ommp82PlusOtuIncomingAlignmentErrorAlarm OBJECT-TYPE
              SYNTAX  DisplayString
              MAX-ACCESS  read-only
              STATUS  current
              DESCRIPTION
			"For port configured with OTU2/OTU1 traffic, IAE alarms
			shall be declared if the IAE bit in the SM overhead
			field (byte 3, bit 6) is 1 for 5 consecutive frames. 
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 89 }

	ommp82PlusOtuTraceIdentifierMismatchAlarm OBJECT-TYPE
              SYNTAX  DisplayString
              MAX-ACCESS  read-only
              STATUS  current
              DESCRIPTION
			"For port configured with OTU2/OTU1 traffic, when there
			is a mismatch between the incoming and the expected
			Trail Trace Identifier(TTI) at the SM section,
			OTU-TIM alarm is generated.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 90 }

	ommp82PlusOtuBackwardIncomingAlignmentErrorAlarm OBJECT-TYPE
              SYNTAX  DisplayString
              MAX-ACCESS  read-only
              STATUS  current
              DESCRIPTION
			"For port configured with OTU2/OTU1 traffic, 
			the presence of this alarm conveys that an incoming
			alignment error(IAE) condition is detected
			by the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 91 }

	ommp82PlusOtuBackwardDefectIndicationAlarm OBJECT-TYPE
              SYNTAX  DisplayString
              MAX-ACCESS  read-only
              STATUS  current
              DESCRIPTION
			"For port configured with OTU2/OTU1 traffic,
			the presence of this alarm conveys that a
			a defect like LOS, LOF, LOM has been detected in the
			by the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 92 }

	ommp82PlusOduSignalFailAlarm OBJECT-TYPE
              SYNTAX  DisplayString
              MAX-ACCESS  read-only
              STATUS  current
              DESCRIPTION
			"For port configured with OTU2/OTU1 traffic, ODU-SF
			alarm is generated when BIP errors evaluated by 
			PM field of OTU2 frame exceeds the 
			'ommp82PlusOduSignalFailThreshold' threshold.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 111 }

	ommp82PlusOduSignalDegradeAlarm OBJECT-TYPE
              SYNTAX  DisplayString
              MAX-ACCESS  read-only
              STATUS  current
              DESCRIPTION
			"For port configured with OTU2/OTU1 traffic,ODU-SD
			alarm is generated when BIP errors evaluated by 
			PM field of OTU2 frame exceeds the 	
			'ommp82PlusOduSignalDegradeThreshold' threshold.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 112 }

	ommp82PlusOduAlarmIndicationSignalAlarm OBJECT-TYPE
              SYNTAX  DisplayString
              MAX-ACCESS  read-only
              STATUS  current
              DESCRIPTION
			"For port configured with OTU2/OTU1 traffic, when the incoming
			OTU2 frame has all 1s in the entire ODUk signal,
			excluding the frame alignment overhead (FA OH),
			OTUk overhead (OTUk OH) and ODUk FTFL, this alarm is
			generated
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 113 }

	ommp82PlusOduTcm1IncomingAlignmentErrorAlarm OBJECT-TYPE
              SYNTAX  DisplayString
              MAX-ACCESS  read-only
              STATUS  current
              DESCRIPTION
			"For port configured with OTU2/OTU1 traffic, TCM1 IAE
			shall be declared if the accepted STAT information is
			0b010
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 114 }

	ommp82PlusOduTcm2IncomingAlignmentErrorAlarm OBJECT-TYPE
              SYNTAX  DisplayString
              MAX-ACCESS  read-only
              STATUS  current
              DESCRIPTION
			"For port configured with OTU2/OTU1 traffic, TCM2 IAE
			shall be declared if the accepted STAT information is
			0b010
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 115 }

	ommp82PlusOduTcm3IncomingAlignmentErrorAlarm OBJECT-TYPE
              SYNTAX  DisplayString
              MAX-ACCESS  read-only
              STATUS  current
              DESCRIPTION
			"For port configured with OTU2/OTU1 traffic, TCM3 IAE
			shall be declared if the accepted STAT information is
			0b010
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 116 }

	ommp82PlusOduTcm4IncomingAlignmentErrorAlarm OBJECT-TYPE
              SYNTAX  DisplayString
              MAX-ACCESS  read-only
              STATUS  current
              DESCRIPTION
			"For port configured with OTU2/OTU1 traffic, TCM4 IAE
			shall be declared if the accepted STAT information is
			0b010
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 117 }

	ommp82PlusOduTcm5IncomingAlignmentErrorAlarm OBJECT-TYPE
              SYNTAX  DisplayString
              MAX-ACCESS  read-only
              STATUS  current
              DESCRIPTION
			"For port configured with OTU2/OTU1 traffic, TCM5 IAE
			shall be declared if the accepted STAT information is
			0b010
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 118 }

	ommp82PlusOduTcm6IncomingAlignmentErrorAlarm OBJECT-TYPE
              SYNTAX  DisplayString
              MAX-ACCESS  read-only
              STATUS  current
              DESCRIPTION
			"For port configured with OTU2/OTU1 traffic, TCM6 IAE
			shall be declared if the accepted STAT information is
			0b010
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 119 }

	ommp82PlusOduTraceIdentifierMismatchAlarm OBJECT-TYPE
              SYNTAX  DisplayString
              MAX-ACCESS  read-only
              STATUS  current
              DESCRIPTION
			"For port configured with OTU2/OTU1 traffic, when there
			is a mismatch between the incoming and the expected
			Trail Trace Identifier(TTI) at the PM section,
			ODU-TIM alarm is generated.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 120 }

	ommp82PlusOduLockedDefectAlarm OBJECT-TYPE
              SYNTAX  DisplayString
              MAX-ACCESS  read-only
              STATUS  current
              DESCRIPTION
			"For port configured with OTU2/OTU1 traffic, 
			the locked maintenance signal is generated on operator
			request in order to lock the signal from user access. It
			consists of a repeating 0b0101 0101 pattern in the
			entire ODUk signal, which excludes the Frame Alignment
			overhead and the OTUk overhead.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 121 }

	ommp82PlusOduOpenConnectionIndicationAlarm OBJECT-TYPE
              SYNTAX  DisplayString
              MAX-ACCESS  read-only
              STATUS  current
              DESCRIPTION
			"For port configured with OTU2/OTU1 traffic, 
			an open connection indication is sent downstream when
			no signal is detected from upstream. It consists of a
			repeating 0b0110 0110 pattern in the entire ODUk signal,
			which excludes the Frame Alignment overhead and the
			OTUk overhead.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 122 }

	ommp82PlusOduBackwardDefectIndicationAlarm OBJECT-TYPE
              SYNTAX  DisplayString
              MAX-ACCESS  read-only
              STATUS  current
              DESCRIPTION
			"For port configured with OTU2/OTU1 traffic, 
			the presence of this alarm conveys that either of
			OTU-LOS or OTU-LOF or OTU-LOM or OTU-AIS or ODU-AIS
			or ODU-OCI or ODU-LCK condition is detected
			by the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 123 }

	ommp82PlusOduTcm1BackwardIncomingAlignmentErrorAlarm OBJECT-TYPE
              SYNTAX  DisplayString
              MAX-ACCESS  read-only
              STATUS  current
              DESCRIPTION
			"For port configured with OTU2/OTU1 traffic, 
			the presence of this alarm conveys that
			TCM1 incoming alignment error (IAE) condition is 
			detected in the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 124 }

	ommp82PlusOduTcm2BackwardIncomingAlignmentErrorAlarm OBJECT-TYPE
              SYNTAX  DisplayString
              MAX-ACCESS  read-only
              STATUS  current
              DESCRIPTION
			"For port configured with OTU2/OTU1 traffic, 
			the presence of this alarm conveys that
			TCM2 incoming alignment error (IAE) condition is 
			detected in the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 125 }

	ommp82PlusOduTcm3BackwardIncomingAlignmentErrorAlarm OBJECT-TYPE
              SYNTAX  DisplayString
              MAX-ACCESS  read-only
              STATUS  current
              DESCRIPTION
			"For port configured with OTU2/OTU1 traffic, 
			the presence of this alarm conveys that
			TCM3 incoming alignment error (IAE) condition is 
			detected in the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 126 }


	ommp82PlusOduTcm4BackwardIncomingAlignmentErrorAlarm OBJECT-TYPE
              SYNTAX  DisplayString
              MAX-ACCESS  read-only
              STATUS  current
              DESCRIPTION
			"For port configured with OTU2/OTU1 traffic, 
			the presence of this alarm conveys that
			TCM4 incoming alignment error (IAE) condition is 
			detected in the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 127 }

	ommp82PlusOduTcm5BackwardIncomingAlignmentErrorAlarm OBJECT-TYPE
              SYNTAX  DisplayString
              MAX-ACCESS  read-only
              STATUS  current
              DESCRIPTION
			"For port configured with OTU2/OTU1 traffic, 
			the presence of this alarm conveys that
			TCM5 incoming alignment error (IAE) condition is 
			detected in the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 128 }

	ommp82PlusOduTcm6BackwardIncomingAlignmentErrorAlarm OBJECT-TYPE
              SYNTAX  DisplayString
              MAX-ACCESS  read-only
              STATUS  current
              DESCRIPTION
			"For port configured with OTU2/OTU1 traffic, 
			the presence of this alarm conveys that
			TCM6 incoming alignment error (IAE) condition is 
			detected in the far-end card.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 129 }

	ommp82PlusOduLossOfFrameLossOfMultiframeAlarm OBJECT-TYPE
              SYNTAX  DisplayString
              MAX-ACCESS  read-only
              STATUS  current
              DESCRIPTION
			"While demultiplexing the incoming OPU2 frame into the
			ODU1, if the start of a ODU1 frame is not found	then 
			this alarm is generated. Since the alarm is generated at
			the demultiplexing level, the alarm cannot be
			represented with respect to a client/line port, as one
			ODU1 slice might have multiple client data. This
			property is w.r.t slice
			-----------------------------
			ommp82PlusInterfaceNumber:
			ODU1 slices demapped from OTU2 signal received at LINE-1
			5 - ODU1 Slice 5
			6 - ODU1 Slice 6
			7 - ODU1 Slice 7
			8 - ODU1 Slice 8
			ODU1 slices demapped from OTU2 signal received at LINE-2
			1 - ODU1 Slice 1
			2 - ODU1 Slice 2
			3 - ODU1 Slice 3
			4 - ODU1 Slice 4
			-----------------------------
			Values :
			If Alarm is Present - Date and Time Stamp
				    eg:2017-5-18,9:47:20.0,+5:30
			If Alarm is Absent  - 0
			-----------------------------"
		::= { ommp82PlusAlarmQueryEntry 130 }

	ommp82PlusOpuPayloadMismatchAlarm OBJECT-TYPE
              SYNTAX  DisplayString
              MAX-ACCESS  read-only
              STATUS  current
              DESCRIPTION
			"For port configured with OTU2/OTU1 traffic, 
			OPU-PLM Alarm is declared if the accepted payload type
			is not equal to the expected payload type.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 135 }

	ommp82PlusOchLossOfPayloadAlarm OBJECT-TYPE
              SYNTAX  DisplayString
              MAX-ACCESS  read-only
              STATUS  current
              DESCRIPTION
			"If input power level at the XFP is less than 
			-21dbm this this alarm will be generated.
			-----------------------------
			ommp82PlusInterfaceNumber:
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 136 }

	ommp82PlusSdhLossOfSignalAlarm OBJECT-TYPE
              SYNTAX  DisplayString
              MAX-ACCESS  read-only
              STATUS  current
              DESCRIPTION
			"For port configured with STM1/4/16 traffic, if there
			is no signal received then SDH-LOS Alarm is 
			generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 141 }

	ommp82PlusSdhOutOfFrameAlarm OBJECT-TYPE
              SYNTAX  DisplayString
              MAX-ACCESS  read-only
              STATUS  current
              DESCRIPTION
			"For port configured with STM1/4/16 traffic, when
			several consecutive SDH frames have A1, A2 bytes errored
			for a period more than 625us, this alarm will be
			generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 142 }

	ommp82PlusSdhLossOfFrameAlarm OBJECT-TYPE
              SYNTAX  DisplayString
              MAX-ACCESS  read-only
              STATUS  current
              DESCRIPTION
			"For port configured with STM1/4/16 traffic, 
			If SDH frame received are out-of-frame (OOF) state for 
			3 ms then LOF alarm is generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 143 }

	ommp82PlusSdhRsAlarmIndicationSignalAlarm OBJECT-TYPE
              SYNTAX  DisplayString
              MAX-ACCESS  read-only
              STATUS  current
              DESCRIPTION
			"For port configured with STM1/4/16 traffic, RS-AIS
			alarm is indicated when there is no signal 
			received by the far-end port.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 144 }

	ommp82PlusSdhRsTraceIdentifierMismatchAlarm OBJECT-TYPE
              SYNTAX  DisplayString
              MAX-ACCESS  read-only
              STATUS  current
              DESCRIPTION
			"For port configured with STM1/4/16 traffic, this alarms
			is generated when there is a mismatch of the accepted
			and expected trace identifier in J0 byte.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 145 }

	ommp82PlusSdhAuAlarmIndicationSignalAlarm OBJECT-TYPE
              SYNTAX  DisplayString
              MAX-ACCESS  read-only
              STATUS  current
              DESCRIPTION
			"For port configured with STM1/4/16 traffic, AU-AIS
			is generated if all ones are detected in the H1 and H2
			bytes of the AU pointer.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 146 }

	ommp82PlusSdhAuLossOfPointerAlarm OBJECT-TYPE
              SYNTAX  DisplayString
              MAX-ACCESS  read-only
              STATUS  current
              DESCRIPTION
			"For port configured with STM1/4/16 traffic, 
			LOP state occurs when N consecutive invalid pointers
			are received or N consecutive New Data Flags (NDF)
			are received where N = 8, 9, or 10. LOP state is 
			cleared when three equal valid pointers or three
			consecutive AIS indications are received.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 147 }

	ommp82PlusSdhMsAlarmIndicationSignalAlarm OBJECT-TYPE
              SYNTAX  DisplayString
              MAX-ACCESS  read-only
              STATUS  current
              DESCRIPTION
			"For port configured with STM1/4/16 traffic, 
			MS-AIS is an alarm indication signal (AIS) is a signal 
			sent downstream as an indication that an upstream
			defect has been detected.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 148 }

	ommp82PlusSdhMsRemoteErrorIndicationAlarm OBJECT-TYPE
              SYNTAX  DisplayString
              MAX-ACCESS  read-only
              STATUS  current
              DESCRIPTION
			"For port configured with STM1/4/16 traffic, 
			this alarm is an indication returned to a transmitting
			node (source) that an errored block has been detected at
			the receiving node (sink).
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 149 }

	ommp82PlusSdhMsRemoteDefectIndicationAlarm OBJECT-TYPE
              SYNTAX  DisplayString
              MAX-ACCESS  read-only
              STATUS  current
              DESCRIPTION
			"For port configured with STM1/4/16 traffic, 
			MS-RDI is a signal returned to the transmitting equipment 
			upon detecting a LOS, LOF, or MS-AIS defect
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 150 }

	ommp82PlusSdhMsRemoteFailureIndicationAlarm OBJECT-TYPE
              SYNTAX  DisplayString
              MAX-ACCESS  read-only
              STATUS  current
              DESCRIPTION
			"For port configured with STM1/4/16 traffic,
			a failure is a defect that persists beyond the maximum
			time allocated to the transmission system protection
			mechanisms. When this situation occurs, an RFI is sent
			to the far end and will initiate a path protection
			switch if this function has been provisioned.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 151 }

	ommp82PlusSdhMsB2ExcessiveErrorAlarm OBJECT-TYPE
              SYNTAX  DisplayString
              MAX-ACCESS  read-only
              STATUS  current
              DESCRIPTION
			"For port configured with STM1/4/16 traffic, 
			B2 SF alarm is generated when Parity errors evaluated 
			by byte B2 of SDH frame exceeds the 
			'ommp82PlusSdhMsB2ExcessiveErrorThreshold' threshold.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 152 }

	ommp82PlusSdhMsB2SignalDegradeAlarm OBJECT-TYPE
              SYNTAX  DisplayString
              MAX-ACCESS  read-only
              STATUS  current
              DESCRIPTION
			"For port configured with STM1/4/16 traffic,
			B2 SD alarm is generated when Parity errors evaluated 
			by byte B2 of SDH frame exceeds the 
			'ommp82PlusSdhMsB2SignalDegradeThreshold' threshold.
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 153 }

	ommp82PlusSdhLossOfSequenceSynchronisationAlarm OBJECT-TYPE
              SYNTAX  DisplayString
              MAX-ACCESS  read-only
              STATUS  current
              DESCRIPTION
			"For port configured with STM1/4/16 traffic, 
			Sequence synchronisation shall be considered to be lost
			and re-synchronisation shall be started if:
			The bit error ratio is >= 0.20 during an integration
			interval of 1 second; or
			It can be unambiguously identified that the test
			sequence and the reference sequence are out of phase.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 154 }

	ommp82PlusSdhLowerOrderPathPayloadLabelMismatchAlarm OBJECT-TYPE
              SYNTAX  DisplayString
              MAX-ACCESS  read-only
              STATUS  current
              DESCRIPTION
			"Reserved for further study
			-----------------------------
			ommp82PlusInterfaceNumber:
			1 to 8 - CLIENT-1 to CLIENT-8
			9 - LINE-1
			10 - LINE-2
			-----------------------------
			Values :
			If Alarm is Present - Date and Time Stamp
				    eg:2017-5-18,9:47:20.0,+5:30
			If Alarm is Absent  - 0
			-----------------------------"
		::= { ommp82PlusAlarmQueryEntry 155 }

	ommp82PlusSdhLowerOrderPathUnequippedAlarm OBJECT-TYPE
              SYNTAX  DisplayString
              MAX-ACCESS  read-only
              STATUS  current
              DESCRIPTION
			"For port configured with STM1/4/16 traffic,
			these signals indicate to downstream transport
			processing functions (refer to ITU-T Rec. G.803) that
			the virtual container is unoccupied,
			not connected to a path termination source function.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 156 }

	ommp82PlusEthernetLossOfSignalAlarm OBJECT-TYPE
              SYNTAX  DisplayString
              MAX-ACCESS  read-only
              STATUS  current
              DESCRIPTION
			"For port configured with 
			GE-GFP-F/FE-GFP-F/GE-GFP-T/FE-GFP-T traffic,
			if there is no signal received then LOS Alarm is 
			generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 171 }

	ommp82PlusEthernetLossOfSignalSyncAlarm OBJECT-TYPE
              SYNTAX  DisplayString
              MAX-ACCESS  read-only
              STATUS  current
              DESCRIPTION
			"For port configured with 
			GE-GFP-F/FE-GFP-F/GE-GFP-T/FE-GFP-T traffic,
			when the receive interface does not achieve PCS
		        sync it is called Loss of Sync.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 172 }

	ommp82PlusEthernetLinkFailureAlarm OBJECT-TYPE
              SYNTAX  DisplayString
              MAX-ACCESS  read-only
              STATUS  current
              DESCRIPTION
			"For port configured with 
			GE-GFP-F/FE-GFP-F/GE-GFP-T/FE-GFP-T traffic,
			in the event of ingress client signal failure, 
			the link failure alarm is generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 173 }

	ommp82PlusEthernetAutoNegotiationAlarm OBJECT-TYPE
              SYNTAX  DisplayString
              MAX-ACCESS  read-only
              STATUS  current
              DESCRIPTION
			"For port configured with 
			GE-GFP-F/GE-GFP-T traffic,
			if auto-negotiation is failed to establish between 
			link-partners, this alarm will get generated
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 174 }

	ommp82PlusEthernetFrameCheckSequenceAlarm OBJECT-TYPE
              SYNTAX  DisplayString
              MAX-ACCESS  read-only
              STATUS  current
              DESCRIPTION
			"For port configured with 
			GE-GFP-F/FE-GFP-F/GE-GFP-T/FE-GFP-T traffic,
			in the incoming ethernet frame, if the FCS value in the
			FCS byte and the FCS value calculated for the payload
			of the frame doesnt match, then number of FCS errors
			is incremented. If in one second, 50 such FCS errors
			are got, then FCS this alarm will be generated. 
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 175 }

	ommp82PlusEthernetCarrierStatusAlarm OBJECT-TYPE
              SYNTAX  DisplayString
              MAX-ACCESS  read-only
              STATUS  current
              DESCRIPTION
			"For port configured with 
			GE-GFP-F/FE-GFP-F/GE-GFP-T/FE-GFP-T traffic,
			whenever there is an absence of the carrier signal
			i.e. carrier sense loss occurs this alarm is generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 176 }

	ommp82PlusEthernetHighBerAlarm OBJECT-TYPE
              SYNTAX  DisplayString
              MAX-ACCESS  read-only
              STATUS  current
              DESCRIPTION
			"For port configured with 
			GE-GFP-F/FE-GFP-F/GE-GFP-T/FE-GFP-T traffic,
			this alarm is generated when signal BER is
			greater than 1e−4. 
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 177 }

	ommp82PlusEthernetLocalFaultAlarm OBJECT-TYPE
              SYNTAX  DisplayString
              MAX-ACCESS  read-only
              STATUS  current
              DESCRIPTION
			"For port configured with 
			GE-GFP-F/FE-GFP-F/GE-GFP-T/FE-GFP-T traffic,
			if fault is detected on the receive data path then Local
			Fault Alarm is generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 178 }

	ommp82PlusEthernetRemoteFaultAlarm OBJECT-TYPE
              SYNTAX  DisplayString
              MAX-ACCESS  read-only
              STATUS  current
              DESCRIPTION
			"For port configured with 
			GE-GFP-F/FE-GFP-F/GE-GFP-T/FE-GFP-T traffic,
			if fault is detected on the transmit data path then 
			Remote Fault Alarm is generated.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 179 }

	ommp82PlusFcTransmitDisparityInversionDefectAlarm OBJECT-TYPE
              SYNTAX  DisplayString
              MAX-ACCESS  read-only
              STATUS  current
              DESCRIPTION
			"For port configured with FC-100/200 traffic,
			get the FC Transmit Disparity Inversion Defect
			alarm status.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 191 }

	ommp82PlusFcTransmitDigitalLossOfLinkDefectAlarm OBJECT-TYPE
              SYNTAX  DisplayString
              MAX-ACCESS  read-only
              STATUS  current
              DESCRIPTION
			"For port configured with FC-100/200 traffic,
			get FC Transmit Digital Loss Of Link Defect alarm status.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 192 }

	ommp82PlusFcTrasnmitLossOfSynchronizationDefectAlarm OBJECT-TYPE
              SYNTAX  DisplayString
              MAX-ACCESS  read-only
              STATUS  current
              DESCRIPTION
			"For port configured with FC-100/200 traffic,
			get FC Transmit Loss Of Synchronization Defect
			alarm status.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 193 }

	ommp82PlusFcReceiveDigitalLossOfLinkDefectAlarm OBJECT-TYPE
              SYNTAX  DisplayString
              MAX-ACCESS  read-only
              STATUS  current
              DESCRIPTION
			"For port configured with FC-100/200 traffic,
			get FC Receive Digital Loss Of Link Defect alarm status.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 194 }

	ommp82PlusFcReceiveLossOfSynchronizationDefectAlarm OBJECT-TYPE
              SYNTAX  DisplayString
              MAX-ACCESS  read-only
              STATUS  current
              DESCRIPTION
			"For port configured with FC-100/200 traffic,
			get FC Receive Loss Of Synchronization Defect alarm
			status.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 195 }

	ommp82PlusFcReceiveTransitionDetectDefectAlarm OBJECT-TYPE
              SYNTAX  DisplayString
              MAX-ACCESS  read-only
              STATUS  current
              DESCRIPTION
			"For port configured with FC-100/200 traffic,
			get FC Receive Transition Detect Defect alarm status.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 196 }

	ommp82PlusFcReceiveAnalogLossOfSignalDefectAlarm OBJECT-TYPE
              SYNTAX  DisplayString
              MAX-ACCESS  read-only
              STATUS  current
              DESCRIPTION
			"For port configured with FC-100/200 traffic,
			get FC Receive Analog Loss Of Signal Defect status.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 197 }

	ommp82PlusFcReceiveLineCodeViolationDefectAlarm OBJECT-TYPE
              SYNTAX  DisplayString
              MAX-ACCESS  read-only
              STATUS  current
              DESCRIPTION
			"For port configured with FC-100/200 traffic,
			get FC Receive Line Code Violation Defect alarm status.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 198 }

	ommp82PlusGfpCsfSignalFailAlarm OBJECT-TYPE
              SYNTAX  DisplayString
              MAX-ACCESS  read-only
              STATUS  current
              DESCRIPTION
			"If signal loss at the far-end occurs, then
			this alarm is detected at the near-end card.
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 211 }

	ommp82PlusGfpCsfLinkFailAlarm OBJECT-TYPE
              SYNTAX  DisplayString
              MAX-ACCESS  read-only
              STATUS  current
              DESCRIPTION
			"If there is a link failure occured at the far-end
			card, then this alarm is detected at the near-end card 
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 212 }

	ommp82PlusGfpCoreHeaderErrorAlarm OBJECT-TYPE
              SYNTAX  DisplayString
              MAX-ACCESS  read-only
              STATUS  current
              DESCRIPTION
			"This alarm is generated if the core header error
			count is found to be greater than 50 for a particular
			instance. i.e. for a particular second
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 213 }

	ommp82PlusGfpExtentionHeaderErrorAlarm OBJECT-TYPE
              SYNTAX  DisplayString
              MAX-ACCESS  read-only
              STATUS  current
              DESCRIPTION
			"This alarm is generated if the extention header error
			count is found to be greater than 50 for a particular
			instance. i.e. for a particular second
			-----------------------------
			ommp82PlusInterfaceNumber:
			1 to 8 - CLIENT-1 to CLIENT-8
			-----------------------------
			Values :
			If Alarm is Present - Date and Time Stamp
				    eg:2017-5-18,9:47:20.0,+5:30
			If Alarm is Absent  - 0
			-----------------------------"
		::= { ommp82PlusAlarmQueryEntry 214 }

	ommp82PlusAlarmQueryTableRowStatus OBJECT-TYPE
              SYNTAX      RowStatus
              MAX-ACCESS  read-write
              STATUS      current
              DESCRIPTION
			"*****************************
			This is MIB realted property,
			NOT to be considered as a card property
			*****************************"
              ::= { ommp82PlusAlarmQueryEntry 215 }	                                

--*****************************************************************************
--				    ALARM Notification Table
--*****************************************************************************
	ommp82PlusXfpInputPowerFailureAlarmTrap NOTIFICATION-TYPE
		OBJECTS { ommp82PlusXfpInputPowerFailureAlarm  }
		STATUS  current
		DESCRIPTION
                        "OMMP82-PLUS XFP Input Power Failure Alarm Trap"
        ::= { ommp82PlusAlarmNotification 1 }

	ommp82PlusXfpOutputPowerFailureAlarmTrap NOTIFICATION-TYPE
		OBJECTS { ommp82PlusXfpOutputPowerFailureAlarm  }
		STATUS  current
		DESCRIPTION
                        "OMMP82-PLUS XFP Output Power Failure Alarm Trap" 
        ::= { ommp82PlusAlarmNotification 2 }

	ommp82PlusXfpHighTemperatureAlarmTrap NOTIFICATION-TYPE
		OBJECTS { ommp82PlusXfpHighTemperatureAlarm  }
		STATUS  current
		DESCRIPTION
                        "OMMP82-PLUS XFP High Temperature Alarm Trap" 
        ::= { ommp82PlusAlarmNotification 3 }

	ommp82PlusXfpLowTemperatureAlarmTrap NOTIFICATION-TYPE
		OBJECTS { ommp82PlusXfpLowTemperatureAlarm  }
		STATUS  current
		DESCRIPTION
                        "OMMP82-PLUS XFP Low Temperature Alarm Trap" 
        ::= { ommp82PlusAlarmNotification 4 }

	ommp82PlusXfpHighTemperatureWarningTrap NOTIFICATION-TYPE
		OBJECTS { ommp82PlusXfpHighTemperatureWarning  }
		STATUS  current
		DESCRIPTION
                        "OMMP82-PLUS XFP High Temperature Warning Trap" 
        ::= { ommp82PlusAlarmNotification 5 }

	ommp82PlusXfpLowTemperatureWarningTrap NOTIFICATION-TYPE
		OBJECTS { ommp82PlusXfpLowTemperatureWarning  }
		STATUS  current
		DESCRIPTION
                        "OMMP82-PLUS XFP Low Temperature Warning Trap" 
        ::= { ommp82PlusAlarmNotification 6 }

	ommp82PlusXfpHighBiasCurrentAlarmTrap NOTIFICATION-TYPE
		OBJECTS { ommp82PlusXfpHighBiasCurrentAlarm  }
		STATUS  current
		DESCRIPTION
                        "OMMP82-PLUS XFP High Bias Current Alarm Trap" 
        ::= { ommp82PlusAlarmNotification 7 }

	ommp82PlusXfpLowBiasCurrentAlarmTrap NOTIFICATION-TYPE
		OBJECTS { ommp82PlusXfpLowBiasCurrentAlarm  }
		STATUS  current
		DESCRIPTION
                        "OMMP82-PLUS XFP Low Bias Current Alarm Trap" 
        ::= { ommp82PlusAlarmNotification 8 }

	ommp82PlusXfpHighBiasCurrentWarningTrap NOTIFICATION-TYPE
		OBJECTS { ommp82PlusXfpHighBiasCurrentWarning  }
		STATUS  current
		DESCRIPTION
                        "OMMP82-PLUS XFP High Bias Current Warning Trap" 
        ::= { ommp82PlusAlarmNotification 9 }

	ommp82PlusXfpLowBiasCurrentWarningTrap NOTIFICATION-TYPE
		OBJECTS { ommp82PlusXfpLowBiasCurrentWarning  }
		STATUS  current
		DESCRIPTION
                        "OMMP82-PLUS XFP Low Bias Current Warning Trap" 
        ::= { ommp82PlusAlarmNotification 10 }

	ommp82PlusXfpInputHighPowerAlarmTrap NOTIFICATION-TYPE
		OBJECTS { ommp82PlusXfpInputHighPowerAlarm  }
		STATUS  current
		DESCRIPTION
                        "OMMP82-PLUS XFP Input High Power Alarm Trap" 
        ::= { ommp82PlusAlarmNotification 11 }

	ommp82PlusXfpInputLowPowerAlarmTrap NOTIFICATION-TYPE
		OBJECTS { ommp82PlusXfpInputLowPowerAlarm  }
		STATUS  current
		DESCRIPTION
                        "OMMP82-PLUS XFP Input Low Power Alarm Trap" 
        ::= { ommp82PlusAlarmNotification 12 }

	ommp82PlusXfpInputHighPowerWarningTrap NOTIFICATION-TYPE
		OBJECTS { ommp82PlusXfpInputHighPowerWarning  }
		STATUS  current
		DESCRIPTION
                        "OMMP82-PLUS XFP Input High Power Warning Trap" 
        ::= { ommp82PlusAlarmNotification 13 }

	ommp82PlusXfpInputLowPowerWarningTrap NOTIFICATION-TYPE
		OBJECTS { ommp82PlusXfpInputLowPowerWarning  }
		STATUS  current
		DESCRIPTION
                        "OMMP82-PLUS XFP Input Low Power Warning Trap" 
        ::= { ommp82PlusAlarmNotification 14 }

	ommp82PlusXfpOutputHighPowerAlarmTrap NOTIFICATION-TYPE
		OBJECTS { ommp82PlusXfpOutputHighPowerAlarm  }
		STATUS  current
		DESCRIPTION
                        "OMMP82-PLUS XFP Output High Power Alarm Trap" 
        ::= { ommp82PlusAlarmNotification 15 }

	ommp82PlusXfpOutputLowPowerAlarmTrap NOTIFICATION-TYPE
		OBJECTS { ommp82PlusXfpOutputLowPowerAlarm  }
		STATUS  current
		DESCRIPTION
                        "OMMP82-PLUS XFP Output Low Power Alarm Trap" 
        ::= { ommp82PlusAlarmNotification 16 }

	ommp82PlusXfpOutputHighPowerWarningTrap NOTIFICATION-TYPE
		OBJECTS { ommp82PlusXfpOutputHighPowerWarning  }
		STATUS  current
		DESCRIPTION
                        "OMMP82-PLUS XFP Output High Power Warning Trap" 
        ::= { ommp82PlusAlarmNotification 17 }

	ommp82PlusXfpOutputLowPowerWarningTrap NOTIFICATION-TYPE
		OBJECTS { ommp82PlusXfpOutputLowPowerWarning  }
		STATUS  current
		DESCRIPTION
                        "OMMP82-PLUS XFP Output Low Power Warning Trap" 
        ::= { ommp82PlusAlarmNotification 18 }

	ommp82PlusXfpHighSupplyVoltageAlarmTrap NOTIFICATION-TYPE
		OBJECTS { ommp82PlusXfpHighSupplyVoltageAlarm  }
		STATUS  current
		DESCRIPTION
                        "OMMP82-PLUS XFP High Supply Voltage Alarm Trap" 
        ::= { ommp82PlusAlarmNotification 19 }

	ommp82PlusXfpLowSupplyVoltageAlarmTrap NOTIFICATION-TYPE
		OBJECTS { ommp82PlusXfpLowSupplyVoltageAlarm  }
		STATUS  current
		DESCRIPTION
                        "OMMP82-PLUS XFP Low Supply Voltage Alarm Trap" 
        ::= { ommp82PlusAlarmNotification 20 }

	ommp82PlusXfpHighSupplyVoltageWarningTrap NOTIFICATION-TYPE
		OBJECTS { ommp82PlusXfpHighSupplyVoltageWarning  }
		STATUS  current
		DESCRIPTION
                        "OMMP82-PLUS XFP High Supply Voltage Warning Trap" 
        ::= { ommp82PlusAlarmNotification 21 }

	ommp82PlusXfpLowSupplyVoltageWarningTrap NOTIFICATION-TYPE
		OBJECTS { ommp82PlusXfpLowSupplyVoltageWarning  }
		STATUS  current
		DESCRIPTION
                        "OMMP82-PLUS XFP Low Supply Voltage Warning Trap" 
        ::= { ommp82PlusAlarmNotification 22 }

	ommp82PlusXfpPresenceAbsenceNotificationTrap NOTIFICATION-TYPE
		OBJECTS { ommp82PlusXfpPresenceAbsenceNotification  }
		STATUS  current
		DESCRIPTION
                        "OMMP82-PLUS XFP Presence Absence Notification Trap" 
        ::= { ommp82PlusAlarmNotification 23 }

	ommp82PlusSfpInputPowerFailureAlarmTrap NOTIFICATION-TYPE
		OBJECTS { ommp82PlusSfpInputPowerFailureAlarm  }
		STATUS  current
		DESCRIPTION
                        "OMMP82-PLUS SFP Input Power Failure Alarm Trap" 
        ::= { ommp82PlusAlarmNotification 41 }

	ommp82PlusSfpOutputPowerFailureAlarmTrap NOTIFICATION-TYPE
		OBJECTS { ommp82PlusSfpOutputPowerFailureAlarm  }
		STATUS  current
		DESCRIPTION
                        "OMMP82-PLUS SFP Output Power Failure Alarm Trap" 
        ::= { ommp82PlusAlarmNotification 42 }

	ommp82PlusSfpHighTemperatureAlarmTrap NOTIFICATION-TYPE
		OBJECTS { ommp82PlusSfpHighTemperatureAlarm  }
		STATUS  current
		DESCRIPTION
                        "OMMP82-PLUS SFP High Temperature Alarm Trap" 
        ::= { ommp82PlusAlarmNotification 43 }

	ommp82PlusSfpLowTemperatureAlarmTrap NOTIFICATION-TYPE
		OBJECTS { ommp82PlusSfpLowTemperatureAlarm  }
		STATUS  current
		DESCRIPTION
                        "OMMP82-PLUS SFP Low Temperature Alarm Trap" 
        ::= { ommp82PlusAlarmNotification 44 }

	ommp82PlusSfpHighTemperatureWarningTrap NOTIFICATION-TYPE
		OBJECTS { ommp82PlusSfpHighTemperatureWarning  }
		STATUS  current
		DESCRIPTION
                        "OMMP82-PLUS SFP High Temperature Warning Trap" 
        ::= { ommp82PlusAlarmNotification 45 }

	ommp82PlusSfpLowTemperatureWarningTrap NOTIFICATION-TYPE
		OBJECTS { ommp82PlusSfpLowTemperatureWarning  }
		STATUS  current
		DESCRIPTION
                        "OMMP82-PLUS SFP Low Temperature Warning Trap" 
        ::= { ommp82PlusAlarmNotification 46 }

	ommp82PlusSfpHighBiasCurrentAlarmTrap NOTIFICATION-TYPE
		OBJECTS { ommp82PlusSfpHighBiasCurrentAlarm  }
		STATUS  current
		DESCRIPTION
                        "OMMP82-PLUS SFP High Bias Current Alarm Trap" 
        ::= { ommp82PlusAlarmNotification 47 }

	ommp82PlusSfpLowBiasCurrentAlarmTrap NOTIFICATION-TYPE
		OBJECTS { ommp82PlusSfpLowBiasCurrentAlarm  }
		STATUS  current
		DESCRIPTION
                        "OMMP82-PLUS SFP Low Bias Current Alarm Trap" 
        ::= { ommp82PlusAlarmNotification 48 }

	ommp82PlusSfpHighBiasCurrentWarningTrap NOTIFICATION-TYPE
		OBJECTS { ommp82PlusSfpHighBiasCurrentWarning  }
		STATUS  current
		DESCRIPTION
                        "OMMP82-PLUS SFP High Bias Current Warning Trap" 
        ::= { ommp82PlusAlarmNotification 49 }

	ommp82PlusSfpLowBiasCurrentWarningTrap NOTIFICATION-TYPE
		OBJECTS { ommp82PlusSfpLowBiasCurrentWarning  }
		STATUS  current
		DESCRIPTION
                        "OMMP82-PLUS SFP Low Bias Current Warning Trap" 
        ::= { ommp82PlusAlarmNotification 50 }

	ommp82PlusSfpInputHighPowerAlarmTrap NOTIFICATION-TYPE
		OBJECTS { ommp82PlusSfpInputHighPowerAlarm  }
		STATUS  current
		DESCRIPTION
                        "OMMP82-PLUS SFP Input High Power Alarm Trap" 
        ::= { ommp82PlusAlarmNotification 51 }

	ommp82PlusSfpInputLowPowerAlarmTrap NOTIFICATION-TYPE
		OBJECTS { ommp82PlusSfpInputLowPowerAlarm  }
		STATUS  current
		DESCRIPTION
                        "OMMP82-PLUS SFP Input Low Power Alarm Trap" 
        ::= { ommp82PlusAlarmNotification 52 }

	ommp82PlusSfpInputHighPowerWarningTrap NOTIFICATION-TYPE
		OBJECTS { ommp82PlusSfpInputHighPowerWarning  }
		STATUS  current
		DESCRIPTION
                        "OMMP82-PLUS SFP Input High Power Warning Trap" 
        ::= { ommp82PlusAlarmNotification 53 }

	ommp82PlusSfpInputLowPowerWarningTrap NOTIFICATION-TYPE
		OBJECTS { ommp82PlusSfpInputLowPowerWarning  }
		STATUS  current
		DESCRIPTION
                        "OMMP82-PLUS SFP Input Low Power Warning Trap" 
        ::= { ommp82PlusAlarmNotification 54 }

	ommp82PlusSfpOutputHighPowerAlarmTrap NOTIFICATION-TYPE
		OBJECTS { ommp82PlusSfpOutputHighPowerAlarm  }
		STATUS  current
		DESCRIPTION
                        "OMMP82-PLUS SFP Output High Power Alarm Trap" 
        ::= { ommp82PlusAlarmNotification 55 }

	ommp82PlusSfpOutputLowPowerAlarmTrap NOTIFICATION-TYPE
		OBJECTS { ommp82PlusSfpOutputLowPowerAlarm  }
		STATUS  current
		DESCRIPTION
                        "OMMP82-PLUS SFP Output Low Power Alarm Trap" 
        ::= { ommp82PlusAlarmNotification 56 }

	ommp82PlusSfpOutputHighPowerWarningTrap NOTIFICATION-TYPE
		OBJECTS { ommp82PlusSfpOutputHighPowerWarning  }
		STATUS  current
		DESCRIPTION
                        "OMMP82-PLUS SFP Output High Power Warning Trap" 
        ::= { ommp82PlusAlarmNotification 57 }

	ommp82PlusSfpOutputLowPowerWarningTrap NOTIFICATION-TYPE
		OBJECTS { ommp82PlusSfpOutputLowPowerWarning  }
		STATUS  current
		DESCRIPTION
                        "OMMP82-PLUS SFP Output Low Power Warning Trap" 
        ::= { ommp82PlusAlarmNotification 58 }

	ommp82PlusSfpHighSupplyVoltageAlarmTrap NOTIFICATION-TYPE
		OBJECTS { ommp82PlusSfpHighSupplyVoltageAlarm  }
		STATUS  current
		DESCRIPTION
                        "OMMP82-PLUS SFP High Supply Voltage Alarm Trap" 
        ::= { ommp82PlusAlarmNotification 59 }

	ommp82PlusSfpLowSupplyVoltageAlarmTrap NOTIFICATION-TYPE
		OBJECTS { ommp82PlusSfpLowSupplyVoltageAlarm  }
		STATUS  current
		DESCRIPTION
                        "OMMP82-PLUS SFP Low Supply Voltage Alarm Trap" 
        ::= { ommp82PlusAlarmNotification 60 }

	ommp82PlusSfpHighSupplyVoltageWarningTrap NOTIFICATION-TYPE
		OBJECTS { ommp82PlusSfpHighSupplyVoltageWarning  }
		STATUS  current
		DESCRIPTION
                        "OMMP82-PLUS SFP High Supply Voltage Warning Trap" 
        ::= { ommp82PlusAlarmNotification 61 }

	ommp82PlusSfpLowSupplyVoltageWarningTrap NOTIFICATION-TYPE
		OBJECTS { ommp82PlusSfpLowSupplyVoltageWarning  }
		STATUS  current
		DESCRIPTION
                        "OMMP82-PLUS SFP Low Supply Voltage Warning Trap" 
        ::= { ommp82PlusAlarmNotification 62 }

	ommp82PlusSfpPresenceAbsenceNotificationTrap NOTIFICATION-TYPE
		OBJECTS { ommp82PlusSfpPresenceAbsenceNotification  }
		STATUS  current
		DESCRIPTION
                        "OMMP82-PLUS SFP Presence Absence Notification Trap" 
        ::= { ommp82PlusAlarmNotification 63 }

	ommp82PlusSfpTransmitFaultPresenceAlarmTrap NOTIFICATION-TYPE
		OBJECTS { ommp82PlusSfpTransmitFaultPresenceAlarm  }
		STATUS  current
		DESCRIPTION
                        "OMMP82-PLUS SFP Transmit Fault Presence Alarm Trap" 
        ::= { ommp82PlusAlarmNotification 64 }

	ommp82PlusOtuLossOfSignalAlarmTrap NOTIFICATION-TYPE
		OBJECTS { ommp82PlusOtuLossOfSignalAlarm  }
		STATUS  current
		DESCRIPTION
                        "OMMP82-PLUS OTU Loss Of Signal Alarm Trap" 
        ::= { ommp82PlusAlarmNotification 81 }

	ommp82PlusOtuLossOfFrameAlarmTrap NOTIFICATION-TYPE
		OBJECTS { ommp82PlusOtuLossOfFrameAlarm  }
		STATUS  current
		DESCRIPTION
                        "OMMP82-PLUS OTU Loss Of Frame Alarm Trap" 
        ::= { ommp82PlusAlarmNotification 82 }

	ommp82PlusOtuOutOfFrameAlarmTrap NOTIFICATION-TYPE
		OBJECTS { ommp82PlusOtuOutOfFrameAlarm  }
		STATUS  current
		DESCRIPTION
                        "OMMP82-PLUS OTU Out Of Frame Alarm Trap" 
        ::= { ommp82PlusAlarmNotification 83 }

	ommp82PlusOtuLossOfMultiFrameAlarmTrap NOTIFICATION-TYPE
		OBJECTS { ommp82PlusOtuLossOfMultiFrameAlarm  }
		STATUS  current
		DESCRIPTION
                        "OMMP82-PLUS OTU Loss Of Multi Frame Alarm Trap" 
        ::= { ommp82PlusAlarmNotification 84 }

	ommp82PlusOtuOutOfMultiFrameAlarmTrap NOTIFICATION-TYPE
		OBJECTS { ommp82PlusOtuOutOfMultiFrameAlarm  }
		STATUS  current
		DESCRIPTION
                        "OMMP82-PLUS OTU Out Of Multi Frame Alarm Trap" 
        ::= { ommp82PlusAlarmNotification 85 }

	ommp82PlusOtuSignalFailAlarmTrap NOTIFICATION-TYPE
		OBJECTS { ommp82PlusOtuSignalFailAlarm  }
		STATUS  current
		DESCRIPTION
                        "OMMP82-PLUS OTU Signal Fail Alarm Trap" 
        ::= { ommp82PlusAlarmNotification 86 }

	ommp82PlusOtuSignalDegradeAlarmTrap NOTIFICATION-TYPE
		OBJECTS { ommp82PlusOtuSignalDegradeAlarm  }
		STATUS  current
		DESCRIPTION
                        "OMMP82-PLUS OTU Signal Degrade Alarm Trap" 
        ::= { ommp82PlusAlarmNotification 87 }

	ommp82PlusOtuAlarmIndicationSignalAlarmTrap NOTIFICATION-TYPE
		OBJECTS { ommp82PlusOtuAlarmIndicationSignalAlarm  }
		STATUS  current
		DESCRIPTION
                        "OMMP82-PLUS OTU Alarm Indication Signal Alarm Trap" 
        ::= { ommp82PlusAlarmNotification 88 }

	ommp82PlusOtuIncomingAlignmentErrorAlarmTrap NOTIFICATION-TYPE
		OBJECTS { ommp82PlusOtuIncomingAlignmentErrorAlarm  }
		STATUS  current
		DESCRIPTION
                        "OMMP82-PLUS OTU Incoming Alignment Error Alarm Trap" 
        ::= { ommp82PlusAlarmNotification 89 }

	ommp82PlusOtuTraceIdentifierMismatchAlarmTrap NOTIFICATION-TYPE
		OBJECTS { ommp82PlusOtuTraceIdentifierMismatchAlarm  }
		STATUS  current
		DESCRIPTION
                        "OMMP82-PLUS OTU Trace Identifier Mismatch Alarm Trap" 
        ::= { ommp82PlusAlarmNotification 90 }

	ommp82PlusOtuBackwardIncomingAlignmentErrorAlarmTrap NOTIFICATION-TYPE
		OBJECTS { ommp82PlusOtuBackwardIncomingAlignmentErrorAlarm  }
		STATUS  current
		DESCRIPTION
                        "OMMP82-PLUS OTU Backward Incoming Alignment Error Alarm Trap" 
        ::= { ommp82PlusAlarmNotification 91 }

	ommp82PlusOtuBackwardDefectIndicationAlarmTrap NOTIFICATION-TYPE
		OBJECTS { ommp82PlusOtuBackwardDefectIndicationAlarm  }
		STATUS  current
		DESCRIPTION
                        "OMMP82-PLUS OTU Backward Defect Indication Alarm Trap" 
        ::= { ommp82PlusAlarmNotification 92 }

	ommp82PlusOduSignalFailAlarmTrap NOTIFICATION-TYPE
		OBJECTS { ommp82PlusOduSignalFailAlarm  }
		STATUS  current
		DESCRIPTION
                        "OMMP82-PLUS ODU Signal Fail Alarm Trap" 
        ::= { ommp82PlusAlarmNotification 111 }

	ommp82PlusOduSignalDegradeAlarmTrap NOTIFICATION-TYPE
		OBJECTS { ommp82PlusOduSignalDegradeAlarm  }
		STATUS  current
		DESCRIPTION
                        "OMMP82-PLUS ODU Signal Degrade Alarm Trap" 
        ::= { ommp82PlusAlarmNotification 112 }

	ommp82PlusOduAlarmIndicationSignalAlarmTrap NOTIFICATION-TYPE
		OBJECTS { ommp82PlusOduAlarmIndicationSignalAlarm  }
		STATUS  current
		DESCRIPTION
                        "OMMP82-PLUS ODU Alarm Indication Signal Alarm Trap" 
        ::= { ommp82PlusAlarmNotification 113 }

	ommp82PlusOduTcm1IncomingAlignmentErrorAlarmTrap NOTIFICATION-TYPE
		OBJECTS { ommp82PlusOduTcm1IncomingAlignmentErrorAlarm  }
		STATUS  current
		DESCRIPTION
                        "OMMP82-PLUS ODU TCM1 Incoming Alignment Error Alarm Trap" 
        ::= { ommp82PlusAlarmNotification 114 }

	ommp82PlusOduTcm2IncomingAlignmentErrorAlarmTrap NOTIFICATION-TYPE
		OBJECTS { ommp82PlusOduTcm2IncomingAlignmentErrorAlarm  }
		STATUS  current
		DESCRIPTION
                        "OMMP82-PLUS ODU TCM2 Incoming Alignment Error Alarm Trap" 
        ::= { ommp82PlusAlarmNotification 115 }

	ommp82PlusOduTcm3IncomingAlignmentErrorAlarmTrap NOTIFICATION-TYPE
		OBJECTS { ommp82PlusOduTcm3IncomingAlignmentErrorAlarm  }
		STATUS  current
		DESCRIPTION
                        "OMMP82-PLUS ODU TCM3 Incoming Alignment Error Alarm Trap" 
        ::= { ommp82PlusAlarmNotification 116 }

	ommp82PlusOduTcm4IncomingAlignmentErrorAlarmTrap NOTIFICATION-TYPE
		OBJECTS { ommp82PlusOduTcm4IncomingAlignmentErrorAlarm  }
		STATUS  current
		DESCRIPTION
                        "OMMP82-PLUS ODU TCM4 Incoming Alignment Error Alarm Trap" 
        ::= { ommp82PlusAlarmNotification 117 }

	ommp82PlusOduTcm5IncomingAlignmentErrorAlarmTrap NOTIFICATION-TYPE
		OBJECTS { ommp82PlusOduTcm5IncomingAlignmentErrorAlarm  }
		STATUS  current
		DESCRIPTION
                        "OMMP82-PLUS ODU TCM5 Incoming Alignment Error Alarm Trap" 
        ::= { ommp82PlusAlarmNotification 118 }

	ommp82PlusOduTcm6IncomingAlignmentErrorAlarmTrap NOTIFICATION-TYPE
		OBJECTS { ommp82PlusOduTcm6IncomingAlignmentErrorAlarm  }
		STATUS  current
		DESCRIPTION
                        "OMMP82-PLUS ODU TCM6 Incoming Alignment Error Alarm Trap" 
        ::= { ommp82PlusAlarmNotification 119 }

	ommp82PlusOduTraceIdentifierMismatchAlarmTrap NOTIFICATION-TYPE
		OBJECTS { ommp82PlusOduTraceIdentifierMismatchAlarm  }
		STATUS  current
		DESCRIPTION
                        "OMMP82-PLUS ODU Trace Identifier Mismatch Alarm Trap" 
        ::= { ommp82PlusAlarmNotification 120 }

	ommp82PlusOduLockedDefectAlarmTrap NOTIFICATION-TYPE
		OBJECTS { ommp82PlusOduLockedDefectAlarm  }
		STATUS  current
		DESCRIPTION
                        "OMMP82-PLUS ODU Locked Defect Alarm Trap" 
        ::= { ommp82PlusAlarmNotification 121 }

	ommp82PlusOduOpenConnectionIndicationAlarmTrap NOTIFICATION-TYPE
		OBJECTS { ommp82PlusOduOpenConnectionIndicationAlarm  }
		STATUS  current
		DESCRIPTION
                        "OMMP82-PLUS ODU Open Connection Indication Alarm Trap" 
        ::= { ommp82PlusAlarmNotification 122 }

	ommp82PlusOduBackwardDefectIndicationAlarmTrap NOTIFICATION-TYPE
		OBJECTS { ommp82PlusOduBackwardDefectIndicationAlarm  }
		STATUS  current
		DESCRIPTION
                        "OMMP82-PLUS ODU Backward Defect Indication Alarm Trap" 
        ::= { ommp82PlusAlarmNotification 123 }

	ommp82PlusOduTcm1BackwardIncomingAlignmentErrorAlarmTrap NOTIFICATION-TYPE
		OBJECTS { ommp82PlusOduTcm1BackwardIncomingAlignmentErrorAlarm  }
		STATUS  current
		DESCRIPTION
                        "OMMP82-PLUS ODU TCM1 Backward Incoming Alignment Error Alarm Trap" 
        ::= { ommp82PlusAlarmNotification 124 }

	ommp82PlusOduTcm2BackwardIncomingAlignmentErrorAlarmTrap NOTIFICATION-TYPE
		OBJECTS { ommp82PlusOduTcm2BackwardIncomingAlignmentErrorAlarm  }
		STATUS  current
		DESCRIPTION
                        "OMMP82-PLUS ODU TCM2 Backward Incoming Alignment Error Alarm Trap" 
        ::= { ommp82PlusAlarmNotification 125 }

	ommp82PlusOduTcm3BackwardIncomingAlignmentErrorAlarmTrap NOTIFICATION-TYPE
		OBJECTS { ommp82PlusOduTcm3BackwardIncomingAlignmentErrorAlarm  }
		STATUS  current
		DESCRIPTION
                        "OMMP82-PLUS ODU TCM3 Backward Incoming Alignment Error Alarm Trap" 
        ::= { ommp82PlusAlarmNotification 126 }

	ommp82PlusOduTcm4BackwardIncomingAlignmentErrorAlarmTrap NOTIFICATION-TYPE
		OBJECTS { ommp82PlusOduTcm4BackwardIncomingAlignmentErrorAlarm  }
		STATUS  current
		DESCRIPTION
                        "OMMP82-PLUS ODU TCM4 Backward Incoming Alignment Error Alarm Trap" 
        ::= { ommp82PlusAlarmNotification 127 }

	ommp82PlusOduTcm5BackwardIncomingAlignmentErrorAlarmTrap NOTIFICATION-TYPE
		OBJECTS { ommp82PlusOduTcm5BackwardIncomingAlignmentErrorAlarm  }
		STATUS  current
		DESCRIPTION
                        "OMMP82-PLUS ODU TCM5 Backward Incoming Alignment Error Alarm Trap" 
        ::= { ommp82PlusAlarmNotification 128 }

	ommp82PlusOduTcm6BackwardIncomingAlignmentErrorAlarmTrap NOTIFICATION-TYPE
		OBJECTS { ommp82PlusOduTcm6BackwardIncomingAlignmentErrorAlarm  }
		STATUS  current
		DESCRIPTION
                        "OMMP82-PLUS ODU TCM6 Backward Incoming Alignment Error Alarm Trap" 
        ::= { ommp82PlusAlarmNotification 129 }

	ommp82PlusOduLossOfFrameLossOfMultiframeAlarmTrap NOTIFICATION-TYPE
		OBJECTS { ommp82PlusOduLossOfFrameLossOfMultiframeAlarm  }
		STATUS  current
		DESCRIPTION
                        "OMMP82-PLUS ODU Loss Of Frame Loss Of Multiframe Alarm Trap" 
        ::= { ommp82PlusAlarmNotification 130 }

	ommp82PlusOpuPayloadMismatchAlarmTrap NOTIFICATION-TYPE
		OBJECTS { ommp82PlusOpuPayloadMismatchAlarm  }
		STATUS  current
		DESCRIPTION
                        "OMMP82-PLUS OPU Payload Mismatch Alarm Trap" 
        ::= { ommp82PlusAlarmNotification 135 }

	ommp82PlusOchLossOfPayloadAlarmTrap NOTIFICATION-TYPE
		OBJECTS { ommp82PlusOchLossOfPayloadAlarm  }
		STATUS  current
		DESCRIPTION
                        "OMMP82-PLUS OCH Loss Of Payload Alarm Trap" 
        ::= { ommp82PlusAlarmNotification 136 }

	ommp82PlusSdhLossOfSignalAlarmTrap NOTIFICATION-TYPE
		OBJECTS { ommp82PlusSdhLossOfSignalAlarm  }
		STATUS  current
		DESCRIPTION
                        "OMMP82-PLUS SDH Loss Of Signal Alarm Trap" 
        ::= { ommp82PlusAlarmNotification 141 }

	ommp82PlusSdhOutOfFrameAlarmTrap NOTIFICATION-TYPE
		OBJECTS { ommp82PlusSdhOutOfFrameAlarm  }
		STATUS  current
		DESCRIPTION
                        "OMMP82-PLUS SDH Out Of Frame Alarm Trap" 
        ::= { ommp82PlusAlarmNotification 142 }

	ommp82PlusSdhLossOfFrameAlarmTrap NOTIFICATION-TYPE
		OBJECTS { ommp82PlusSdhLossOfFrameAlarm  }
		STATUS  current
		DESCRIPTION
                        "OMMP82-PLUS SDH Loss Of Frame Alarm Trap" 
        ::= { ommp82PlusAlarmNotification 143 }

	ommp82PlusSdhRsAlarmIndicationSignalAlarmTrap NOTIFICATION-TYPE
		OBJECTS { ommp82PlusSdhRsAlarmIndicationSignalAlarm  }
		STATUS  current
		DESCRIPTION
                        "OMMP82-PLUS SDH RS Alarm Indication Signal Alarm Trap" 
        ::= { ommp82PlusAlarmNotification 144 }

	ommp82PlusSdhRsTraceIdentifierMismatchAlarmTrap NOTIFICATION-TYPE
		OBJECTS { ommp82PlusSdhRsTraceIdentifierMismatchAlarm  }
		STATUS  current
		DESCRIPTION
                        "OMMP82-PLUS SDH RS Trace Identifier Mismatch Alarm Trap" 
        ::= { ommp82PlusAlarmNotification 145 }

	ommp82PlusSdhAuAlarmIndicationSignalAlarmTrap NOTIFICATION-TYPE
		OBJECTS { ommp82PlusSdhAuAlarmIndicationSignalAlarm  }
		STATUS  current
		DESCRIPTION
                        "OMMP82-PLUS SDH AU Alarm Indication Signal Alarm Trap" 
        ::= { ommp82PlusAlarmNotification 146 }

	ommp82PlusSdhAuLossOfPointerAlarmTrap NOTIFICATION-TYPE
		OBJECTS { ommp82PlusSdhAuLossOfPointerAlarm  }
		STATUS  current
		DESCRIPTION
                        "OMMP82-PLUS SDH AU Loss Of Pointer Alarm Trap" 
        ::= { ommp82PlusAlarmNotification 147 }

	ommp82PlusSdhMsAlarmIndicationSignalAlarmTrap NOTIFICATION-TYPE
		OBJECTS { ommp82PlusSdhMsAlarmIndicationSignalAlarm  }
		STATUS  current
		DESCRIPTION
                        "OMMP82-PLUS SDH MS Alarm Indication Signal Alarm Trap" 
        ::= { ommp82PlusAlarmNotification 148 }

	ommp82PlusSdhMsRemoteErrorIndicationAlarmTrap NOTIFICATION-TYPE
		OBJECTS { ommp82PlusSdhMsRemoteErrorIndicationAlarm  }
		STATUS  current
		DESCRIPTION
                        "OMMP82-PLUS SDH MS Remote Error Indication Alarm Trap" 
        ::= { ommp82PlusAlarmNotification 149 }

	ommp82PlusSdhMsRemoteDefectIndicationAlarmTrap NOTIFICATION-TYPE
		OBJECTS { ommp82PlusSdhMsRemoteDefectIndicationAlarm  }
		STATUS  current
		DESCRIPTION
                        "OMMP82-PLUS SDH MS Remote Defect Indication Alarm Trap" 
        ::= { ommp82PlusAlarmNotification 150 }

	ommp82PlusSdhMsRemoteFailureIndicationAlarmTrap NOTIFICATION-TYPE
		OBJECTS { ommp82PlusSdhMsRemoteFailureIndicationAlarm  }
		STATUS  current
		DESCRIPTION
                        "OMMP82-PLUS SDH MS Remote Failure Indication Alarm Trap" 
        ::= { ommp82PlusAlarmNotification 151 }

	ommp82PlusSdhMsB2ExcessiveErrorAlarmTrap NOTIFICATION-TYPE
		OBJECTS { ommp82PlusSdhMsB2ExcessiveErrorAlarm  }
		STATUS  current
		DESCRIPTION
                        "OMMP82-PLUS SDH MS B2 Signal Fail Alarm Trap" 
        ::= { ommp82PlusAlarmNotification 152 }

	ommp82PlusSdhMsB2SignalDegradeAlarmTrap NOTIFICATION-TYPE
		OBJECTS { ommp82PlusSdhMsB2SignalDegradeAlarm  }
		STATUS  current
		DESCRIPTION
                        "OMMP82-PLUS SDH MS B2 Signal Degrade Alarm Trap" 
        ::= { ommp82PlusAlarmNotification 153 }

	ommp82PlusSdhLossOfSequenceSynchronisationAlarmTrap NOTIFICATION-TYPE
		OBJECTS { ommp82PlusSdhLossOfSequenceSynchronisationAlarm  }
		STATUS  current
		DESCRIPTION
                        "OMMP82-PLUS SDH Loss Of Sequence Synchronisation Alarm Trap" 
        ::= { ommp82PlusAlarmNotification 154 }

	ommp82PlusSdhLowerOrderPathPayloadLabelMismatchAlarmTrap NOTIFICATION-TYPE
		OBJECTS { ommp82PlusSdhLowerOrderPathPayloadLabelMismatchAlarm  }
		STATUS  current
		DESCRIPTION
                        "OMMP82-PLUS SDH Lower Order Path Payload Label Mismatch Alarm Trap" 
        ::= { ommp82PlusAlarmNotification 155 }

	ommp82PlusSdhLowerOrderPathUnequippedAlarmTrap NOTIFICATION-TYPE
		OBJECTS { ommp82PlusSdhLowerOrderPathUnequippedAlarm  }
		STATUS  current
		DESCRIPTION
                        "OMMP82-PLUS SDH Lower Order Path Unequipped Alarm Trap" 
        ::= { ommp82PlusAlarmNotification 156 }

	ommp82PlusEthernetLossOfSignalAlarmTrap NOTIFICATION-TYPE
		OBJECTS { ommp82PlusEthernetLossOfSignalAlarm  }
		STATUS  current
		DESCRIPTION
                        "OMMP82-PLUS Ethernet Loss Of Signal Alarm Trap" 
        ::= { ommp82PlusAlarmNotification 171 }

	ommp82PlusEthernetLossOfSignalSyncAlarmTrap NOTIFICATION-TYPE
		OBJECTS { ommp82PlusEthernetLossOfSignalSyncAlarm  }
		STATUS  current
		DESCRIPTION
                        "OMMP82-PLUS Ethernet Loss Of Signal Sync Alarm Trap" 
        ::= { ommp82PlusAlarmNotification 172 }

	ommp82PlusEthernetLinkFailureAlarmTrap NOTIFICATION-TYPE
		OBJECTS { ommp82PlusEthernetLinkFailureAlarm  }
		STATUS  current
		DESCRIPTION
                        "OMMP82-PLUS Ethernet Link Failure Alarm Trap" 
        ::= { ommp82PlusAlarmNotification 173 }

	ommp82PlusEthernetAutoNegotiationAlarmTrap NOTIFICATION-TYPE
		OBJECTS { ommp82PlusEthernetAutoNegotiationAlarm  }
		STATUS  current
		DESCRIPTION
                        "OMMP82-PLUS Ethernet AUto Negotiation Alarm Trap" 
        ::= { ommp82PlusAlarmNotification 174 }

	ommp82PlusEthernetFrameCheckSequenceAlarmTrap NOTIFICATION-TYPE
		OBJECTS { ommp82PlusEthernetFrameCheckSequenceAlarm  }
		STATUS  current
		DESCRIPTION
                        "OMMP82-PLUS Ethernet Frame Check Sequence Alarm Trap" 
        ::= { ommp82PlusAlarmNotification 175 }

	ommp82PlusEthernetCarrierStatusAlarmTrap NOTIFICATION-TYPE
		OBJECTS { ommp82PlusEthernetCarrierStatusAlarm  }
		STATUS  current
		DESCRIPTION
                        "OMMP82-PLUS Ethernet Carrier Status Alarm Trap" 
        ::= { ommp82PlusAlarmNotification 176 }

	ommp82PlusEthernetHighBerAlarmTrap NOTIFICATION-TYPE
		OBJECTS { ommp82PlusEthernetHighBerAlarm  }
		STATUS  current
		DESCRIPTION
                        "OMMP82-PLUS Ethernet High Ber Alarm Trap" 
        ::= { ommp82PlusAlarmNotification 177 }

	ommp82PlusEthernetLocalFaultAlarmTrap NOTIFICATION-TYPE
		OBJECTS { ommp82PlusEthernetLocalFaultAlarm  }
		STATUS  current
		DESCRIPTION
                        "OMMP82-PLUS Ethernet Local Fault Alarm Trap" 
        ::= { ommp82PlusAlarmNotification 178 }

	ommp82PlusEthernetRemoteFaultAlarmTrap NOTIFICATION-TYPE
		OBJECTS { ommp82PlusEthernetRemoteFaultAlarm  }
		STATUS  current
		DESCRIPTION
                        "OMMP82-PLUS Ethernet Remote Fault Alarm Trap" 
        ::= { ommp82PlusAlarmNotification 179 }

	ommp82PlusFcTransmitDisparityInversionDefectAlarmTrap NOTIFICATION-TYPE
		OBJECTS { ommp82PlusFcTransmitDisparityInversionDefectAlarm  }
		STATUS  current
		DESCRIPTION
                        "OMMP82-PLUS FC Transmit Display Invert Alarm Trap" 
        ::= { ommp82PlusAlarmNotification 191 }

	ommp82PlusFcTransmitDigitalLossOfLinkDefectAlarmTrap NOTIFICATION-TYPE
		OBJECTS { ommp82PlusFcTransmitDigitalLossOfLinkDefectAlarm  }
		STATUS  current
		DESCRIPTION
                        "OMMP82-PLUS FC Transmit Dlolb Alarm Trap" 
        ::= { ommp82PlusAlarmNotification 192 }

	ommp82PlusFcTrasnmitLossOfSynchronizationDefectAlarmTrap NOTIFICATION-TYPE
		OBJECTS { ommp82PlusFcTrasnmitLossOfSynchronizationDefectAlarm  }
		STATUS  current
		DESCRIPTION
                        "OMMP82-PLUS FC Transmit Sync Alarm Trap" 
        ::= { ommp82PlusAlarmNotification 193 }

	ommp82PlusFcReceiveDigitalLossOfLinkDefectAlarmTrap NOTIFICATION-TYPE
		OBJECTS { ommp82PlusFcReceiveDigitalLossOfLinkDefectAlarm  }
		STATUS  current
		DESCRIPTION
                        "OMMP82-PLUS FC Receive Dlolb Alarm Trap" 
        ::= { ommp82PlusAlarmNotification 194 }

	ommp82PlusFcReceiveLossOfSynchronizationDefectAlarmTrap NOTIFICATION-TYPE
		OBJECTS { ommp82PlusFcReceiveLossOfSynchronizationDefectAlarm  }
		STATUS  current
		DESCRIPTION
                        "OMMP82-PLUS FC Receive Sync Alarm Trap" 
        ::= { ommp82PlusAlarmNotification 195 }

	ommp82PlusFcReceiveTransitionDetectDefectAlarmTrap NOTIFICATION-TYPE
		OBJECTS { ommp82PlusFcReceiveTransitionDetectDefectAlarm  }
		STATUS  current
		DESCRIPTION
                        "OMMP82-PLUS FC Receive Xdet Alarm Trap" 
        ::= { ommp82PlusAlarmNotification 196 }

	ommp82PlusFcReceiveAnalogLossOfSignalDefectAlarmTrap NOTIFICATION-TYPE
		OBJECTS { ommp82PlusFcReceiveAnalogLossOfSignalDefectAlarm  }
		STATUS  current
		DESCRIPTION
                        "OMMP82-PLUS FC Receive Asd Alarm Trap" 
        ::= { ommp82PlusAlarmNotification 197 }

	ommp82PlusFcReceiveLineCodeViolationDefectAlarmTrap NOTIFICATION-TYPE
		OBJECTS { ommp82PlusFcReceiveLineCodeViolationDefectAlarm  }
		STATUS  current
		DESCRIPTION
                        "OMMP82-PLUS FC Receive Lcv Alarm Trap" 
        ::= { ommp82PlusAlarmNotification 198 }

	ommp82PlusGfpCsfSignalFailAlarmTrap NOTIFICATION-TYPE
		OBJECTS { ommp82PlusGfpCsfSignalFailAlarm  }
		STATUS  current
		DESCRIPTION
                        "OMMP82-PLUS GFP Csf Signal Failure Alarm Trap" 
        ::= { ommp82PlusAlarmNotification 211 }

	ommp82PlusGfpCsfLinkFailAlarmTrap NOTIFICATION-TYPE
		OBJECTS { ommp82PlusGfpCsfLinkFailAlarm  }
		STATUS  current
		DESCRIPTION
                        "OMMP82-PLUS GFP Csf Link Failure Alarm Trap" 
        ::= { ommp82PlusAlarmNotification 212 }

	ommp82PlusGfpCoreHeaderErrorAlarmTrap NOTIFICATION-TYPE
		OBJECTS { ommp82PlusGfpCoreHeaderErrorAlarm  }
		STATUS  current
		DESCRIPTION
                        "OMMP82-PLUS GFP Core Header Error Alarm Trap" 
        ::= { ommp82PlusAlarmNotification 213 }

	ommp82PlusGfpExtentionHeaderErrorAlarmTrap NOTIFICATION-TYPE
		OBJECTS { ommp82PlusGfpExtentionHeaderErrorAlarm  }
		STATUS  current
		DESCRIPTION
                        "OMMP82-PLUS GFP Extention Header Error Alarm Trap" 
        ::= { ommp82PlusAlarmNotification 214 }

--*****************************************************************************
--				    PERFORMANCE
--*****************************************************************************        

	ommp82PlusPerformanceTable OBJECT-TYPE
	      SYNTAX  SEQUENCE OF Ommp82PlusPerformanceEntry
              MAX-ACCESS  not-accessible
              STATUS  current
              DESCRIPTION
                      "Gives Optical and Signal performance status of the OMMP82-PLUS card"
		::= { ommp82PlusPerformance 1 }	

	ommp82PlusPerformanceEntry   OBJECT-TYPE
              SYNTAX  Ommp82PlusPerformanceEntry 
              MAX-ACCESS  not-accessible
              STATUS  current
              DESCRIPTION 
              	""
		INDEX   { node, rack , subRack , slot , ommp82PlusInterfaceNumber}
		::= { ommp82PlusPerformanceTable 1 }
	
	Ommp82PlusPerformanceEntry ::= 
		SEQUENCE {
				ommp82PlusXfpInputPower							DisplayString,
				ommp82PlusXfpOutputPower						DisplayString,
				ommp82PlusXfpBiasCurrent						DisplayString,
				ommp82PlusXfpSupplyVoltage						DisplayString,
				ommp82PlusXfpTemperature						DisplayString,
				ommp82PlusSfpInputPower							DisplayString,
				ommp82PlusSfpOutputPower						DisplayString,
				ommp82PlusSfpBiasCurrent						DisplayString,
				ommp82PlusSfpSupplyVoltage						DisplayString,
				ommp82PlusSfpTemperature						DisplayString,
				ommp82PlusOtnFecUncorrectedWords					DisplayString,
				ommp82PlusOtnFecCorrectedBits						DisplayString,
				ommp82PlusOtnFecZerosCorrectedBits					DisplayString,
				ommp82PlusOtnFecOnesCorrectedBits					DisplayString,
				ommp82PlusOtuBitInterleavedParityErrors					DisplayString,
				ommp82PlusOtuIncomingAlignmentErrorSeconds				DisplayString,
				ommp82PlusOtuBackwardErrorIndicationErrorCount				DisplayString,
				ommp82PlusOtuBackwardIncomingAlignmentErrorSeconds			DisplayString,
				ommp82PlusOtuErrorFreeSeconds						DisplayString,
				ommp82PlusOtuErrorSeconds						DisplayString,
				ommp82PlusOtuBackgroundBlockErrors					DisplayString,
				ommp82PlusOtuSevereErrorSeconds						DisplayString,
				ommp82PlusOtuUnavailableSeconds						DisplayString,
				ommp82PlusOtuBackgroundBlockErrorRatio					DisplayString,
				ommp82PlusOtuSevereErrorSecondsErrorRatio				DisplayString,
				ommp82PlusOtuFarEndErrorFreeSeconds					DisplayString,
				ommp82PlusOtuFarEndErrorSeconds						DisplayString,
				ommp82PlusOtuFarEndBackgroundBlockErrors				DisplayString,
				ommp82PlusOtuFarEndSevereErrorSeconds					DisplayString,
				ommp82PlusOtuFarEndUnavailableSeconds					DisplayString,
				ommp82PlusOtuFarEndBackgroundBlockErrorRatio				DisplayString,
				ommp82PlusOtuFarEndSevereErrorSecondsErrorRatio				DisplayString,
				ommp82PlusOtuErrorRatio							DisplayString,
				ommp82PlusOtuBitErrorRate						DisplayString,
				ommp82PlusOtuFramesReceived						DisplayString,
				ommp82PlusOduBitInterleavedParityErrors					DisplayString,
				ommp82PlusOduTcm1BitInterleavedParityErrors				DisplayString,
				ommp82PlusOduTcm2BitInterleavedParityErrors				DisplayString,
				ommp82PlusOduTcm3BitInterleavedParityErrors				DisplayString,
				ommp82PlusOduTcm4BitInterleavedParityErrors				DisplayString,
				ommp82PlusOduTcm5BitInterleavedParityErrors				DisplayString,
				ommp82PlusOduTcm6BitInterleavedParityErrors				DisplayString,
				ommp82PlusOduTcm1IncomingAlignmentErrorSeconds				DisplayString,
				ommp82PlusOduBackwardErrorIndicationErrorCount				DisplayString,
				ommp82PlusOduTcm1BackwardErrorIndicationErrorCount			DisplayString,
				ommp82PlusOduTcm2BackwardErrorIndicationErrorCount			DisplayString,
				ommp82PlusOduTcm3BackwardErrorIndicationErrorCount			DisplayString,
				ommp82PlusOduTcm4BackwardErrorIndicationErrorCount			DisplayString,
				ommp82PlusOduTcm5BackwardErrorIndicationErrorCount			DisplayString,
				ommp82PlusOduTcm6BackwardErrorIndicationErrorCount			DisplayString,
				ommp82PlusOduTcm1BackwardIncomingAlignmentErrorSeconds			DisplayString,
				ommp82PlusOduDelayMeasurement						DisplayString,
				ommp82PlusOduErrorFreeSeconds						DisplayString,
				ommp82PlusOduErrorSeconds						DisplayString,
				ommp82PlusOduBackgroundBlockErrors					DisplayString,
				ommp82PlusOduSevereErrorSeconds						DisplayString,
				ommp82PlusOduUnavailableSeconds						DisplayString,
				ommp82PlusOduBackgroundBlockErrorRatio					DisplayString,
				ommp82PlusOduSevereErrorSecondsErrorRatio				DisplayString,
				ommp82PlusOduFarEndErrorFreeSeconds					DisplayString,
				ommp82PlusOduFarEndErrorSeconds						DisplayString,
				ommp82PlusOduFarEndBackgroundBlockErrors				DisplayString,
				ommp82PlusOduFarEndSevereErrorSeconds					DisplayString,
				ommp82PlusOduFarEndUnavailableSeconds					DisplayString,
				ommp82PlusOduFarEndBackgroundBlockErrorRatio				DisplayString,
				ommp82PlusOduFarEndSevereErrorSecondsErrorRatio				DisplayString,
				ommp82PlusSdhRsB1BitInterleavedParityErrors				DisplayString,
				ommp82PlusSdhMsB2BitInterleavedParityErrors				DisplayString,
				ommp82PlusSdhMsB3BitInterleavedParityErrors				DisplayString,
				ommp82PlusSdhMsRemoteErrorIndicationErrorCount				DisplayString,
				ommp82PlusSdhMsRemoteDefectIndicationErrorCount				DisplayString,
				ommp82PlusSdhErrorFreeSeconds						DisplayString,
				ommp82PlusSdhErrorSeconds						DisplayString,
				ommp82PlusSdhBackgroundBlockErrors					DisplayString,
				ommp82PlusSdhSevereErrorSeconds						DisplayString,
				ommp82PlusSdhUnavailableSeconds						DisplayString,
				ommp82PlusSdhErrorSecondsErrorRatio					DisplayString,
				ommp82PlusSdhBackgroundBlockErrorRatio					DisplayString,
				ommp82PlusSdhSevereErrorSecondsErrorRatio				DisplayString,
				ommp82PlusEthernetMacTerminatedFramesTransmitted			DisplayString,
				ommp82PlusEthernetMacTerminatedFramesReceived				DisplayString,
				ommp82PlusEthernetMacTerminatedPauseFramesTransmitted			DisplayString,
				ommp82PlusEthernetMacTerminatedPauseFramesReceived			DisplayString,
				ommp82PlusEthernetMacTerminatedUnicastFramesTransmitted			DisplayString,
				ommp82PlusEthernetMacTerminatedUnicastFramesReceived			DisplayString,
				ommp82PlusEthernetMacTerminatedMulticastFramesTransmitted		DisplayString,
				ommp82PlusEthernetMacTerminatedMulticastFramesReceived			DisplayString,
				ommp82PlusEthernetMacTerminatedBroadcastFramesTransmitted		DisplayString,
				ommp82PlusEthernetMacTerminatedBroadcastFramesReceived			DisplayString,
				ommp82PlusEthernetMacTerminatedUnderSizeFramesTransmitted		DisplayString,
				ommp82PlusEthernetMacTerminatedUnderSizeFramesReceived			DisplayString,
				ommp82PlusEthernetMacTerminatedOverSizeFramesTransmitted		DisplayString,
				ommp82PlusEthernetMacTerminatedOverSizeFramesReceived			DisplayString,
				ommp82PlusEthernetMacTerminatedVlanTaggedFramesTransmitted		DisplayString,
				ommp82PlusEthernetMacTerminatedVlanTaggedFramesReceived			DisplayString,
				ommp82PlusEthernetMacTerminatedFrameSymbolErrorsReceived		DisplayString,
				ommp82PlusEthernetMacTerminatedFragmentFramesReceived			DisplayString,
				ommp82PlusEthernetMacTerminatedFrameCheckSequenceErrorsReceived		DisplayString,
				ommp82PlusEthernetMacTerminatedFramesReceivedWithNoDefect		DisplayString,
				ommp82PlusEthernetMacTerminatedBytesTransmitted				DisplayString,
				ommp82PlusEthernetMacTerminatedBytesReceived				DisplayString,	
				ommp82PlusEthernetMacTerminatedControlFramesTransmitted			DisplayString,
				ommp82PlusEthernetMacTerminatedControlFramesReceived			DisplayString,
				ommp82PlusEthernetTransparentTransmitLcvCount				DisplayString,	
				ommp82PlusEthernetTransparentTransmitPropagationErrorDeletionCount	DisplayString,
				ommp82PlusEthernetTransparentTransmitIdleDeletionCount			DisplayString,
				ommp82PlusEthernetTransparentTransmitConfDeletionCount			DisplayString,
				ommp82PlusEthernetTransparentTransmitPropagationInsertionCount		DisplayString,
				ommp82PlusEthernetTransparentTransmitIdleInsertionCount			DisplayString,
				ommp82PlusEthernetTransparentTransmitConfInsertionCount			DisplayString,
				ommp82PlusEthernetTransparentReceiveLcvCount				DisplayString,
				ommp82PlusEthernetTransparentReceivePropagationErrorDeletionCount	DisplayString,
				ommp82PlusEthernetTransparentReceiveIdleDeletionCount			DisplayString,
				ommp82PlusEthernetTransparentReceiveConfDeletionCount			DisplayString,
				ommp82PlusEthernetTransparentReceivePacketDeletionCount			DisplayString,
				ommp82PlusGfpCoreHeaderErrorCount					DisplayString,
				ommp82PlusGfpExtentionHeaderErrorCount					DisplayString,
				ommp82PlusGfpFrameCountWithSingleBitError				DisplayString,
				ommp82PlusGfpTypeHeaderErrorCount					DisplayString,
				ommp82PlusGfpReceiveDropFrameCount					DisplayString,
				ommp82PlusGfpReceiveExtensionHeaderIdentifierFilterDropCount		DisplayString,
				ommp82PlusFcTransmitWordCount						DisplayString,
				ommp82PlusFcReceiveWordCount						DisplayString,
				ommp82PlusFcTransmitTotalPackets					DisplayString,
				ommp82PlusFcReceiveTotalPackets						DisplayString,
				ommp82PlusFcTransmitBadCrc						DisplayString,
				ommp82PlusFcReceiveBadCrc						DisplayString,
				ommp82PlusFcTransmitLcvCount						DisplayString,
				ommp82PlusFcReceiveLcvCount						DisplayString,
				ommp82PlusFcTransmitFillWordInsertionCount				DisplayString,
				ommp82PlusFcTransmitPrimitiveSequenceInsertionCount			DisplayString,
				ommp82PlusFcTransmitFillWordDeletionCount				DisplayString,
				ommp82PlusFcTransmitPrimitiveSequenceDeletionCount			DisplayString,
				ommp82PlusPerformanceTableRowStatus					RowStatus
			}	           

	ommp82PlusXfpInputPower OBJECT-TYPE
		SYNTAX  DisplayString
		MAX-ACCESS  read-only
		STATUS  current
		DESCRIPTION
			"Gives the current Input power(dbm) received at the port
			-----------------------------
			ommp82PlusInterfaceNumber:
			9 - LINE-1
			10 - LINE-2
			-----------------------------
			Values:
			eg: -9.0
			-----------------------------"
	::= { ommp82PlusPerformanceEntry 1 }

	ommp82PlusXfpOutputPower OBJECT-TYPE
		SYNTAX  DisplayString
		MAX-ACCESS  read-only
		STATUS  current
		DESCRIPTION
			"Gives the current Output power(dbm) transmitted at the port
			-----------------------------
			ommp82PlusInterfaceNumber:
			9 - LINE-1
			10 - LINE-2
			-----------------------------
			Values:
			eg: -0.6
			-----------------------------"
	::= { ommp82PlusPerformanceEntry 2 }

	ommp82PlusXfpBiasCurrent OBJECT-TYPE
		SYNTAX  DisplayString
		MAX-ACCESS  read-only
		STATUS  current
		DESCRIPTION
			"Gives the bias current(mA) thats transmitted at the port
			-----------------------------
			ommp82PlusInterfaceNumber:
			9 - LINE-1
			10 - LINE-2
			-----------------------------
			Values:
			eg: 55
			-----------------------------"
	::= { ommp82PlusPerformanceEntry 3 }

	ommp82PlusXfpSupplyVoltage OBJECT-TYPE
		SYNTAX  DisplayString
		MAX-ACCESS  read-only
		STATUS  current
		DESCRIPTION
			"Gives the Supply Voltage of the port
			-----------------------------
			ommp82PlusInterfaceNumber:
			9 - LINE-1
			10 - LINE-2
			-----------------------------
			Values:
			eg: 3.3
			-----------------------------"
	::= { ommp82PlusPerformanceEntry 4 }

	ommp82PlusXfpTemperature OBJECT-TYPE
		SYNTAX  DisplayString
		MAX-ACCESS  read-only
		STATUS  current
		DESCRIPTION
			"Gives the temperature(degree celcius) of the transmitter
			at  the port
			-----------------------------
			ommp82PlusInterfaceNumber:
			9 - LINE-1
			10 - LINE-2
			-----------------------------
			Values:
			eg: 33.35
			-----------------------------"
	::= { ommp82PlusPerformanceEntry 5 }

	ommp82PlusSfpInputPower OBJECT-TYPE
		SYNTAX  DisplayString
		MAX-ACCESS  read-only
		STATUS  current
		DESCRIPTION
			"Gives the current Input power(dbm) received at the port
			-----------------------------
			ommp82PlusInterfaceNumber:
			1 to 8 - CLIENT-1 to CLIENT-8
			-----------------------------
			Values:
			eg: -9.0
			-----------------------------"
	::= { ommp82PlusPerformanceEntry 21 }

	ommp82PlusSfpOutputPower OBJECT-TYPE
		SYNTAX  DisplayString
		MAX-ACCESS  read-only
		STATUS  current
		DESCRIPTION
			"Gives the current Output power(dbm) transmitted at the port
			-----------------------------
			ommp82PlusInterfaceNumber:
			1 to 8 - CLIENT-1 to CLIENT-8
			-----------------------------
			Values:
			eg: -6.0
			-----------------------------"
	::= { ommp82PlusPerformanceEntry 22 }

	ommp82PlusSfpBiasCurrent OBJECT-TYPE
		SYNTAX  DisplayString
		MAX-ACCESS  read-only
		STATUS  current
		DESCRIPTION
			"Gives the bias current(mA) thats transmitted at the port
			-----------------------------
			ommp82PlusInterfaceNumber:
			1 to 8 - CLIENT-1 to CLIENT-8
			-----------------------------
			Values:
			eg: 55
			-----------------------------"
	::= { ommp82PlusPerformanceEntry 23 }

	ommp82PlusSfpSupplyVoltage OBJECT-TYPE
		SYNTAX  DisplayString
		MAX-ACCESS  read-only
		STATUS  current
		DESCRIPTION
			"Gives the Supply Voltage of the port
			-----------------------------
			ommp82PlusInterfaceNumber:
			1 to 8 - CLIENT-1 to CLIENT-8
			-----------------------------
			Values:
			eg: 3.3
			-----------------------------"
	::= { ommp82PlusPerformanceEntry 24 }

	ommp82PlusSfpTemperature OBJECT-TYPE
		SYNTAX  DisplayString
		MAX-ACCESS  read-only
		STATUS  current
		DESCRIPTION
			"Gives the temperature(degree celcius) of the transmitter
			at the port
			-----------------------------
			ommp82PlusInterfaceNumber:
			1 to 8 - CLIENT-1 to CLIENT-8
			-----------------------------
			Values:
			eg: 33.35
			-----------------------------"
	::= { ommp82PlusPerformanceEntry 25 }

	ommp82PlusOtnFecUncorrectedWords OBJECT-TYPE
		SYNTAX  DisplayString
		MAX-ACCESS  read-only
		STATUS  current
		DESCRIPTION
			"For port configured with OTU2/OTU1 traffic,
			OTU Uncorrected Word Error Counter counts the number of
			FEC errored code words that could not be corrected.
			-----------------------------
			ommp82PlusInterfaceNumber:
			1 to 8 - CLIENT-1 to CLIENT-8
			9 - LINE-1
			10 - LINE-2
			-----------------------------
			Values:
			eg: 1234
			-----------------------------"
	::= { ommp82PlusPerformanceEntry 41 }

	ommp82PlusOtnFecCorrectedBits OBJECT-TYPE
		SYNTAX  DisplayString
		MAX-ACCESS  read-only
		STATUS  current
		DESCRIPTION
			"For port configured with OTU2/OTU1 traffic,
			OTU Corrected Bit Error Counter counts the number of
			FEC error bits that could be corrected(sum of ones
			corrected and zeros corrected bits).
			-----------------------------
			ommp82PlusInterfaceNumber:
			1 to 8 - CLIENT-1 to CLIENT-8
			9 - LINE-1
			10 - LINE-2
			-----------------------------
			Values:
			eg: 1234
			-----------------------------"
	::= { ommp82PlusPerformanceEntry 42 }

	ommp82PlusOtnFecZerosCorrectedBits OBJECT-TYPE
		SYNTAX  DisplayString
		MAX-ACCESS  read-only
		STATUS  current
		DESCRIPTION
			"For port configured with OTU2/OTU1 traffic,
			OTU Zero Corrected Bits Error Counter counts the number
			of FEC error bits that could be corrected from
			one to zero value(Expected 0 but received as 1).
			-----------------------------
			ommp82PlusInterfaceNumber:
			1 to 8 - CLIENT-1 to CLIENT-8
			9 - LINE-1
			10 - LINE-2
			-----------------------------
			Values:
			eg: 1234
			-----------------------------"
	::= { ommp82PlusPerformanceEntry 43 }

	ommp82PlusOtnFecOnesCorrectedBits OBJECT-TYPE
		SYNTAX  DisplayString
		MAX-ACCESS  read-only
		STATUS  current
		DESCRIPTION
			"For port configured with OTU2/OTU1 traffic,
			OTU Ones Corrected Byte Error Counter counts the number
			of FEC error bytes that could be corrected from
			zero to one value(Expected 1 but received as 0).
			-----------------------------
			ommp82PlusInterfaceNumber:
			1 to 8 - CLIENT-1 to CLIENT-8
			9 - LINE-1
			10 - LINE-2
			-----------------------------
			Values:
			eg: 1234
			-----------------------------"
	::= { ommp82PlusPerformanceEntry 44 }

	ommp82PlusOtuBitInterleavedParityErrors OBJECT-TYPE
		SYNTAX  DisplayString
		MAX-ACCESS  read-only
		STATUS  current
		DESCRIPTION
			"For port configured with OTU2/OTU1 traffic,
			OTU-BIP Counter counts the Parity errors evaluated by
			SM field of an OTU2 frame.
			-----------------------------
			ommp82PlusInterfaceNumber:
			1 to 8 - CLIENT-1 to CLIENT-8
			9 - LINE-1
			10 - LINE-2
			-----------------------------
			Values:
			eg: 1234
			-----------------------------"
	::= { ommp82PlusPerformanceEntry 45 }

	ommp82PlusOtuIncomingAlignmentErrorSeconds OBJECT-TYPE
		SYNTAX  DisplayString
		MAX-ACCESS  read-only
		STATUS  current
		DESCRIPTION
			"For port configured with OTU2/OTU1 traffic,
			OTU Incoming Alignment Error Second increases,
			when OTU IAE Alarm is detected in that particular second
			of the incoming OTU signal
			-----------------------------
			ommp82PlusInterfaceNumber:
			1 to 8 - CLIENT-1 to CLIENT-8
			9 - LINE-1
			10 - LINE-2
			-----------------------------
			Values:
			eg: 1234
			-----------------------------"
	::= { ommp82PlusPerformanceEntry 46 }

	ommp82PlusOtuBackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code.
			-----------------------------
			ommp82PlusInterfaceNumber:
			1 to 8 - CLIENT-1 to CLIENT-8
			9 - LINE-1
			10 - LINE-2
			-----------------------------
			Values:
			eg: 1234
			-----------------------------"
	::= { ommp82PlusPerformanceEntry 47 }

	ommp82PlusOtuBackwardIncomingAlignmentErrorSeconds OBJECT-TYPE
		SYNTAX  DisplayString
		MAX-ACCESS  read-only
		STATUS  current
		DESCRIPTION
			"For port configured with OTU2/OTU1 traffic,
			OTU-BIAE Counter increases when SM-BIAE Alarm is 
			detected in that particular second
			of the incoming OTU signal
			-----------------------------
			ommp82PlusInterfaceNumber:
			1 to 8 - CLIENT-1 to CLIENT-8
			9 - LINE-1
			10 - LINE-2
			-----------------------------
			Values:
			eg: 1234
			-----------------------------"
	::= { ommp82PlusPerformanceEntry 48 }

	ommp82PlusOtuErrorFreeSeconds OBJECT-TYPE
		SYNTAX  DisplayString
		MAX-ACCESS  read-only
		STATUS  current
		DESCRIPTION
			"For port configured with OTU2/OTU1 traffic,
			OTU Error Free Seconds increases when no BIP errors
			or defects are detected
			-----------------------------
			ommp82PlusInterfaceNumber:
			1 to 8 - CLIENT-1 to CLIENT-8
			9 - LINE-1
			10 - LINE-2
			-----------------------------
			Values:
			eg: 1234
			-----------------------------"
	::= { ommp82PlusPerformanceEntry 49 }

	ommp82PlusOtuErrorSeconds OBJECT-TYPE
		SYNTAX  DisplayString
		MAX-ACCESS  read-only
		STATUS  current
		DESCRIPTION
			"For port configured with OTU2/OTU1 traffic,
			OTU Error Seconds increases when any defects like 
			OTU-AIS, SM-TIM etc are detected at the
			section monitoring level
			-----------------------------
			ommp82PlusInterfaceNumber:
			1 to 8 - CLIENT-1 to CLIENT-8
			9 - LINE-1
			10 - LINE-2
			-----------------------------
			Values:
			eg: 1234
			-----------------------------"
	::= { ommp82PlusPerformanceEntry 50 }

	ommp82PlusOtuBackgroundBlockErrors OBJECT-TYPE
		SYNTAX  DisplayString
		MAX-ACCESS  read-only
		STATUS  current
		DESCRIPTION
			"For port configured with OTU2/OTU1 traffic,
			OTU Background Block Errors increases on defects 
			detected and when BIP errors are less than 15% errored
			blocks received 
			-----------------------------
			ommp82PlusInterfaceNumber:
			1 to 8 - CLIENT-1 to CLIENT-8
			9 - LINE-1
			10 - LINE-2
			-----------------------------
			Values:
			eg: 1234
			-----------------------------"
	::= { ommp82PlusPerformanceEntry 51 }

	ommp82PlusOtuSevereErrorSeconds OBJECT-TYPE
		SYNTAX  DisplayString
		MAX-ACCESS  read-only
		STATUS  current
		DESCRIPTION
			"For port configured with OTU2/OTU1 traffic,
			OTU Severe Error Seconds increases on defects
			detected and when BIP errors are greater than or
			equal to 15% errored blocks received 
			-----------------------------
			ommp82PlusInterfaceNumber:
			1 to 8 - CLIENT-1 to CLIENT-8
			9 - LINE-1
			10 - LINE-2
			-----------------------------
			Values:
			eg: 1234
			-----------------------------"
	::= { ommp82PlusPerformanceEntry 52 }

	ommp82PlusOtuUnavailableSeconds OBJECT-TYPE
		SYNTAX  DisplayString
		MAX-ACCESS  read-only
		STATUS  current
		DESCRIPTION
			"For port configured with OTU2/OTU1 traffic,
			OTU Unavailable Seconds increases,
			when 10 consecutive OTU Severe Error seconds
			are detected
			-----------------------------
			ommp82PlusInterfaceNumber:
			1 to 8 - CLIENT-1 to CLIENT-8
			9 - LINE-1
			10 - LINE-2
			-----------------------------
			Values:
			eg: 1234
			-----------------------------"
	::= { ommp82PlusPerformanceEntry 53 }

	ommp82PlusOtuBackgroundBlockErrorRatio OBJECT-TYPE
		SYNTAX  DisplayString
		MAX-ACCESS  read-only
		STATUS  current
		DESCRIPTION
			"For port configured with OTU2/OTU1 traffic,
			gives OTU Background Block Error Seconds Error Ratio.
			The ratio of BBE in available time to total seconds
			in available time during a fixed measurement interval.
			-----------------------------
			ommp82PlusInterfaceNumber:
			1 to 8 - CLIENT-1 to CLIENT-8
			9 - LINE-1
			10 - LINE-2
			-----------------------------
			Values:
			eg: 1e-3
			-----------------------------"
	::= { ommp82PlusPerformanceEntry 55 }

	ommp82PlusOtuSevereErrorSecondsErrorRatio OBJECT-TYPE
		SYNTAX  DisplayString
		MAX-ACCESS  read-only
		STATUS  current
		DESCRIPTION
			"For port configured with OTU2/OTU1 traffic,
			gives OTU Severe Error Seconds Error Ratio.
			The ratio of SES in available time to total seconds
			in available time during a fixed measurement interval.
			-----------------------------
			ommp82PlusInterfaceNumber:
			1 to 8 - CLIENT-1 to CLIENT-8
			9 - LINE-1
			10 - LINE-2
			-----------------------------
			Values:
			eg: 1e-3
			-----------------------------"
	::= { ommp82PlusPerformanceEntry 56 }

	ommp82PlusOtuFarEndErrorFreeSeconds OBJECT-TYPE
		SYNTAX  DisplayString
		MAX-ACCESS  read-only
		STATUS  current
		DESCRIPTION
			"For port configured with OTU2/OTU1 traffic,
			OTU Far end Error Free Seconds, increases when no
			backward errors or defects like BDI or BEI
			are detected in the incoming OTU signal.
			-----------------------------
			ommp82PlusInterfaceNumber:
			1 to 8 - CLIENT-1 to CLIENT-8
			9 - LINE-1
			10 - LINE-2
			-----------------------------
			Values:
			eg: 1234
			-----------------------------"
	::= { ommp82PlusPerformanceEntry 57 }

	ommp82PlusOtuFarEndErrorSeconds OBJECT-TYPE
		SYNTAX  DisplayString
		MAX-ACCESS  read-only
		STATUS  current
		DESCRIPTION
			"For port configured with OTU2/OTU1 traffic,
			OTU Far End Error Seconds increases on
			detection of defects like BDI in incoming
			OTU signal.
			-----------------------------
			ommp82PlusInterfaceNumber:
			1 to 8 - CLIENT-1 to CLIENT-8
			9 - LINE-1
			10 - LINE-2
			-----------------------------
			Values:
			eg: 1234
			-----------------------------"
	::= { ommp82PlusPerformanceEntry 58 }

	ommp82PlusOtuFarEndBackgroundBlockErrors OBJECT-TYPE
		SYNTAX  DisplayString
		MAX-ACCESS  read-only
		STATUS  current
		DESCRIPTION
			"For port configured with OTU2/OTU1 traffic,
			OTU Far End Background Block Errors increases when BEI
			errors are less than 15% Errored Blocks in incoming
			OTU signal.
			-----------------------------
			ommp82PlusInterfaceNumber:
			1 to 8 - CLIENT-1 to CLIENT-8
			9 - LINE-1
			10 - LINE-2
			-----------------------------
			Values:
			eg: 1234
			-----------------------------"
	::= { ommp82PlusPerformanceEntry 59 }

	ommp82PlusOtuFarEndSevereErrorSeconds OBJECT-TYPE
		SYNTAX  DisplayString
		MAX-ACCESS  read-only
		STATUS  current
		DESCRIPTION
			"For port configured with OTU2/OTU1 traffic,
			OTU Far End Severe Error Seconds increases on defects
			like BDI are detected and when BEI errors are greater
			than or equal to 15% Errored Blocks in incoming OTU 
			signal.
			-----------------------------
			ommp82PlusInterfaceNumber:
			1 to 8 - CLIENT-1 to CLIENT-8
			9 - LINE-1
			10 - LINE-2
			-----------------------------
			Values:
			eg: 1234
			-----------------------------"
	::= { ommp82PlusPerformanceEntry 60 }

	ommp82PlusOtuFarEndUnavailableSeconds OBJECT-TYPE
		SYNTAX  DisplayString
		MAX-ACCESS  read-only
		STATUS  current
		DESCRIPTION
			"For port configured with OTU2/OTU1 traffic,
			OTU Far End Unavailable Seconds increases, 
			after 9 consecutive OTU Far End Severe Error
			seconds are detected
			-----------------------------
			ommp82PlusInterfaceNumber:
			1 to 8 - CLIENT-1 to CLIENT-8
			9 - LINE-1
			10 - LINE-2
			-----------------------------
			Values:
			eg: 1234
			-----------------------------"
	::= { ommp82PlusPerformanceEntry 61 }

	ommp82PlusOtuFarEndBackgroundBlockErrorRatio OBJECT-TYPE
		SYNTAX  DisplayString
		MAX-ACCESS  read-only
		STATUS  current
		DESCRIPTION
			"For port configured with OTU2/OTU1 traffic,
			gives Otu Far End Background Block Error Ratio.
			The ratio of Far End BBE in available time to tota
			seconds in available time during a fixed measurement
			interval.
			-----------------------------
			ommp82PlusInterfaceNumber:
			1 to 8 - CLIENT-1 to CLIENT-8
			9 - LINE-1
			10 - LINE-2
			-----------------------------
			Values:
			eg: 1e-3
			-----------------------------"
	::= { ommp82PlusPerformanceEntry 63 }

	ommp82PlusOtuFarEndSevereErrorSecondsErrorRatio OBJECT-TYPE
		SYNTAX  DisplayString
		MAX-ACCESS  read-only
		STATUS  current
		DESCRIPTION
			"For port configured with OTU2/OTU1 traffic,
			gives Otu Far End Severe Error Seconds Error Ratio.
			The ratio of Far End SES in available time to total seconds
			in available time during a fixed measurement interval.
			-----------------------------
			ommp82PlusInterfaceNumber:
			1 to 8 - CLIENT-1 to CLIENT-8
			9 - LINE-1
			10 - LINE-2
			-----------------------------
			Values:
			eg: 1e-3
			-----------------------------"
	::= { ommp82PlusPerformanceEntry 64 }

	ommp82PlusOtuErrorRatio   OBJECT-TYPE
              SYNTAX  DisplayString
              MAX-ACCESS  read-only
              STATUS  current
              DESCRIPTION
			"For port configured with OTU2/OTU1 traffic,
			gives the OTU Error Ratio for requested port. The ratio  
			of number of error bits to the number of bits received in
			a particular second
			-----------------------------
			ommp82PlusInterfaceNumber:
			1 to 8 - CLIENT-1 to CLIENT-8
			9 - LINE-1
			10 - LINE-2
			-----------------------------	
			Value:
			eg: 4.0
			-----------------------------"
	::= { ommp82PlusPerformanceEntry 65 } 

	ommp82PlusOtuBitErrorRate  OBJECT-TYPE
              SYNTAX  DisplayString
              MAX-ACCESS  read-only
              STATUS  current
              DESCRIPTION
			"For port configured with OTU2/OTU1 traffic, gives the 
			Bit Error Rate. Bit error rate is the Error ratio 
			multiplied by the OTU2 standard signal 
			data-rate( 10.709225316 Gbps )
			-----------------------------
			ommp82PlusInterfaceNumber:
			1 to 8 - CLIENT-1 to CLIENT-8
			9 - LINE-1
			10 - LINE-2
			-----------------------------	
			Value:
			eg: 4.0
			-----------------------------"
	::= { ommp82PlusPerformanceEntry 66 }

	ommp82PlusOtuFramesReceived  OBJECT-TYPE
              SYNTAX  DisplayString
              MAX-ACCESS  read-only
              STATUS  current
              DESCRIPTION
			"For port configured with OTU2/OTU1 traffic, gives the 
			gives the number of OTU frames transmitted.
			-----------------------------
			ommp82PlusInterfaceNumber:
			1 to 8 - CLIENT-1 to CLIENT-8
			9 - LINE-1
			10 - LINE-2
			-----------------------------	
			Value:
			eg: 4.0
			-----------------------------"
	::= { ommp82PlusPerformanceEntry 67 }

	ommp82PlusOduBitInterleavedParityErrors OBJECT-TYPE
		SYNTAX  DisplayString
		MAX-ACCESS  read-only
		STATUS  current
		DESCRIPTION
			"For port configured with OTU2/OTU1 traffic,
			ODU-BIP Counter counts the Parity errors evaluated by
			PM field of an OTU2 frame
			-----------------------------
			ommp82PlusInterfaceNumber:
			1 to 8 - CLIENT-1 to CLIENT-8
			9 - LINE-1
			10 - LINE-2
			-----------------------------
			Values:
			eg: 1234
			-----------------------------"
	::= { ommp82PlusPerformanceEntry 81 }

	ommp82PlusOduTcm1BitInterleavedParityErrors OBJECT-TYPE
		SYNTAX  DisplayString
		MAX-ACCESS  read-only
		STATUS  current
		DESCRIPTION
			"For port configured with OTU2/OTU1 traffic,
			TCM1-BIP Counter counts the Parity errors evaluated by
			TCM1 field in ODU frame
			-----------------------------
			ommp82PlusInterfaceNumber:
			1 to 8 - CLIENT-1 to CLIENT-8
			9 - LINE-1
			10 - LINE-2
			-----------------------------
			Values:
			eg: 1234
			-----------------------------"
	::= { ommp82PlusPerformanceEntry 82 }

	ommp82PlusOduTcm2BitInterleavedParityErrors OBJECT-TYPE
		SYNTAX  DisplayString
		MAX-ACCESS  read-only
		STATUS  current
		DESCRIPTION
			"For port configured with OTU2/OTU1 traffic,
			TCM2-BIP Counter counts the Parity errors evaluated by
			TCM2 field in ODU frame
			-----------------------------
			ommp82PlusInterfaceNumber:
			1 to 8 - CLIENT-1 to CLIENT-8
			9 - LINE-1
			10 - LINE-2
			-----------------------------
			Values:
			eg: 1234
			-----------------------------"
	::= { ommp82PlusPerformanceEntry 83 }

	ommp82PlusOduTcm3BitInterleavedParityErrors OBJECT-TYPE
		SYNTAX  DisplayString
		MAX-ACCESS  read-only
		STATUS  current
		DESCRIPTION
			"For port configured with OTU2/OTU1 traffic,
			TCM3-BIP Counter counts the Parity errors evaluated by
			TCM3 field in ODU frame
			-----------------------------
			ommp82PlusInterfaceNumber:
			1 to 8 - CLIENT-1 to CLIENT-8
			9 - LINE-1
			10 - LINE-2
			-----------------------------
			Values:
			eg: 1234
			-----------------------------"
	::= { ommp82PlusPerformanceEntry 84 }

	ommp82PlusOduTcm4BitInterleavedParityErrors OBJECT-TYPE
		SYNTAX  DisplayString
		MAX-ACCESS  read-only
		STATUS  current
		DESCRIPTION
			"For port configured with OTU2/OTU1 traffic,
			TCM4-BIP Counter counts the Parity errors evaluated by
			TCM4 field in ODU frame
			-----------------------------
			ommp82PlusInterfaceNumber:
			1 to 8 - CLIENT-1 to CLIENT-8
			9 - LINE-1
			10 - LINE-2
			-----------------------------
			Values:
			eg: 1234
			-----------------------------"
	::= { ommp82PlusPerformanceEntry 85 }

	ommp82PlusOduTcm5BitInterleavedParityErrors OBJECT-TYPE
		SYNTAX  DisplayString
		MAX-ACCESS  read-only
		STATUS  current
		DESCRIPTION
			"For port configured with OTU2/OTU1 traffic,
			TCM5-BIP Counter counts the Parity errors evaluated by
			TCM5 field in ODU frame
			-----------------------------
			ommp82PlusInterfaceNumber:
			1 to 8 - CLIENT-1 to CLIENT-8
			9 - LINE-1
			10 - LINE-2
			-----------------------------
			Values:
			eg: 1234
			-----------------------------"
	::= { ommp82PlusPerformanceEntry 86 }

	ommp82PlusOduTcm6BitInterleavedParityErrors OBJECT-TYPE
		SYNTAX  DisplayString
		MAX-ACCESS  read-only
		STATUS  current
		DESCRIPTION
			"For port configured with OTU2/OTU1 traffic,
			TCM6-BIP Counter counts the Parity errors evaluated by
			TCM6 field in ODU frame
			-----------------------------
			ommp82PlusInterfaceNumber:
			1 to 8 - CLIENT-1 to CLIENT-8
			9 - LINE-1
			10 - LINE-2
			-----------------------------
			Values:
			eg: 1234
			-----------------------------"
	::= { ommp82PlusPerformanceEntry 87 }

	ommp82PlusOduTcm1IncomingAlignmentErrorSeconds OBJECT-TYPE
		SYNTAX  DisplayString
		MAX-ACCESS  read-only
		STATUS  current
		DESCRIPTION
			"For port configured with OTU2/OTU1 traffic,
			ODU Incoming Alignment Error Count increases,
			when ODU-TCM1-IAE is detected in that particular second
			of the incoming OTU signal
			-----------------------------
			ommp82PlusInterfaceNumber:
			1 to 8 - CLIENT-1 to CLIENT-8
			9 - LINE-1
			10 - LINE-2
			-----------------------------
			Values:
			eg: 1234
			-----------------------------"
	::= { ommp82PlusPerformanceEntry 88 }

	ommp82PlusOduBackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code.
			-----------------------------
			ommp82PlusInterfaceNumber:
			1 to 8 - CLIENT-1 to CLIENT-8
			9 - LINE-1
			10 - LINE-2
			-----------------------------
			Values:
			eg: 1234
			-----------------------------"
	::= { ommp82PlusPerformanceEntry 89 }

	ommp82PlusOduTcm1BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM1 level.
			-----------------------------
			ommp82PlusInterfaceNumber:
			1 to 8 - CLIENT-1 to CLIENT-8
			9 - LINE-1
			10 - LINE-2
			-----------------------------
			Values:
			eg: 1234
			-----------------------------"
	::= { ommp82PlusPerformanceEntry 90 }

	ommp82PlusOduTcm2BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM2 level.
			-----------------------------
			ommp82PlusInterfaceNumber:
			1 to 8 - CLIENT-1 to CLIENT-8
			9 - LINE-1
			10 - LINE-2
			-----------------------------
			Values:
			eg: 1234
			-----------------------------"
	::= { ommp82PlusPerformanceEntry 91 }

	ommp82PlusOduTcm3BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM3 level.
			-----------------------------
			ommp82PlusInterfaceNumber:
			1 to 8 - CLIENT-1 to CLIENT-8
			9 - LINE-1
			10 - LINE-2
			-----------------------------
			Values:
			eg: 1234
			-----------------------------"
	::= { ommp82PlusPerformanceEntry 92 }

	ommp82PlusOduTcm4BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM4 level.
			-----------------------------
			ommp82PlusInterfaceNumber:
			1 to 8 - CLIENT-1 to CLIENT-8
			9 - LINE-1
			10 - LINE-2
			-----------------------------
			Values:
			eg: 1234
			-----------------------------"
	::= { ommp82PlusPerformanceEntry 93 }

	ommp82PlusOduTcm5BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM5 level.
			-----------------------------
			ommp82PlusInterfaceNumber:
			1 to 8 - CLIENT-1 to CLIENT-8
			9 - LINE-1
			10 - LINE-2
			-----------------------------
			Values:
			eg: 1234
			-----------------------------"
	::= { ommp82PlusPerformanceEntry 94 }

	ommp82PlusOduTcm6BackwardErrorIndicationErrorCount OBJECT-TYPE
		SYNTAX  DisplayString
		MAX-ACCESS  read-only
		STATUS  current
		DESCRIPTION
			"For port configured with OTU2/OTU1 traffic,
			this signal is used to convey in the upstream direction 
			the count of interleaved bit blocks that have 
			been detected in error using the BIP-8 code at
			TCM6 level.
			-----------------------------
			ommp82PlusInterfaceNumber:
			1 to 8 - CLIENT-1 to CLIENT-8
			9 - LINE-1
			10 - LINE-2
			-----------------------------
			Values:
			eg: 1234
			-----------------------------"
	::= { ommp82PlusPerformanceEntry 95 }

	ommp82PlusOduTcm1BackwardIncomingAlignmentErrorSeconds OBJECT-TYPE
		SYNTAX  DisplayString
		MAX-ACCESS  read-only
		STATUS  current
		DESCRIPTION
			"For port configured with OTU2/OTU1 traffic,
			ODU Backward Incoming Alignment Error Count increases,
			when ODU-TCM1-BIAE is detected in that particular second
			of the incoming OTU signal
			-----------------------------
			ommp82PlusInterfaceNumber:
			1 to 8 - CLIENT-1 to CLIENT-8
			9 - LINE-1
			10 - LINE-2
			-----------------------------
			Values:
			eg: 1234
			-----------------------------"
	::= { ommp82PlusPerformanceEntry 96 }

	ommp82PlusOduDelayMeasurement OBJECT-TYPE
		SYNTAX  DisplayString
		MAX-ACCESS  read-only
		STATUS  current
		DESCRIPTION
			"For port configured with OTU2/OTU1 traffic,
			gives delay measurement of ODU frame
			-----------------------------
			ommp82PlusInterfaceNumber:
			1 to 8 - CLIENT-1 to CLIENT-8
			9 - LINE-1
			10 - LINE-2
			-----------------------------
			Values:
			eg: Reserved for further study
			-----------------------------"
	::= { ommp82PlusPerformanceEntry 97 }

	ommp82PlusOduErrorFreeSeconds OBJECT-TYPE
		SYNTAX  DisplayString
		MAX-ACCESS  read-only
		STATUS  current
		DESCRIPTION
			"For port configured with OTU2/OTU1 traffic,
			ODU Error Free Seconds increases,
			when no BIP errors or defects are detected at the
			path monitoring level
			-----------------------------
			ommp82PlusInterfaceNumber:
			1 to 8 - CLIENT-1 to CLIENT-8
			9 - LINE-1
			10 - LINE-2
			-----------------------------
			Values:
			eg: 1234
			-----------------------------"
	::= { ommp82PlusPerformanceEntry 98 }

	ommp82PlusOduErrorSeconds OBJECT-TYPE
		SYNTAX  DisplayString
		MAX-ACCESS  read-only
		STATUS  current
		DESCRIPTION
			"For port configured with OTU2/OTU1 traffic,
			ODU Error Seconds increases on defects detected at the
			path monitoring level
			-----------------------------
			ommp82PlusInterfaceNumber:
			1 to 8 - CLIENT-1 to CLIENT-8
			9 - LINE-1
			10 - LINE-2
			-----------------------------
			Values:
			eg: 1234
			-----------------------------"
	::= { ommp82PlusPerformanceEntry 99 }

	ommp82PlusOduBackgroundBlockErrors OBJECT-TYPE
		SYNTAX  DisplayString
		MAX-ACCESS  read-only
		STATUS  current
		DESCRIPTION
			"For port configured with OTU2/OTU1 traffic,
			ODU Background Block Errors increases on defects 
			detected and when BIP errors are less than 15% 
			Errored Blocks in incoming OTU signal.
			-----------------------------
			ommp82PlusInterfaceNumber:
			1 to 8 - CLIENT-1 to CLIENT-8
			9 - LINE-1
			10 - LINE-2
			-----------------------------
			Values:
			eg: 1234
			-----------------------------"
	::= { ommp82PlusPerformanceEntry 100 }

	ommp82PlusOduSevereErrorSeconds OBJECT-TYPE
		SYNTAX  DisplayString
		MAX-ACCESS  read-only
		STATUS  current
		DESCRIPTION
			"For port configured with OTU2/OTU1 traffic,
			ODU Severe Error Seconds increases on defects detected
			and when BIP errors are more than 15% Errored Blocks
			in incoming OTU signal.
			-----------------------------
			ommp82PlusInterfaceNumber:
			1 to 8 - CLIENT-1 to CLIENT-8
			9 - LINE-1
			10 - LINE-2
			-----------------------------
			Values:
			eg: 1234
			-----------------------------"
	::= { ommp82PlusPerformanceEntry 101 }

	ommp82PlusOduUnavailableSeconds OBJECT-TYPE
		SYNTAX  DisplayString
		MAX-ACCESS  read-only
		STATUS  current
		DESCRIPTION
			"For port configured with OTU2/OTU1 traffic,
			ODU Unavailable Seconds increases, when 10 consecutive
			Severe ODU Error seconds are detected
			-----------------------------
			ommp82PlusInterfaceNumber:
			1 to 8 - CLIENT-1 to CLIENT-8
			9 - LINE-1
			10 - LINE-2
			-----------------------------
			Values:
			eg: 1234
			-----------------------------"
	::= { ommp82PlusPerformanceEntry 102 }

	ommp82PlusOduBackgroundBlockErrorRatio OBJECT-TYPE
		SYNTAX  DisplayString
		MAX-ACCESS  read-only
		STATUS  current
		DESCRIPTION
			"For port configured with OTU2/OTU1 traffic,
			gives ODU Background Block Error Ratio i.e.
			the ratio of BBE in available time to total seconds
			in available time during a fixed measurement interval.
			-----------------------------
			ommp82PlusInterfaceNumber:
			1 to 8 - CLIENT-1 to CLIENT-8
			9 - LINE-1
			10 - LINE-2
			-----------------------------
			Values:
			eg: 1e-3
			-----------------------------"
	::= { ommp82PlusPerformanceEntry 104 }

	ommp82PlusOduSevereErrorSecondsErrorRatio OBJECT-TYPE
		SYNTAX  DisplayString
		MAX-ACCESS  read-only
		STATUS  current
		DESCRIPTION
			"For port configured with OTU2/OTU1 traffic,
			gives ODU Severe Error Seconds Error Ratio i.e.
			the ratio of SES in available time to total seconds
			in available time during a fixed measurement interval.
			-----------------------------
			ommp82PlusInterfaceNumber:
			1 to 8 - CLIENT-1 to CLIENT-8
			9 - LINE-1
			10 - LINE-2
			-----------------------------
			Values:
			eg: 1e-3
			-----------------------------"
	::= { ommp82PlusPerformanceEntry 105 }

	ommp82PlusOduFarEndErrorFreeSeconds OBJECT-TYPE
		SYNTAX  DisplayString
		MAX-ACCESS  read-only
		STATUS  current
		DESCRIPTION
			"For port configured with OTU2/OTU1 traffic,
			ODU Far end Error Free Seconds, increases when no
			far end errors or defects are detected
			-----------------------------
			ommp82PlusInterfaceNumber:
			1 to 8 - CLIENT-1 to CLIENT-8
			9 - LINE-1
			10 - LINE-2
			-----------------------------
			Values:
			eg: 1234
			-----------------------------"
	::= { ommp82PlusPerformanceEntry 106 }

	ommp82PlusOduFarEndErrorSeconds OBJECT-TYPE
		SYNTAX  DisplayString
		MAX-ACCESS  read-only
		STATUS  current
		DESCRIPTION
			"For port configured with OTU2/OTU1 traffic,
			ODU Far End Error Seconds increases on detection of
			defects like BDI and BEI at path monitoring level
			-----------------------------
			ommp82PlusInterfaceNumber:
			1 to 8 - CLIENT-1 to CLIENT-8
			9 - LINE-1
			10 - LINE-2
			-----------------------------
			Values:
			eg: 1234
			-----------------------------"
	::= { ommp82PlusPerformanceEntry 107 }

	ommp82PlusOduFarEndBackgroundBlockErrors OBJECT-TYPE
		SYNTAX  DisplayString
		MAX-ACCESS  read-only
		STATUS  current
		DESCRIPTION
			"For port configured with OTU2/OTU1 traffic,
			ODU Far End Background Block Errors increases when
			BEI errors are less than 15% Errored Blocks in
			incoming OTU signal.
			-----------------------------
			ommp82PlusInterfaceNumber:
			1 to 8 - CLIENT-1 to CLIENT-8
			9 - LINE-1
			10 - LINE-2
			-----------------------------
			Values:
			eg: 1234
			-----------------------------"
	::= { ommp82PlusPerformanceEntry 108 }

	ommp82PlusOduFarEndSevereErrorSeconds OBJECT-TYPE
		SYNTAX  DisplayString
		MAX-ACCESS  read-only
		STATUS  current
		DESCRIPTION
			"For port configured with OTU2/OTU1 traffic,
			ODU Far End Severe Error Seconds increases on defects
			like BDI are detected and when BEI errors are more than
			15% Errored Blocks in incoming OTU signal.
			-----------------------------
			ommp82PlusInterfaceNumber:
			1 to 8 - CLIENT-1 to CLIENT-8
			9 - LINE-1
			10 - LINE-2
			-----------------------------
			Values:
			eg: 1234
			-----------------------------"
	::= { ommp82PlusPerformanceEntry 109 }

	ommp82PlusOduFarEndUnavailableSeconds OBJECT-TYPE
		SYNTAX  DisplayString
		MAX-ACCESS  read-only
		STATUS  current
		DESCRIPTION
			"For port configured with OTU2/OTU1 traffic,
			ODU Far End Unavailable Seconds increases, when 10
			consecutive OTU Far End Error seconds are detected
			-----------------------------
			ommp82PlusInterfaceNumber:
			1 to 8 - CLIENT-1 to CLIENT-8
			9 - LINE-1
			10 - LINE-2
			-----------------------------
			Values:
			eg: 1234
			-----------------------------"
	::= { ommp82PlusPerformanceEntry 110 }

	ommp82PlusOduFarEndBackgroundBlockErrorRatio OBJECT-TYPE
		SYNTAX  DisplayString
		MAX-ACCESS  read-only
		STATUS  current
		DESCRIPTION
			"For port configured with OTU2/OTU1 traffic,
			gives ODU Far End Background Block Error Ratio i.e.
			the ratio of Far End BBE in available time to total
			seconds	in available time during a fixed measurement
			interval.
			-----------------------------
			ommp82PlusInterfaceNumber:
			1 to 8 - CLIENT-1 to CLIENT-8
			9 - LINE-1
			10 - LINE-2
			-----------------------------
			Values:
			eg: 1e-3
			-----------------------------"
	::= { ommp82PlusPerformanceEntry 112 }

	ommp82PlusOduFarEndSevereErrorSecondsErrorRatio OBJECT-TYPE
		SYNTAX  DisplayString
		MAX-ACCESS  read-only
		STATUS  current
		DESCRIPTION
			"For port configured with OTU2/OTU1 traffic,
			gives ODU Far End Severe Error Seconds Error Ratio i.e.
			The ratio of Far End SES in available time to total
			seconds in available time during a fixed measurement
			interval.
			-----------------------------
			ommp82PlusInterfaceNumber:
			1 to 8 - CLIENT-1 to CLIENT-8
			9 - LINE-1
			10 - LINE-2
			-----------------------------
			Values:
			eg: 1e-3
			-----------------------------"
	::= { ommp82PlusPerformanceEntry 113 }

	ommp82PlusSdhRsB1BitInterleavedParityErrors OBJECT-TYPE
		SYNTAX  DisplayString
		MAX-ACCESS  read-only
		STATUS  current
		DESCRIPTION
			"For port configured with STM1/4/16 traffic,
			SDH B1 BIP counter counts the Parity errors evaluated
			from byte B1 of the STM frame
			-----------------------------
			ommp82PlusInterfaceNumber:
			1 to 8 - CLIENT-1 to CLIENT-8
			-----------------------------
			Values:
			eg: 1234
			-----------------------------"
	::= { ommp82PlusPerformanceEntry 121 }

	ommp82PlusSdhMsB2BitInterleavedParityErrors OBJECT-TYPE
		SYNTAX  DisplayString
		MAX-ACCESS  read-only
		STATUS  current
		DESCRIPTION
			"For port configured with STM1/4/16 traffic,
			SDH B2 BIP counter counts the Parity errors evaluated 
			from byte B2 of the STM frame
			-----------------------------
			ommp82PlusInterfaceNumber:
			1 to 8 - CLIENT-1 to CLIENT-8
			-----------------------------
			Values:
			eg: 1234
			-----------------------------"
	::= { ommp82PlusPerformanceEntry 122 }

	ommp82PlusSdhMsB3BitInterleavedParityErrors OBJECT-TYPE
		SYNTAX  DisplayString
		MAX-ACCESS  read-only
		STATUS  current
		DESCRIPTION
			"For port configured with STM1/4/16 traffic,
			SDH B3 BIP counter counts the Parity errors evaluated 
			from byte B3 of the STM frame
			-----------------------------
			ommp82PlusInterfaceNumber:
			1 to 8 - CLIENT-1 to CLIENT-8
			-----------------------------
			Values:
			eg: 1234
			-----------------------------"
	::= { ommp82PlusPerformanceEntry 123 }

	ommp82PlusSdhMsRemoteErrorIndicationErrorCount OBJECT-TYPE
		SYNTAX  DisplayString
		MAX-ACCESS  read-only
		STATUS  current
		DESCRIPTION
			"For port configured with STM1/4/16 traffic,
			SDH MS-REI error count increases when
			MS-REI is detected for that particular second
			in incoming SDH signal.
			-----------------------------
			ommp82PlusInterfaceNumber:
			1 to 8 - CLIENT-1 to CLIENT-8
			-----------------------------
			Values:
			eg: 1234
			-----------------------------"
	::= { ommp82PlusPerformanceEntry 124 }

	ommp82PlusSdhMsRemoteDefectIndicationErrorCount OBJECT-TYPE
		SYNTAX  DisplayString
		MAX-ACCESS  read-only
		STATUS  current
		DESCRIPTION
			"For port configured with STM1/4/16 traffic,
			SDH MS-RDI error count increases when
			MS-RDI is detected for that particular second
			in incoming SDH signal.
			-----------------------------
			ommp82PlusInterfaceNumber:
			1 to 8 - CLIENT-1 to CLIENT-8
			-----------------------------
			Values:
			eg: 1234
			-----------------------------"
	::= { ommp82PlusPerformanceEntry 125 }

	ommp82PlusSdhErrorFreeSeconds OBJECT-TYPE
		SYNTAX  DisplayString
		MAX-ACCESS  read-only
		STATUS  current
		DESCRIPTION
			"For port configured with STM1/4/16 traffic,
			SDH Error Free Seconds increases when no BIP
			errors or no defects are detected in incoming
			SDH signal.
			-----------------------------
			ommp82PlusInterfaceNumber:
			1 to 8 - CLIENT-1 to CLIENT-8
			-----------------------------
			Values:
			eg: 1234
			-----------------------------"
	::= { ommp82PlusPerformanceEntry 126 }

	ommp82PlusSdhErrorSeconds OBJECT-TYPE
		SYNTAX  DisplayString
		MAX-ACCESS  read-only
		STATUS  current
		DESCRIPTION
			"For port configured with STM1/4/16 traffic,
			SDH Error Seconds increases on detection of BIP errors
			and defects like B1 errors, LOS, LOF in incoming SDH
			signal.
			-----------------------------
			ommp82PlusInterfaceNumber:
			1 to 8 - CLIENT-1 to CLIENT-8
			-----------------------------
			Values:
			eg: 1234
			-----------------------------"
	::= { ommp82PlusPerformanceEntry 127 }

	ommp82PlusSdhBackgroundBlockErrors OBJECT-TYPE
		SYNTAX  DisplayString
		MAX-ACCESS  read-only
		STATUS  current
		DESCRIPTION
			"For port configured with STM1/4/16 traffic,
			SDH Background Block Errors increases on defects 
			detected and when BIP errors are less than 30%
			errored blocks in the incoming SDH signal.
			-----------------------------
			ommp82PlusInterfaceNumber:
			1 to 8 - CLIENT-1 to CLIENT-8
			-----------------------------
			Values:
			eg: 1234
			-----------------------------"
	::= { ommp82PlusPerformanceEntry 128 }

	ommp82PlusSdhSevereErrorSeconds OBJECT-TYPE
		SYNTAX  DisplayString
		MAX-ACCESS  read-only
		STATUS  current
		DESCRIPTION
			"For port configured with STM1/4/16 traffic,
			SDH Severe Error Secodns increases on defects 
			detected and when BIP errors are greater than or equal
			to 30% errored blocks in the incoming SDH signal.
			-----------------------------
			ommp82PlusInterfaceNumber:
			1 to 8 - CLIENT-1 to CLIENT-8
			-----------------------------
			Values:
			eg: 1234
			-----------------------------"
	::= { ommp82PlusPerformanceEntry 129 }

	ommp82PlusSdhUnavailableSeconds OBJECT-TYPE
		SYNTAX  DisplayString
		MAX-ACCESS  read-only
		STATUS  current
		DESCRIPTION
			"For port configured with STM1/4/16 traffic,
			SDH Unavailable Seconds increases, when 10 consecutive
			Severe Error seconds are detected
			-----------------------------
			ommp82PlusInterfaceNumber:
			1 to 8 - CLIENT-1 to CLIENT-8
			-----------------------------
			Values:
			eg: 1234
			-----------------------------"
	::= { ommp82PlusPerformanceEntry 130 }

	ommp82PlusSdhErrorSecondsErrorRatio OBJECT-TYPE
		SYNTAX  DisplayString
		MAX-ACCESS  read-only
		STATUS  current
		DESCRIPTION
			"For port configured with STM1/4/16 traffic,
			gives SDH Error Seconds Error Ratio.
			The ratio of ES in available time to total seconds
			in available time during a fixed measurement interval.
			-----------------------------
			ommp82PlusInterfaceNumber:
			1 to 8 - CLIENT-1 to CLIENT-8
			-----------------------------
			Values:
			eg: 1234
			-----------------------------"
	::= { ommp82PlusPerformanceEntry 131 }

	ommp82PlusSdhBackgroundBlockErrorRatio OBJECT-TYPE
		SYNTAX  DisplayString
		MAX-ACCESS  read-only
		STATUS  current
		DESCRIPTION
			"For port configured with STM1/4/16 traffic,
			gives SDH Background Block Error Ratio.
			The ratio of BBE in available time to total seconds
			in available time during a fixed measurement interval.
			-----------------------------
			ommp82PlusInterfaceNumber:
			1 to 8 - CLIENT-1 to CLIENT-8
			-----------------------------
			Values:
			eg: 1234
			-----------------------------"
	::= { ommp82PlusPerformanceEntry 132 }

	ommp82PlusSdhSevereErrorSecondsErrorRatio OBJECT-TYPE
		SYNTAX  DisplayString
		MAX-ACCESS  read-only
		STATUS  current
		DESCRIPTION
			"For port configured with STM1/4/16 traffic,
			gives SDH Severe Error Seconds Error Ratio.
			The ratio of SES in available time to total seconds
			in available time during a fixed measurement interval.
			-----------------------------
			ommp82PlusInterfaceNumber:
			1 to 8 - CLIENT-1 to CLIENT-8
			-----------------------------
			Values:
			eg: 1234
			-----------------------------"
	::= { ommp82PlusPerformanceEntry 133 }

	ommp82PlusEthernetMacTerminatedFramesTransmitted OBJECT-TYPE
		SYNTAX  DisplayString
		MAX-ACCESS  read-only
		STATUS  current
		DESCRIPTION
			"For port configured with GE-GFP-F/FE-GFP-F traffic,
			gives the number of Ethernet frame transmitted.
			-----------------------------
			ommp82PlusInterfaceNumber:
			1 to 8 - CLIENT-1 to CLIENT-8
			-----------------------------
			Values:
			eg: 1234
			-----------------------------"
	::= { ommp82PlusPerformanceEntry 151 }

	ommp82PlusEthernetMacTerminatedFramesReceived OBJECT-TYPE
		SYNTAX  DisplayString
		MAX-ACCESS  read-only
		STATUS  current
		DESCRIPTION
			"For port configured with GE-GFP-F/FE-GFP-F traffic,
			gives the number of Ethernet frame received.
			-----------------------------
			ommp82PlusInterfaceNumber:
			1 to 8 - CLIENT-1 to CLIENT-8
			-----------------------------
			Values:
			eg: 1234
			-----------------------------"
	::= { ommp82PlusPerformanceEntry 152 }

	ommp82PlusEthernetMacTerminatedPauseFramesTransmitted OBJECT-TYPE
		SYNTAX  DisplayString
		MAX-ACCESS  read-only
		STATUS  current
		DESCRIPTION
			"For port configured with GE-GFP-F/FE-GFP-F traffic,
			gives number of Pause frame transmitted.
			-----------------------------
			ommp82PlusInterfaceNumber:
			1 to 8 - CLIENT-1 to CLIENT-8
			-----------------------------
			Values:
			eg: 1234
			-----------------------------"
	::= { ommp82PlusPerformanceEntry 153 }

	ommp82PlusEthernetMacTerminatedPauseFramesReceived OBJECT-TYPE
		SYNTAX  DisplayString
		MAX-ACCESS  read-only
		STATUS  current
		DESCRIPTION
			"For port configured with GE-GFP-F/FE-GFP-F traffic,
			gives the number of Pause frame received.
			-----------------------------
			ommp82PlusInterfaceNumber:
			1 to 8 - CLIENT-1 to CLIENT-8
			-----------------------------
			Values:
			eg: 1234
			-----------------------------"
	::= { ommp82PlusPerformanceEntry 154 }

	ommp82PlusEthernetMacTerminatedUnicastFramesTransmitted OBJECT-TYPE
		SYNTAX  DisplayString
		MAX-ACCESS  read-only
		STATUS  current
		DESCRIPTION
			"For port configured with GE-GFP-F/FE-GFP-F traffic,
			gives the number of unicast frames transmitted.
			-----------------------------
			ommp82PlusInterfaceNumber:
			1 to 8 - CLIENT-1 to CLIENT-8
			-----------------------------
			Values:
			eg: 1234
			-----------------------------"
	::= { ommp82PlusPerformanceEntry 155 }

	ommp82PlusEthernetMacTerminatedUnicastFramesReceived OBJECT-TYPE
		SYNTAX  DisplayString
		MAX-ACCESS  read-only
		STATUS  current
		DESCRIPTION
			"For port configured with GE-GFP-F/FE-GFP-F traffic,
			gives, the number of unicast frames received.
			-----------------------------
			ommp82PlusInterfaceNumber:
			1 to 8 - CLIENT-1 to CLIENT-8
			-----------------------------
			Values:
			eg: 1234
			-----------------------------"
	::= { ommp82PlusPerformanceEntry 156 }

	ommp82PlusEthernetMacTerminatedMulticastFramesTransmitted OBJECT-TYPE
		SYNTAX  DisplayString
		MAX-ACCESS  read-only
		STATUS  current
		DESCRIPTION
			"For port configured with GE-GFP-F/FE-GFP-F traffic,
			gives, the number of multicast frames transmitted.
			-----------------------------
			ommp82PlusInterfaceNumber:
			1 to 8 - CLIENT-1 to CLIENT-8
			-----------------------------
			Values:
			eg: 1234
			-----------------------------"
	::= { ommp82PlusPerformanceEntry 157 }

	ommp82PlusEthernetMacTerminatedMulticastFramesReceived OBJECT-TYPE
		SYNTAX  DisplayString
		MAX-ACCESS  read-only
		STATUS  current
		DESCRIPTION
			"For port configured with GE-GFP-F/FE-GFP-F traffic,
			gives the number of multicast frames received.
			-----------------------------
			ommp82PlusInterfaceNumber:
			1 to 8 - CLIENT-1 to CLIENT-8
			-----------------------------
			Values:
			eg: 1234
			-----------------------------"
	::= { ommp82PlusPerformanceEntry 158 }

	ommp82PlusEthernetMacTerminatedBroadcastFramesTransmitted OBJECT-TYPE
		SYNTAX  DisplayString
		MAX-ACCESS  read-only
		STATUS  current
		DESCRIPTION
			"For port configured with GE-GFP-F/FE-GFP-F traffic,
			gives the number of broadcast frames transmitted.
			-----------------------------
			ommp82PlusInterfaceNumber:
			1 to 8 - CLIENT-1 to CLIENT-8
			-----------------------------
			Values:
			eg: 1234
			-----------------------------"
	::= { ommp82PlusPerformanceEntry 159 }

	ommp82PlusEthernetMacTerminatedBroadcastFramesReceived OBJECT-TYPE
		SYNTAX  DisplayString
		MAX-ACCESS  read-only
		STATUS  current
		DESCRIPTION
			"For port configured with GE-GFP-F/FE-GFP-F traffic,
			gives the number of broadcast frames received.
			-----------------------------
			ommp82PlusInterfaceNumber:
			1 to 8 - CLIENT-1 to CLIENT-8
			-----------------------------
			Values:
			eg: 1234
			-----------------------------"
	::= { ommp82PlusPerformanceEntry 160 }

	ommp82PlusEthernetMacTerminatedUnderSizeFramesTransmitted OBJECT-TYPE
		SYNTAX  DisplayString
		MAX-ACCESS  read-only
		STATUS  current
		DESCRIPTION
			"For port configured with GE-GFP-F/FE-GFP-F traffic,
			gives the count of transmitted ethernet frames whose
			frame size is less than	64 bytes.
			-----------------------------
			ommp82PlusInterfaceNumber:
			1 to 8 - CLIENT-1 to CLIENT-8
			-----------------------------
			Values:
			eg: 1234
			-----------------------------"
	::= { ommp82PlusPerformanceEntry 161 }

	ommp82PlusEthernetMacTerminatedUnderSizeFramesReceived OBJECT-TYPE
		SYNTAX  DisplayString
		MAX-ACCESS  read-only
		STATUS  current
		DESCRIPTION
			"For port configured with GE-GFP-F/FE-GFP-F traffic,
			gives the count of received ethernet frames whose
			framesize is less than 64 bytes.
			-----------------------------
			ommp82PlusInterfaceNumber:
			1 to 8 - CLIENT-1 to CLIENT-8
			-----------------------------
			Values:
			eg: 1234
			-----------------------------"
	::= { ommp82PlusPerformanceEntry 162 }

	ommp82PlusEthernetMacTerminatedOverSizeFramesTransmitted OBJECT-TYPE
		SYNTAX  DisplayString
		MAX-ACCESS  read-only
		STATUS  current
		DESCRIPTION
			"For port configured with GE-GFP-F/FE-GFP-F traffic,
			gives the count of transmitted ethernet frames 
			whose frame size is greater than 1518 bytes.
			-----------------------------
			ommp82PlusInterfaceNumber:
			1 to 8 - CLIENT-1 to CLIENT-8
			-----------------------------
			Values:
			eg: 1234
			-----------------------------"
	::= { ommp82PlusPerformanceEntry 163 }

	ommp82PlusEthernetMacTerminatedOverSizeFramesReceived OBJECT-TYPE
		SYNTAX  DisplayString
		MAX-ACCESS  read-only
		STATUS  current
		DESCRIPTION
			"For port configured with GE-GFP-F/FE-GFP-F traffic,
			gives the count of received ethernet frames
			whose frame size is greater than 
			1518 bytes.
			-----------------------------
			ommp82PlusInterfaceNumber:
			1 to 8 - CLIENT-1 to CLIENT-8
			-----------------------------
			Values:
			eg: 1234
			-----------------------------"
	::= { ommp82PlusPerformanceEntry 164 }

	ommp82PlusEthernetMacTerminatedVlanTaggedFramesTransmitted OBJECT-TYPE
		SYNTAX  DisplayString
		MAX-ACCESS  read-only
		STATUS  current
		DESCRIPTION
			"For port configured with GE-GFP-F/FE-GFP-F traffic,
			gives the count of transmitted VLAN Tagged frames.
			-----------------------------
			ommp82PlusInterfaceNumber:
			1 to 8 - CLIENT-1 to CLIENT-8
			-----------------------------
			Values:
			eg: 1234
			-----------------------------"
	::= { ommp82PlusPerformanceEntry 165 }

	ommp82PlusEthernetMacTerminatedVlanTaggedFramesReceived OBJECT-TYPE
		SYNTAX  DisplayString
		MAX-ACCESS  read-only
		STATUS  current
		DESCRIPTION
			"For port configured with GE-GFP-F/FE-GFP-F traffic,
			gives the count of received VLAN Tagged frames.
			-----------------------------
			ommp82PlusInterfaceNumber:
			1 to 8 - CLIENT-1 to CLIENT-8
			-----------------------------
			Values:
			eg: 1234
			-----------------------------"
	::= { ommp82PlusPerformanceEntry 166 }

	ommp82PlusEthernetMacTerminatedFrameSymbolErrorsReceived OBJECT-TYPE
		SYNTAX  DisplayString
		MAX-ACCESS  read-only
		STATUS  current
		DESCRIPTION
			"For port configured with GE-GFP-F/FE-GFP-F traffic,
			gives the count of Frame Symbol Error received.
			-----------------------------
			ommp82PlusInterfaceNumber:
			1 to 8 - CLIENT-1 to CLIENT-8
			-----------------------------
			Values:
			eg: 1234
			-----------------------------"
	::= { ommp82PlusPerformanceEntry 167 }

	ommp82PlusEthernetMacTerminatedFragmentFramesReceived OBJECT-TYPE
		SYNTAX  DisplayString
		MAX-ACCESS  read-only
		STATUS  current
		DESCRIPTION
			"For port configured with GE-GFP-F/FE-GFP-F traffic,
			gives the count of Fragment Frames received.
			-----------------------------
			ommp82PlusInterfaceNumber:
			1 to 8 - CLIENT-1 to CLIENT-8
			-----------------------------
			Values:
			eg: 1234
			-----------------------------"
	::= { ommp82PlusPerformanceEntry 168 }

	ommp82PlusEthernetMacTerminatedFrameCheckSequenceErrorsReceived OBJECT-TYPE
		SYNTAX  DisplayString
		MAX-ACCESS  read-only
		STATUS  current
		DESCRIPTION
			"For port configured with GE-GFP-F/FE-GFP-F traffic,
			gives the count of Frame Check Sequence Errors received.
			-----------------------------
			ommp82PlusInterfaceNumber:
			1 to 8 - CLIENT-1 to CLIENT-8
			-----------------------------
			Values:
			eg: 1234
			-----------------------------"
	::= { ommp82PlusPerformanceEntry 169 }

	ommp82PlusEthernetMacTerminatedFramesReceivedWithNoDefect OBJECT-TYPE
		SYNTAX  DisplayString
		MAX-ACCESS  read-only
		STATUS  current
		DESCRIPTION
			"For port configured with GE-GFP-F/FE-GFP-F traffic,
			gives the count of frames that are 
			received with no defects such as undersized frames, FCS
			errors.
			-----------------------------
			ommp82PlusInterfaceNumber:
			1 to 8 - CLIENT-1 to CLIENT-8
			-----------------------------
			Values:
			eg: 1234
			-----------------------------"
	::= { ommp82PlusPerformanceEntry 170 }
	
	ommp82PlusEthernetMacTerminatedBytesTransmitted OBJECT-TYPE
		SYNTAX  DisplayString
		MAX-ACCESS  read-only
		STATUS  current
		DESCRIPTION
			"For port configured with GE-GFP-F/FE-GFP-F traffic,
			gives the count of the Ethernet bytes transmitted.
			-----------------------------
			ommp82PlusInterfaceNumber:
			1 to 8 - CLIENT-1 to CLIENT-8
			-----------------------------
			Values:
			eg: 1234
			-----------------------------"
	::= { ommp82PlusPerformanceEntry 171 }

	ommp82PlusEthernetMacTerminatedBytesReceived OBJECT-TYPE
		SYNTAX  DisplayString
		MAX-ACCESS  read-only
		STATUS  current
		DESCRIPTION
			"For port configured with GE-GFP-F/FE-GFP-F traffic,
			gives the count of Ethernet bytes received.
			-----------------------------
			ommp82PlusInterfaceNumber:
			1 to 8 - CLIENT-1 to CLIENT-8
			-----------------------------
			Values:
			eg: 1234
			-----------------------------"
	::= { ommp82PlusPerformanceEntry 172 }

	ommp82PlusEthernetMacTerminatedControlFramesTransmitted OBJECT-TYPE
		SYNTAX  DisplayString
		MAX-ACCESS  read-only
		STATUS  current
		DESCRIPTION
			"For port configured with GE-GFP-F/FE-GFP-F traffic,
			gives the count of the Ethernet control frames
			transmitted.
			-----------------------------
			ommp82PlusInterfaceNumber:
			1 to 8 - CLIENT-1 to CLIENT-8
			-----------------------------
			Values:
			eg: 1234
			-----------------------------"
	::= { ommp82PlusPerformanceEntry 173 }

	ommp82PlusEthernetMacTerminatedControlFramesReceived OBJECT-TYPE
		SYNTAX  DisplayString
		MAX-ACCESS  read-only
		STATUS  current
		DESCRIPTION
			"For port configured with GE-GFP-F/FE-GFP-F traffic,
			gives the count of the Ethernet control frames
			received.
			-----------------------------
			ommp82PlusInterfaceNumber:
			1 to 8 - CLIENT-1 to CLIENT-8
			-----------------------------
			Values:
			eg: 1234
			-----------------------------"
	::= { ommp82PlusPerformanceEntry 174 }

	ommp82PlusEthernetTransparentTransmitLcvCount OBJECT-TYPE
		SYNTAX  DisplayString
		MAX-ACCESS  read-only
		STATUS  current
		DESCRIPTION
			"For port configured with GE-GFP-T/FE-GFP-T traffic,
			gives the count of Transparent LCV that are transmitted.
			-----------------------------
			ommp82PlusInterfaceNumber:
			1 to 8 - CLIENT-1 to CLIENT-8
			-----------------------------
			Values:
			eg: 1234
			-----------------------------"
	::= { ommp82PlusPerformanceEntry 181 }

	ommp82PlusEthernetTransparentTransmitPropagationErrorDeletionCount OBJECT-TYPE
		SYNTAX  DisplayString
		MAX-ACCESS  read-only
		STATUS  current
		DESCRIPTION
			"For port configured with GE-GFP-T/FE-GFP-T traffic,
			gives the count of Propagation Error Deletion Count
			that are transmitted.
			-----------------------------
			ommp82PlusInterfaceNumber:
			1 to 8 - CLIENT-1 to CLIENT-8
			-----------------------------
			Values:
			eg: 1234
			-----------------------------"
	::= { ommp82PlusPerformanceEntry 182 }

	ommp82PlusEthernetTransparentTransmitIdleDeletionCount OBJECT-TYPE
		SYNTAX  DisplayString
		MAX-ACCESS  read-only
		STATUS  current
		DESCRIPTION
			"For port configured with GE-GFP-T/FE-GFP-T traffic,
			gives the count of Idle Deletion Count that are
			transmitted.
			-----------------------------
			ommp82PlusInterfaceNumber:
			1 to 8 - CLIENT-1 to CLIENT-8
			-----------------------------
			Values:
			eg: 1234
			-----------------------------"
	::= { ommp82PlusPerformanceEntry 183 }

	ommp82PlusEthernetTransparentTransmitConfDeletionCount OBJECT-TYPE
		SYNTAX  DisplayString
		MAX-ACCESS  read-only
		STATUS  current
		DESCRIPTION
			"For port configured with GE-GFP-T/FE-GFP-T traffic,
			gives the count of Conf Deletion Count that are
			transmitted.
			-----------------------------
			ommp82PlusInterfaceNumber:
			1 to 8 - CLIENT-1 to CLIENT-8
			-----------------------------
			Values:
			eg: 1234
			-----------------------------"
	::= { ommp82PlusPerformanceEntry 184 }

	ommp82PlusEthernetTransparentTransmitPropagationInsertionCount OBJECT-TYPE
		SYNTAX  DisplayString
		MAX-ACCESS  read-only
		STATUS  current
		DESCRIPTION
			"For port configured with GE-GFP-T/FE-GFP-T traffic,
			gives the count of Propagation Insertions that are
			transmitted.
			-----------------------------
			ommp82PlusInterfaceNumber:
			1 to 8 - CLIENT-1 to CLIENT-8
			-----------------------------
			Values:
			eg: 1234
			-----------------------------"
	::= { ommp82PlusPerformanceEntry 185 }

	ommp82PlusEthernetTransparentTransmitIdleInsertionCount OBJECT-TYPE
		SYNTAX  DisplayString
		MAX-ACCESS  read-only
		STATUS  current
		DESCRIPTION
			"For port configured with GE-GFP-T/FE-GFP-T traffic,
			gives the count of Idle Insertions that are tranmsitted.
			-----------------------------
			ommp82PlusInterfaceNumber:
			1 to 8 - CLIENT-1 to CLIENT-8
			-----------------------------
			Values:
			eg: 1234
			-----------------------------"
	::= { ommp82PlusPerformanceEntry 186 }

	ommp82PlusEthernetTransparentTransmitConfInsertionCount OBJECT-TYPE
		SYNTAX  DisplayString
		MAX-ACCESS  read-only
		STATUS  current
		DESCRIPTION
			"For port configured with GE-GFP-T/FE-GFP-T traffic,
			gives the count of Conf Insertions that are tranmsitted.
			-----------------------------
			ommp82PlusInterfaceNumber:
			1 to 8 - CLIENT-1 to CLIENT-8
			-----------------------------
			Values:
			eg: 1234
			-----------------------------"
	::= { ommp82PlusPerformanceEntry 187 }

	ommp82PlusEthernetTransparentReceiveLcvCount OBJECT-TYPE
		SYNTAX  DisplayString
		MAX-ACCESS  read-only
		STATUS  current
		DESCRIPTION
			"For port configured with GE-GFP-T/FE-GFP-T traffic,
			gives the count of LCV that are received.
			-----------------------------
			ommp82PlusInterfaceNumber:
			1 to 8 - CLIENT-1 to CLIENT-8
			-----------------------------
			Values:
			eg: 1234
			-----------------------------"
	::= { ommp82PlusPerformanceEntry 188 }

	ommp82PlusEthernetTransparentReceivePropagationErrorDeletionCount OBJECT-TYPE
		SYNTAX  DisplayString
		MAX-ACCESS  read-only
		STATUS  current
		DESCRIPTION
			"For port configured with GE-GFP-T/FE-GFP-T traffic,
			gives the count of Propagation Error Deletions that are
			received.
			-----------------------------
			ommp82PlusInterfaceNumber:
			1 to 8 - CLIENT-1 to CLIENT-8
			-----------------------------
			Values:
			eg: 1234
			-----------------------------"
	::= { ommp82PlusPerformanceEntry 189 }

	ommp82PlusEthernetTransparentReceiveIdleDeletionCount OBJECT-TYPE
		SYNTAX  DisplayString
		MAX-ACCESS  read-only
		STATUS  current
		DESCRIPTION
			"For port configured with GE-GFP-T/FE-GFP-T traffic,
			gives the count of Idle Deletions that are
			received.
			-----------------------------
			ommp82PlusInterfaceNumber:
			1 to 8 - CLIENT-1 to CLIENT-8
			-----------------------------
			Values:
			eg: 1234
			-----------------------------"
	::= { ommp82PlusPerformanceEntry 190 }

	ommp82PlusEthernetTransparentReceiveConfDeletionCount OBJECT-TYPE
		SYNTAX  DisplayString
		MAX-ACCESS  read-only
		STATUS  current
		DESCRIPTION
			"For port configured with GE-GFP-T/FE-GFP-T traffic,
			gives the count of Conf Deletions that are
			received.
			-----------------------------
			ommp82PlusInterfaceNumber:
			1 to 8 - CLIENT-1 to CLIENT-8
			-----------------------------
			Values:
			eg: 1234
			-----------------------------"
	::= { ommp82PlusPerformanceEntry 191 }

	ommp82PlusEthernetTransparentReceivePacketDeletionCount OBJECT-TYPE
		SYNTAX  DisplayString
		MAX-ACCESS  read-only
		STATUS  current
		DESCRIPTION
			"For port configured with GE-GFP-T/FE-GFP-T traffic,
			gives the count of Packet Deletions that are
			received.
			-----------------------------
			ommp82PlusInterfaceNumber:
			1 to 8 - CLIENT-1 to CLIENT-8
			-----------------------------
			Values:
			eg: 1234
			-----------------------------"
	::= { ommp82PlusPerformanceEntry 192 }

	ommp82PlusGfpCoreHeaderErrorCount OBJECT-TYPE
		SYNTAX  DisplayString
		MAX-ACCESS  read-only
		STATUS  current
		DESCRIPTION
			"For port configured with
			GE-GFP-F/FE-GFP-F/GE-GFP-T/FE-GFP-T traffic,
			gives the count of received GFP frames which have error
			in the core header.
			-----------------------------
			ommp82PlusInterfaceNumber:
			1 to 8 - CLIENT-1 to CLIENT-8
			-----------------------------
			Values:
			eg: 1234
			-----------------------------"
	::= { ommp82PlusPerformanceEntry 201 }

	ommp82PlusGfpExtentionHeaderErrorCount OBJECT-TYPE
		SYNTAX  DisplayString
		MAX-ACCESS  read-only
		STATUS  current
		DESCRIPTION
			"For port configured with
			GE-GFP-F/FE-GFP-F/GE-GFP-T/FE-GFP-T traffic,
			gives the count of received GFP frames which have error
			in the extention header.
			-----------------------------
			ommp82PlusInterfaceNumber:
			1 to 8 - CLIENT-1 to CLIENT-8
			-----------------------------
			Values:
			eg: 1234
			-----------------------------"
	::= { ommp82PlusPerformanceEntry 202 }

	ommp82PlusGfpFrameCountWithSingleBitError OBJECT-TYPE
		SYNTAX  DisplayString
		MAX-ACCESS  read-only
		STATUS  current
		DESCRIPTION
			"For port configured with
			GE-GFP-F/FE-GFP-F/GE-GFP-T/FE-GFP-T traffic,
			gives the count of GFP Frames that are received 
			with single bit error.
			-----------------------------
			ommp82PlusInterfaceNumber:
			1 to 8 - CLIENT-1 to CLIENT-8
			-----------------------------
			Values:
			eg: 1234
			-----------------------------"
	::= { ommp82PlusPerformanceEntry 203 }

	ommp82PlusGfpTypeHeaderErrorCount OBJECT-TYPE
		SYNTAX  DisplayString
		MAX-ACCESS  read-only
		STATUS  current
		DESCRIPTION
			"For port configured with
			GE-GFP-F/FE-GFP-F/GE-GFP-T/FE-GFP-T traffic,
			gives the count of received GFP frames which have error
			in the type header.
			-----------------------------
			ommp82PlusInterfaceNumber:
			1 to 8 - CLIENT-1 to CLIENT-8
			-----------------------------
			Values:
			eg: 1234
			-----------------------------"
	::= { ommp82PlusPerformanceEntry 204 }

	ommp82PlusGfpReceiveDropFrameCount OBJECT-TYPE
		SYNTAX  DisplayString
		MAX-ACCESS  read-only
		STATUS  current
		DESCRIPTION
			"For port configured with
			GE-GFP-F/FE-GFP-F/GE-GFP-T/FE-GFP-T traffic,
			gives the Drop Frame count of received GFP frames.
			-----------------------------
			ommp82PlusInterfaceNumber:
			1 to 8 - CLIENT-1 to CLIENT-8
			-----------------------------
			Values:
			eg: 1234
			-----------------------------"
	::= { ommp82PlusPerformanceEntry 205 }

	ommp82PlusGfpReceiveExtensionHeaderIdentifierFilterDropCount OBJECT-TYPE
		SYNTAX  DisplayString
		MAX-ACCESS  read-only
		STATUS  current
		DESCRIPTION
			"For port configured with
			GE-GFP-F/FE-GFP-F/GE-GFP-T/FE-GFP-T traffic,
			gives the Extension Header Identifier Filter
			Drop count of received GFP frames.
			-----------------------------
			ommp82PlusInterfaceNumber:
			1 to 8 - CLIENT-1 to CLIENT-8
			-----------------------------
			Values:
			eg: 1234
			-----------------------------"
	::= { ommp82PlusPerformanceEntry 206 }

	ommp82PlusFcTransmitWordCount OBJECT-TYPE
		SYNTAX  DisplayString
		MAX-ACCESS  read-only
		STATUS  current
		DESCRIPTION
			"For port configured with FC-100/FC-200 traffic,
			gives the count of words that are transmitted.
			-----------------------------
			ommp82PlusInterfaceNumber:
			1 to 8 - CLIENT-1 to CLIENT-8
			-----------------------------
			Values:
			eg: 1234
			-----------------------------"
	::= { ommp82PlusPerformanceEntry 211 }

	ommp82PlusFcReceiveWordCount OBJECT-TYPE
		SYNTAX  DisplayString
		MAX-ACCESS  read-only
		STATUS  current
		DESCRIPTION
			"For port configured with FC-100/FC-200 traffic,
			gives the count of words that are received.
			-----------------------------
			ommp82PlusInterfaceNumber:
			1 to 8 - CLIENT-1 to CLIENT-8
			-----------------------------
			Values:
			eg: 1234
			-----------------------------"
	::= { ommp82PlusPerformanceEntry 212 }

	ommp82PlusFcTransmitTotalPackets OBJECT-TYPE
		SYNTAX  DisplayString
		MAX-ACCESS  read-only
		STATUS  current
		DESCRIPTION
			"For port configured with FC-100/FC-200 traffic,
			gives the count of total packets that are tranmsitted.
			-----------------------------
			ommp82PlusInterfaceNumber:
			1 to 8 - CLIENT-1 to CLIENT-8
			-----------------------------
			Values:
			eg: 1234
			-----------------------------"
	::= { ommp82PlusPerformanceEntry 213 }

	ommp82PlusFcReceiveTotalPackets OBJECT-TYPE
		SYNTAX  DisplayString
		MAX-ACCESS  read-only
		STATUS  current
		DESCRIPTION
			"For port configured with FC-100/FC-200 traffic,
			gives the count of total packets that are received.
			-----------------------------
			ommp82PlusInterfaceNumber:
			1 to 8 - CLIENT-1 to CLIENT-8
			-----------------------------
			Values:
			eg: 1234
			-----------------------------"
	::= { ommp82PlusPerformanceEntry 214 }

	ommp82PlusFcTransmitBadCrc OBJECT-TYPE
		SYNTAX  DisplayString
		MAX-ACCESS  read-only
		STATUS  current
		DESCRIPTION
			"For port configured with FC-100/FC-200 traffic,
			gives the count of bad CRCs that are tranmsitted.
			-----------------------------
			ommp82PlusInterfaceNumber:
			1 to 8 - CLIENT-1 to CLIENT-8
			-----------------------------
			Values:
			eg: 1234
			-----------------------------"
	::= { ommp82PlusPerformanceEntry 215 }

	ommp82PlusFcReceiveBadCrc OBJECT-TYPE
		SYNTAX  DisplayString
		MAX-ACCESS  read-only
		STATUS  current
		DESCRIPTION
			"For port configured with FC-100/FC-200 traffic,
			gives the frame count of that
			had CRC32 mismatch, invalid/abort end-of-frame or
			line code violations.
			-----------------------------
			ommp82PlusInterfaceNumber:
			1 to 8 - CLIENT-1 to CLIENT-8
			-----------------------------
			Values:
			eg: 1234
			-----------------------------"
	::= { ommp82PlusPerformanceEntry 216 }

	ommp82PlusFcTransmitLcvCount OBJECT-TYPE
		SYNTAX  DisplayString
		MAX-ACCESS  read-only
		STATUS  current
		DESCRIPTION
			"For port configured with FC-100/FC-200 traffic,
			reports the number of 8B/10B line-code violations
			(invalid characters or incorrect running
			disparity) that occurred on the data from upstream
			block.
			-----------------------------
			ommp82PlusInterfaceNumber:
			1 to 8 - CLIENT-1 to CLIENT-8
			-----------------------------
			Values:
			eg: 1234
			-----------------------------"
	::= { ommp82PlusPerformanceEntry 217 }

	ommp82PlusFcReceiveLcvCount OBJECT-TYPE
		SYNTAX  DisplayString
		MAX-ACCESS  read-only
		STATUS  current
		DESCRIPTION
			"For port configured with FC-100/FC-200 traffic,
			reports the number of 8B/10B line-code violations
			(invalid characters or incorrect running disparity) that
			occurred on the data from line interface.
			-----------------------------
			ommp82PlusInterfaceNumber:
			1 to 8 - CLIENT-1 to CLIENT-8
			-----------------------------
			Values:
			eg: 1234
			-----------------------------"
	::= { ommp82PlusPerformanceEntry 218 }

	ommp82PlusFcTransmitFillWordInsertionCount OBJECT-TYPE
		SYNTAX  DisplayString
		MAX-ACCESS  read-only
		STATUS  current
		DESCRIPTION
			"For port configured with FC-100/FC-200 traffic,
			gives the count of FW Insertion count. It
			reports number of fill words that were inserted
			for rate adaptation. For fibre channel, each increment
			indicates the number of 4-character IDLE
			(or ARBs - when enabled) ordered set that were inserted.
			-----------------------------
			ommp82PlusInterfaceNumber:
			1 to 8 - CLIENT-1 to CLIENT-8
			-----------------------------
			Values:
			eg: 1234
			-----------------------------"
	::= { ommp82PlusPerformanceEntry 219 }

	ommp82PlusFcTransmitPrimitiveSequenceInsertionCount OBJECT-TYPE
		SYNTAX  DisplayString
		MAX-ACCESS  read-only
		STATUS  current
		DESCRIPTION
			"For port configured with FC-100/FC-200 traffic,
			gives the count of Primitive Sequence Insertions. It
			reports number of primitive sequences or sequence
			functions that were inserted for rate adaptation.
			For fibre channel, each increment indicates the number
			of 4-character Primitive Sequences that
			were inserted.
			-----------------------------
			ommp82PlusInterfaceNumber:
			1 to 8 - CLIENT-1 to CLIENT-8
			-----------------------------
			Values:
			eg: 1234
			-----------------------------"
	::= { ommp82PlusPerformanceEntry 220 }

	ommp82PlusFcTransmitFillWordDeletionCount OBJECT-TYPE
		SYNTAX  DisplayString
		MAX-ACCESS  read-only
		STATUS  current
		DESCRIPTION
			"For port configured with FC-100/FC-200 traffic,
			gives the count of number of fill words that were
			deleted for rate adaptation.
			-----------------------------
			ommp82PlusInterfaceNumber:
			1 to 8 - CLIENT-1 to CLIENT-8
			-----------------------------
			Values:
			eg: 1234
			-----------------------------"
	::= { ommp82PlusPerformanceEntry 221 }

	ommp82PlusFcTransmitPrimitiveSequenceDeletionCount OBJECT-TYPE
		SYNTAX  DisplayString
		MAX-ACCESS  read-only
		STATUS  current
		DESCRIPTION
			"For port configured with FC-100/FC-200 traffic,
			reports number of Primitive Signals or Sequence
			Functions that were deleted for rate adaptation.
			For fibre channel, each increment indicates the
			number of 4-character Primitive Sequences that were
			deleted.
			-----------------------------
			ommp82PlusInterfaceNumber:
			1 to 8 - CLIENT-1 to CLIENT-8
			-----------------------------
			Values:
			eg: 1234
			-----------------------------"
	::= { ommp82PlusPerformanceEntry 222 }

	ommp82PlusPerformanceTableRowStatus OBJECT-TYPE
              SYNTAX      RowStatus
              MAX-ACCESS  read-write
              STATUS      current
              DESCRIPTION
			"*****************************
			This is MIB realted property,
			NOT to be considered as a card property
			*****************************"
              ::= { ommp82PlusPerformanceEntry 223 }
              
--*****************************************************************************
--				    DIAGNOSTICS
--*****************************************************************************        

	ommp82PlusDiagnosticsTable OBJECT-TYPE
	      SYNTAX  SEQUENCE OF Ommp82PlusDiagnosticsEntry
              MAX-ACCESS  not-accessible
              STATUS  current
              DESCRIPTION
                      "Category contains properties that are used for debugging
                      card software"
		::= { ommp82PlusDiagnostics 1 }	

	ommp82PlusDiagnosticsEntry   OBJECT-TYPE
              SYNTAX  Ommp82PlusDiagnosticsEntry 
              MAX-ACCESS  not-accessible
              STATUS  current
              DESCRIPTION 
              	""
		INDEX   { node, rack , subRack , slot , ommp82PlusInterfaceNumber }
		::= { ommp82PlusDiagnosticsTable 1 }
	
	Ommp82PlusDiagnosticsEntry ::= 
		SEQUENCE {
				ommp82PlusAccessHyphyRegister			INTEGER,
				ommp82PlusCnodeCrashCount			INTEGER,
				ommp82PlusKernelState				DisplayString,
				ommp82PlusDiagnosticTableRowStatus		RowStatus
			}
			
	ommp82PlusAccessHyphyRegister OBJECT-TYPE
		SYNTAX  INTEGER
		MAX-ACCESS  read-write
		STATUS  current
		DESCRIPTION
			"Sets/gets the value of any hyphy register
			-----------------------------
			ommp82PlusInterfaceNumber: 0
			-----------------------------
			Values:
			eg:
			example of hyphy register - 76071076
			value - 1
			-----------------------------"
	::= { ommp82PlusDiagnosticsEntry 1 }

	ommp82PlusCnodeCrashCount OBJECT-TYPE
		SYNTAX  INTEGER
		MAX-ACCESS  read-only
		STATUS  current
		DESCRIPTION
			"Gets the count of number of times the hyphy_cnode has
			crashed
			-----------------------------
			ommp82PlusInterfaceNumber: 0
			-----------------------------
			Values: 
			eg: 0, 1, 4, 7 etc.
			-----------------------------"
	::= { ommp82PlusDiagnosticsEntry 2 }

	ommp82PlusKernelState OBJECT-TYPE
		SYNTAX  DisplayString
		MAX-ACCESS  read-only
		STATUS  current
		DESCRIPTION
			"Gets the state of the kernel
			-----------------------------
			ommp82PlusInterfaceNumber: 0
			-----------------------------
			Values:
			non-tainted - kernel is working fine
			tainted - kernel panic has occured
			-----------------------------"
	::= { ommp82PlusDiagnosticsEntry 3 }
	
	ommp82PlusDiagnosticTableRowStatus OBJECT-TYPE
              SYNTAX      RowStatus
              MAX-ACCESS  read-write
              STATUS      current
              DESCRIPTION
			"*****************************
			This is MIB realted property,
			NOT to be considered as a card property
			*****************************"
	::= { ommp82PlusDiagnosticsEntry 4 }

--*****************************************************************************

--*****************************************************************************

	snmpCurrentNotificationsGroup NOTIFICATION-GROUP
		NOTIFICATIONS { 
					ommp82PlusXfpInputPowerFailureAlarmTrap,
					ommp82PlusXfpOutputPowerFailureAlarmTrap,
					ommp82PlusXfpHighTemperatureAlarmTrap,
					ommp82PlusXfpLowTemperatureAlarmTrap,
					ommp82PlusXfpHighTemperatureWarningTrap,
					ommp82PlusXfpLowTemperatureWarningTrap,
					ommp82PlusXfpHighBiasCurrentAlarmTrap,
					ommp82PlusXfpLowBiasCurrentAlarmTrap,
					ommp82PlusXfpHighBiasCurrentWarningTrap,
					ommp82PlusXfpLowBiasCurrentWarningTrap,
					ommp82PlusXfpInputHighPowerAlarmTrap,
					ommp82PlusXfpInputLowPowerAlarmTrap,
					ommp82PlusXfpInputHighPowerWarningTrap,
					ommp82PlusXfpInputLowPowerWarningTrap,
					ommp82PlusXfpOutputHighPowerAlarmTrap,
					ommp82PlusXfpOutputLowPowerAlarmTrap,
					ommp82PlusXfpOutputHighPowerWarningTrap,
					ommp82PlusXfpOutputLowPowerWarningTrap,
					ommp82PlusXfpHighSupplyVoltageAlarmTrap,
					ommp82PlusXfpLowSupplyVoltageAlarmTrap,
					ommp82PlusXfpHighSupplyVoltageWarningTrap,
					ommp82PlusXfpLowSupplyVoltageWarningTrap,
					ommp82PlusXfpPresenceAbsenceNotificationTrap,
					ommp82PlusSfpInputPowerFailureAlarmTrap,
					ommp82PlusSfpOutputPowerFailureAlarmTrap,
					ommp82PlusSfpHighTemperatureAlarmTrap,
					ommp82PlusSfpLowTemperatureAlarmTrap,
					ommp82PlusSfpHighTemperatureWarningTrap,
					ommp82PlusSfpLowTemperatureWarningTrap,
					ommp82PlusSfpHighBiasCurrentAlarmTrap,
					ommp82PlusSfpLowBiasCurrentAlarmTrap,
					ommp82PlusSfpHighBiasCurrentWarningTrap,
					ommp82PlusSfpLowBiasCurrentWarningTrap,
					ommp82PlusSfpInputHighPowerAlarmTrap,
					ommp82PlusSfpInputLowPowerAlarmTrap,
					ommp82PlusSfpInputHighPowerWarningTrap,
					ommp82PlusSfpInputLowPowerWarningTrap,
					ommp82PlusSfpOutputHighPowerAlarmTrap,
					ommp82PlusSfpOutputLowPowerAlarmTrap,
					ommp82PlusSfpOutputHighPowerWarningTrap,
					ommp82PlusSfpOutputLowPowerWarningTrap,
					ommp82PlusSfpHighSupplyVoltageAlarmTrap,
					ommp82PlusSfpLowSupplyVoltageAlarmTrap,
					ommp82PlusSfpHighSupplyVoltageWarningTrap,
					ommp82PlusSfpLowSupplyVoltageWarningTrap,
					ommp82PlusSfpPresenceAbsenceNotificationTrap,
					ommp82PlusSfpTransmitFaultPresenceAlarmTrap,
					ommp82PlusOtuLossOfSignalAlarmTrap,
					ommp82PlusOtuLossOfFrameAlarmTrap,
					ommp82PlusOtuOutOfFrameAlarmTrap,
					ommp82PlusOtuLossOfMultiFrameAlarmTrap,
					ommp82PlusOtuOutOfMultiFrameAlarmTrap,
					ommp82PlusOtuSignalFailAlarmTrap,
					ommp82PlusOtuSignalDegradeAlarmTrap,
					ommp82PlusOtuAlarmIndicationSignalAlarmTrap,
					ommp82PlusOtuIncomingAlignmentErrorAlarmTrap,
					ommp82PlusOtuTraceIdentifierMismatchAlarmTrap,
					ommp82PlusOtuBackwardIncomingAlignmentErrorAlarmTrap,
					ommp82PlusOtuBackwardDefectIndicationAlarmTrap,
					ommp82PlusOduSignalFailAlarmTrap,
					ommp82PlusOduSignalDegradeAlarmTrap,
					ommp82PlusOduAlarmIndicationSignalAlarmTrap,
					ommp82PlusOduTcm1IncomingAlignmentErrorAlarmTrap,
					ommp82PlusOduTcm2IncomingAlignmentErrorAlarmTrap,
					ommp82PlusOduTcm3IncomingAlignmentErrorAlarmTrap,
					ommp82PlusOduTcm4IncomingAlignmentErrorAlarmTrap,
					ommp82PlusOduTcm5IncomingAlignmentErrorAlarmTrap,
					ommp82PlusOduTcm6IncomingAlignmentErrorAlarmTrap,
					ommp82PlusOduTraceIdentifierMismatchAlarmTrap,
					ommp82PlusOduLockedDefectAlarmTrap,
					ommp82PlusOduOpenConnectionIndicationAlarmTrap,
					ommp82PlusOduBackwardDefectIndicationAlarmTrap,
					ommp82PlusOduTcm1BackwardIncomingAlignmentErrorAlarmTrap,
					ommp82PlusOduTcm2BackwardIncomingAlignmentErrorAlarmTrap,
					ommp82PlusOduTcm3BackwardIncomingAlignmentErrorAlarmTrap,
					ommp82PlusOduTcm4BackwardIncomingAlignmentErrorAlarmTrap,
					ommp82PlusOduTcm5BackwardIncomingAlignmentErrorAlarmTrap,
					ommp82PlusOduTcm6BackwardIncomingAlignmentErrorAlarmTrap,
					ommp82PlusOduLossOfFrameLossOfMultiframeAlarmTrap,
					ommp82PlusOpuPayloadMismatchAlarmTrap,
					ommp82PlusOchLossOfPayloadAlarmTrap,
					ommp82PlusSdhLossOfSignalAlarmTrap,
					ommp82PlusSdhOutOfFrameAlarmTrap,
					ommp82PlusSdhLossOfFrameAlarmTrap,
					ommp82PlusSdhRsAlarmIndicationSignalAlarmTrap,
					ommp82PlusSdhRsTraceIdentifierMismatchAlarmTrap,
					ommp82PlusSdhAuAlarmIndicationSignalAlarmTrap,
					ommp82PlusSdhAuLossOfPointerAlarmTrap,
					ommp82PlusSdhMsAlarmIndicationSignalAlarmTrap,
					ommp82PlusSdhMsRemoteErrorIndicationAlarmTrap,
					ommp82PlusSdhMsRemoteDefectIndicationAlarmTrap,
					ommp82PlusSdhMsRemoteFailureIndicationAlarmTrap,
					ommp82PlusSdhMsB2ExcessiveErrorAlarmTrap,
					ommp82PlusSdhMsB2SignalDegradeAlarmTrap,
					ommp82PlusSdhLossOfSequenceSynchronisationAlarmTrap,
					ommp82PlusSdhLowerOrderPathPayloadLabelMismatchAlarmTrap,
					ommp82PlusSdhLowerOrderPathUnequippedAlarmTrap,
					ommp82PlusEthernetLossOfSignalAlarmTrap,
					ommp82PlusEthernetLossOfSignalSyncAlarmTrap,
					ommp82PlusEthernetLinkFailureAlarmTrap,
					ommp82PlusEthernetAutoNegotiationAlarmTrap,
					ommp82PlusEthernetFrameCheckSequenceAlarmTrap,
					ommp82PlusEthernetCarrierStatusAlarmTrap,
					ommp82PlusEthernetHighBerAlarmTrap,
					ommp82PlusEthernetLocalFaultAlarmTrap,
					ommp82PlusEthernetRemoteFaultAlarmTrap,
					ommp82PlusFcTransmitDisparityInversionDefectAlarmTrap,
					ommp82PlusFcTransmitDigitalLossOfLinkDefectAlarmTrap,
					ommp82PlusFcTrasnmitLossOfSynchronizationDefectAlarmTrap,
					ommp82PlusFcReceiveDigitalLossOfLinkDefectAlarmTrap,
					ommp82PlusFcReceiveLossOfSynchronizationDefectAlarmTrap,
					ommp82PlusFcReceiveTransitionDetectDefectAlarmTrap,
					ommp82PlusFcReceiveAnalogLossOfSignalDefectAlarmTrap,
					ommp82PlusFcReceiveLineCodeViolationDefectAlarmTrap,
					ommp82PlusGfpCsfSignalFailAlarmTrap,
					ommp82PlusGfpCsfLinkFailAlarmTrap,
					ommp82PlusGfpCoreHeaderErrorAlarmTrap,
					ommp82PlusGfpExtentionHeaderErrorAlarmTrap
				}
  	STATUS current
	DESCRIPTION
  	   	"The UTL OMMP82-PLUS current notifications group"
  	::= { ommp82Plus 6 }

            snmpcurrentGroup OBJECT-GROUP
    OBJECTS 	{ 
			ommp82PlusInterfaceNumber,	
    			ommp82PlusEepromCardId,
			ommp82PlusEepromCardName,
			ommp82PlusEepromPartCode,
			ommp82PlusEepromCardSerialNumber,
			ommp82PlusEepromHardwareExternalReleaseVersion,
			ommp82PlusSoftwareExternalReleaseVersion,
			ommp82PlusEepromHardwareInternalReleaseVersion,
			ommp82PlusSoftwareInternalReleaseVersion,
			ommp82PlusEepromCardUidNumber,
			ommp82PlusEepromCardEui48Number,
			ommp82PlusEepromCardEui64Number,
			ommp82PlusCardRootFileSystemVersion,
			ommp82PlusCardInstallationDate,
			ommp82PlusCardCommissionDate,
			ommp82PlusCardRunningTime,
			ommp82PlusCardRestartCount,
			ommp82PlusXfpReadyForOperation,
			ommp82PlusXfpI2cCommunicationStatus,
			ommp82PlusXfpEepromPage,
			ommp82PlusCheckCodeOfXfpEepromPage,
			ommp82PlusExtendedCheckCodeOfXfpEepromPage,
			ommp82PlusXfpVendorName,
			ommp82PlusXfpVendorIeeeId,
			ommp82PlusXfpPartNumber,
			ommp82PlusXfpSerialNumber,
			ommp82PlusXfpRevisionNumber,
			ommp82PlusXfpManufacturingDate,
			ommp82PlusFixedXfpLaserWavelength,
			ommp82PlusXfpLaserWavelengthTolerance,
			ommp82PlusXfpWavelengthTunabilitySupported,
			ommp82PlusTunableXfpLaserWavelengthError,
			ommp82PlusTunableXfpLaserFrequencyError,
			ommp82PlusTunableXfpLaserFirstFrequency,
			ommp82PlusTunableXfpLaserLastFrequency,
			ommp82PlusTunableXfpWavelengthGridSpacing,
			ommp82PlusXfpConnectorType,
			ommp82PlusXfpLinkLength,
			ommp82PlusXfpCdrRateSupported,
			ommp82PlusXfpSignalEncodingTypeSupported,
			ommp82PlusXfpTransceiverCodesSupported,
			ommp82PlusXfpMaximumBitrateSupported,
			ommp82PlusXfpMinimumBitrateSupported,
			ommp82PlusXfpMaximumCaseTemperatureSupported,
			ommp82PlusXfpMaximumPowerDissipationSupported,
			ommp82PlusXfpMaximumPowerDissipationSupportedAtPowerDownMode,
			ommp82PlusXfpMaximumCurrentLimitSupportedAtPlus5vSupply,
			ommp82PlusXfpMaximumCurrentLimitSupportedAtPlus3Point3vSupply,
			ommp82PlusXfpMaximumCurrentLimitSupportedAtPlus1Point8vSupply,
			ommp82PlusXfpMaximumCurrentLimitSupportedAtMinus5Point2vSupply,
			ommp82PlusXfpLineLoopbackSupported,
			ommp82PlusXfpXfiLoopbackSupported,
			ommp82PlusXfpOptionalVpsSupported,
			ommp82PlusXfpLaserDisableThroughI2cSupported,
			ommp82PlusXfpPowerDownThroughI2cSupported,
			ommp82PlusXfpVpsLvRegulatorModeSupported,
			ommp82PlusXfpVpsBypassedRegulatorModeSupported,
			ommp82PlusXfpActiveFecControlSupported,
			ommp82PlusXfpOptionalCmuModeSupported,
			ommp82PlusXfpFecBerSupported,
			ommp82PlusXfpReceivePowerMeasurementIsInOmaOrAverage,
			ommp82PlusXfpActiveWavelengthControlSupported,
			ommp82PlusXfpTransmitterIsCooledOrUncooled,
			ommp82PlusXfpReceiverTypeIsPinOrApd,
			ommp82PlusSfpEepromPage,
			ommp82PlusCheckCodeOfSfpEepromPage,
			ommp82PlusExtendedCheckCodeOfSfpEepromPage,
			ommp82PlusSfpVendorName,
			ommp82PlusSfpVendorIeeeId,
			ommp82PlusSfpPartNumber,
			ommp82PlusSfpSerialNumber,
			ommp82PlusSfpRevisionNumber,
			ommp82PlusSfpManufacturingDate,
			ommp82PlusFixedSfpLaserWavelength,
			ommp82PlusSfpConnectorType,
			ommp82PlusSfpLinkLength,
			ommp82PlusSfpSignalEncodingTypeSupported,
			ommp82PlusSfpTransceiverCodesSupported,
			ommp82PlusSfpMaximumBitrateSupported,
			ommp82PlusSfpNominalBitrateSupported,
			ommp82PlusSfpMinimumBitrateSupported,
			ommp82PlusCardGeneralDetailsTableRowStatus,
			ommp82PlusCardSoftwareUpgrade,
			ommp82PlusCardSignalMonitorState,
			ommp82PlusCardOpticalMonitorState,
			ommp82PlusCardSoftReset,
			ommp82PlusCardFactoryReset,
			ommp82PlusCardAccessStatus,
			ommp82PlusSyncSystemTimeWithNtpServer,
			ommp82PlusSyncRtcWithNtpServer,
			ommp82PlusSyncRtcWithSystemTime,
			ommp82PlusUpdateGivenTimeIntoSystem,
			ommp82PlusUpdateGivenTimeIntoRtc,
			ommp82PlusSystemTimeAndRtcTime,
			ommp82PlusApsLinePathSwitchingMode,
			ommp82PlusApsUserChoiceOfLinePath,
			ommp82PlusApsCurrentOperationalLinePath,
			ommp82PlusTrafficConfiguration,
			ommp82PlusLoopbackState,
			ommp82PlusPortSignalMonitorState,
			ommp82PlusPortOpticalMonitorState,
			ommp82PlusClearSignalPerformance,
			ommp82PlusAlsState,
			ommp82PlusAlsPulseRepetitionTime,
			ommp82PlusOtuFecConfiguration,
			ommp82PlusOtuSignalFailThreshold,
			ommp82PlusOtuSignalDegradeThreshold,
			ommp82PlusOtuAlarmIndicationSignalAlarmInsertion,
			ommp82PlusOtuSapiTransmitTraceMessage,
			ommp82PlusOtuDapiTransmitTraceMessage,
			ommp82PlusOtuOperatorSpecificTransmitTraceMessage,
			ommp82PlusOtuSapiExpectedTraceMessage,
			ommp82PlusOtuDapiExpectedTraceMessage,
			ommp82PlusOtuOperatorSpecificExpectedTraceMessage,
			ommp82PlusOtuSapiReceivedTraceMessage,
			ommp82PlusOtuDapiReceivedTraceMessage,
			ommp82PlusOtuOperatorSpecificReceivedTraceMessage,
			ommp82PlusOduSignalFailThreshold,
			ommp82PlusOduSignalDegradeThreshold,
			ommp82PlusOduAlarmIndicationSignalAlarmInsertion,
			ommp82PlusOduLockedDefectAlarmInsertion,
			ommp82PlusOduOpenConnectionIndicationAlarmInsertion,
			ommp82PlusOduSapiTransmitTraceMessage,
			ommp82PlusOduDapiTransmitTraceMessage,
			ommp82PlusOduOperatorSpecificTransmitTraceMessage,
			ommp82PlusOduSapiExpectedTraceMessage,
			ommp82PlusOduDapiExpectedTraceMessage,
			ommp82PlusOduOperatorSpecificExpectedTraceMessage,
			ommp82PlusOduSapiReceivedTraceMessage,
			ommp82PlusOduDapiReceivedTraceMessage,
			ommp82PlusOduOperatorSpecificReceivedTraceMessage,
			ommp82PlusOpuTransmitPayloadType,
			ommp82PlusOpuReceivedPayloadType,
			ommp82PlusSdhMsB2ExcessiveErrorThreshold,
			ommp82PlusSdhMsB2SignalDegradeThreshold,
			ommp82PlusEthernetAutoNegotiation,
			ommp82PlusCalibrateHyphyXfiSerdes,
			ommp82PlusTunableXfpLaserWavelength,
			ommp82PlusTunableXfpLaserChannelNumber,
			ommp82PlusXfpLaserState,
			ommp82PlusXfpReset,
			ommp82PlusXfpPowerDownMode,
			ommp82PlusXfpLineLoopback,
			ommp82PlusXfpXfiLoopback,
			ommp82PlusXfpAmplitudeThresholdOfReceiverForFecControl,
			ommp82PlusXfpPhaseInEyeDiagramForFecControl,
			ommp82PlusXfpSystemReportingBer,
			ommp82PlusXfpHighTemperatureAlarmThreshold,
			ommp82PlusXfpLowTemperatureAlarmThreshold,
			ommp82PlusXfpHighTemperatureWarningThreshold,
			ommp82PlusXfpLowTemperatureWarningThreshold,
			ommp82PlusXfpHighBiasCurrentAlarmThreshold,
			ommp82PlusXfpLowBiasCurrentAlarmThreshold,
			ommp82PlusXfpHighBiasCurrentWarningThreshold,
			ommp82PlusXfpLowBiasCurrentWarningThreshold,
			ommp82PlusXfpInputHighPowerAlarmThreshold,
			ommp82PlusXfpInputLowPowerAlarmThreshold,
			ommp82PlusXfpInputHighPowerWarningThreshold,
			ommp82PlusXfpInputLowPowerWarningThreshold,
			ommp82PlusXfpOutputHighPowerAlarmThreshold,
			ommp82PlusXfpOutputLowPowerAlarmThreshold,
			ommp82PlusXfpOutputHighPowerWarningThreshold,
			ommp82PlusXfpOutputLowPowerWarningThreshold,
			ommp82PlusXfpHighSupplyVoltageAlarmThreshold,
			ommp82PlusXfpLowSupplyVoltageAlarmThreshold,
			ommp82PlusXfpHighSupplyVoltageWarningThreshold,
			ommp82PlusXfpLowSupplyVoltageWarningThreshold,
			ommp82PlusSfpLaserState,
			ommp82PlusSfpHighTemperatureAlarmThreshold,
			ommp82PlusSfpLowTemperatureAlarmThreshold,
			ommp82PlusSfpHighTemperatureWarningThreshold,
			ommp82PlusSfpLowTemperatureWarningThreshold,
			ommp82PlusSfpHighBiasCurrentAlarmThreshold,
			ommp82PlusSfpLowBiasCurrentAlarmThreshold,
			ommp82PlusSfpHighBiasCurrentWarningThreshold,
			ommp82PlusSfpLowBiasCurrentWarningThreshold,
			ommp82PlusSfpInputHighPowerAlarmThreshold,
			ommp82PlusSfpInputLowPowerAlarmThreshold,
			ommp82PlusSfpInputHighPowerWarningThreshold,
			ommp82PlusSfpInputLowPowerWarningThreshold,
			ommp82PlusSfpOutputHighPowerAlarmThreshold,
			ommp82PlusSfpOutputLowPowerAlarmThreshold,
			ommp82PlusSfpOutputHighPowerWarningThreshold,
			ommp82PlusSfpOutputLowPowerWarningThreshold,
			ommp82PlusSfpHighSupplyVoltageAlarmThreshold,
			ommp82PlusSfpLowSupplyVoltageAlarmThreshold,
			ommp82PlusSfpHighSupplyVoltageWarningThreshold,
			ommp82PlusSfpLowSupplyVoltageWarningThreshold,
			ommp82PlusXfpInputPowerFailureAlarmInhibit,
			ommp82PlusXfpOutputPowerFailureAlarmInhibit,
			ommp82PlusXfpHighTemperatureAlarmInhibit,
			ommp82PlusXfpLowTemperatureAlarmInhibit,
			ommp82PlusXfpHighTemperatureWarningInhibit,
			ommp82PlusXfpLowTemperatureWarningInhibit,
			ommp82PlusXfpHighBiasCurrentAlarmInhibit,
			ommp82PlusXfpLowBiasCurrentAlarmInhibit,
			ommp82PlusXfpHighBiasCurrentWarningInhibit,
			ommp82PlusXfpLowBiasCurrentWarningInhibit,
			ommp82PlusXfpInputHighPowerAlarmInhibit,
			ommp82PlusXfpInputLowPowerAlarmInhibit,
			ommp82PlusXfpInputHighPowerWarningInhibit,
			ommp82PlusXfpInputLowPowerWarningInhibit,
			ommp82PlusXfpOutputHighPowerAlarmInhibit,
			ommp82PlusXfpOutputLowPowerAlarmInhibit,
			ommp82PlusXfpOutputHighPowerWarningInhibit,
			ommp82PlusXfpOutputLowPowerWarningInhibit,
			ommp82PlusXfpHighSupplyVoltageAlarmInhibit,
			ommp82PlusXfpLowSupplyVoltageAlarmInhibit,
			ommp82PlusXfpHighSupplyVoltageWarningInhibit,
			ommp82PlusXfpLowSupplyVoltageWarningInhibit,
			ommp82PlusXfpPresenceAbsenceNotificationInhibit,
			ommp82PlusSfpInputPowerFailureAlarmInhibit,
			ommp82PlusSfpOutputPowerFailureAlarmInhibit,
			ommp82PlusSfpHighTemperatureAlarmInhibit,
			ommp82PlusSfpLowTemperatureAlarmInhibit,
			ommp82PlusSfpHighTemperatureWarningInhibit,
			ommp82PlusSfpLowTemperatureWarningInhibit,
			ommp82PlusSfpHighBiasCurrentAlarmInhibit,
			ommp82PlusSfpLowBiasCurrentAlarmInhibit,
			ommp82PlusSfpHighBiasCurrentWarningInhibit,
			ommp82PlusSfpLowBiasCurrentWarningInhibit,
			ommp82PlusSfpInputHighPowerAlarmInhibit,
			ommp82PlusSfpInputLowPowerAlarmInhibit,
			ommp82PlusSfpInputHighPowerWarningInhibit,
			ommp82PlusSfpInputLowPowerWarningInhibit,
			ommp82PlusSfpOutputHighPowerAlarmInhibit,
			ommp82PlusSfpOutputLowPowerAlarmInhibit,
			ommp82PlusSfpOutputHighPowerWarningInhibit,
			ommp82PlusSfpOutputLowPowerWarningInhibit,
			ommp82PlusSfpHighSupplyVoltageAlarmInhibit,
			ommp82PlusSfpLowSupplyVoltageAlarmInhibit,
			ommp82PlusSfpHighSupplyVoltageWarningInhibit,
			ommp82PlusSfpLowSupplyVoltageWarningInhibit,
			ommp82PlusSfpPresenceAbsenceNotificationInhibit,
			ommp82PlusSfpTransmitFaultPresenceAlarmInhibit,
			ommp82PlusOtuLossOfSignalAlarmInhibit,
			ommp82PlusOtuLossOfFrameAlarmInhibit,
			ommp82PlusOtuOutOfFrameAlarmInhibit,
			ommp82PlusOtuLossOfMultiFrameAlarmInhibit,
			ommp82PlusOtuOutOfMultiFrameAlarmInhibit,
			ommp82PlusOtuSignalFailAlarmInhibit,
			ommp82PlusOtuSignalDegradeAlarmInhibit,
			ommp82PlusOtuAlarmIndicationSignalAlarmInhibit,
			ommp82PlusOtuIncomingAlignmentErrorAlarmInhibit,
			ommp82PlusOtuTraceIdentifierMismatchAlarmInhibit,
			ommp82PlusOtuBackwardIncomingAlignmentErrorAlarmInhibit,
			ommp82PlusOtuBackwardDefectIndicationAlarmInhibit,
			ommp82PlusOduSignalFailAlarmInhibit,
			ommp82PlusOduSignalDegradeAlarmInhibit,
			ommp82PlusOduAlarmIndicationSignalAlarmInhibit,
			ommp82PlusOduTcm1IncomingAlignmentErrorAlarmInhibit,
			ommp82PlusOduTcm2IncomingAlignmentErrorAlarmInhibit,
			ommp82PlusOduTcm3IncomingAlignmentErrorAlarmInhibit,
			ommp82PlusOduTcm4IncomingAlignmentErrorAlarmInhibit,
			ommp82PlusOduTcm5IncomingAlignmentErrorAlarmInhibit,
			ommp82PlusOduTcm6IncomingAlignmentErrorAlarmInhibit,
			ommp82PlusOduTraceIdentifierMismatchAlarmInhibit,
			ommp82PlusOduLockedDefectAlarmInhibit,
			ommp82PlusOduOpenConnectionIndicationAlarmInhibit,
			ommp82PlusOduBackwardDefectIndicationAlarmInhibit,
			ommp82PlusOduTcm1BackwardIncomingAlignmentErrorAlarmInhibit,
			ommp82PlusOduTcm2BackwardIncomingAlignmentErrorAlarmInhibit,
			ommp82PlusOduTcm3BackwardIncomingAlignmentErrorAlarmInhibit,
			ommp82PlusOduTcm4BackwardIncomingAlignmentErrorAlarmInhibit,
			ommp82PlusOduTcm5BackwardIncomingAlignmentErrorAlarmInhibit,
			ommp82PlusOduTcm6BackwardIncomingAlignmentErrorAlarmInhibit,
			ommp82PlusOduLossOfFrameLossOfMultiframeAlarmInhibit,
			ommp82PlusOpuPayloadMismatchAlarmInhibit,
			ommp82PlusOchLossOfPayloadAlarmInhibit,
			ommp82PlusSdhLossOfSignalAlarmInhibit,
			ommp82PlusSdhOutOfFrameAlarmInhibit,
			ommp82PlusSdhLossOfFrameAlarmInhibit,
			ommp82PlusSdhRsAlarmIndicationSignalAlarmInhibit,
			ommp82PlusSdhRsTraceIdentifierMismatchAlarmInhibit,
			ommp82PlusSdhAuAlarmIndicationSignalAlarmInhibit,
			ommp82PlusSdhAuLossOfPointerAlarmInhibit,
			ommp82PlusSdhMsAlarmIndicationSignalAlarmInhibit,
			ommp82PlusSdhMsRemoteErrorIndicationAlarmInhibit,
			ommp82PlusSdhMsRemoteDefectIndicationAlarmInhibit,
			ommp82PlusSdhMsRemoteFailureIndicationAlarmInhibit,
			ommp82PlusSdhMsB2ExcessiveErrorAlarmInhibit,
			ommp82PlusSdhMsB2SignalDegradeAlarmInhibit,
			ommp82PlusSdhLossOfSequenceSynchronisationAlarmInhibit,
			ommp82PlusSdhLowerOrderPathPayloadLabelMismatchAlarmInhibit,
			ommp82PlusSdhLowerOrderPathUnequippedAlarmInhibit,
			ommp82PlusEthernetLossOfSignalAlarmInhibit,
			ommp82PlusEthernetLossOfSignalSyncAlarmInhibit,
			ommp82PlusEthernetLinkFailureAlarmInhibit,
			ommp82PlusEthernetAutoNegotiationAlarmInhibit,
			ommp82PlusEthernetFrameCheckSequenceAlarmInhibit,
			ommp82PlusEthernetCarrierStatusAlarmInhibit,
			ommp82PlusEthernetHighBerAlarmInhibit,
			ommp82PlusEthernetLocalFaultAlarmInhibit,
			ommp82PlusEthernetRemoteFaultAlarmInhibit,
			ommp82PlusFcTransmitDisparityInversionDefectAlarmInhibit,
			ommp82PlusFcTransmitDigitalLossOfLinkDefectAlarmInhibit,
			ommp82PlusFcTrasnmitLossOfSynchronizationDefectAlarmInhibit,
			ommp82PlusFcReceiveDigitalLossOfLinkDefectAlarmInhibit,
			ommp82PlusFcReceiveLossOfSynchronizationDefectAlarmInhibit,
			ommp82PlusFcReceiveTransitionDetectDefectAlarmInhibit,
			ommp82PlusFcReceiveAnalogLossOfSignalDefectAlarmInhibit,
			ommp82PlusFcReceiveLineCodeViolationDefectAlarmInhibit,
			ommp82PlusGfpCsfSignalFailAlarmInhibit,
			ommp82PlusGfpCsfLinkFailAlarmInhibit,
			ommp82PlusGfpCoreHeaderErrorAlarmInhibit,
			ommp82PlusGfpExtentionHeaderErrorAlarmInhibit,
			ommp82PlusXfpInputPowerFailureAlarmSeverity,
			ommp82PlusXfpOutputPowerFailureAlarmSeverity,
			ommp82PlusXfpHighTemperatureAlarmSeverity,
			ommp82PlusXfpLowTemperatureAlarmSeverity,
			ommp82PlusXfpHighTemperatureWarningSeverity,
			ommp82PlusXfpLowTemperatureWarningSeverity,
			ommp82PlusXfpHighBiasCurrentAlarmSeverity,
			ommp82PlusXfpLowBiasCurrentAlarmSeverity,
			ommp82PlusXfpHighBiasCurrentWarningSeverity,
			ommp82PlusXfpLowBiasCurrentWarningSeverity,
			ommp82PlusXfpInputHighPowerAlarmSeverity,
			ommp82PlusXfpInputLowPowerAlarmSeverity,
			ommp82PlusXfpInputHighPowerWarningSeverity,
			ommp82PlusXfpInputLowPowerWarningSeverity,
			ommp82PlusXfpOutputHighPowerAlarmSeverity,
			ommp82PlusXfpOutputLowPowerAlarmSeverity,
			ommp82PlusXfpOutputHighPowerWarningSeverity,
			ommp82PlusXfpOutputLowPowerWarningSeverity,
			ommp82PlusXfpHighSupplyVoltageAlarmSeverity,
			ommp82PlusXfpLowSupplyVoltageAlarmSeverity,
			ommp82PlusXfpHighSupplyVoltageWarningSeverity,
			ommp82PlusXfpLowSupplyVoltageWarningSeverity,
			ommp82PlusXfpPresenceAbsenceNotificationSeverity,
			ommp82PlusSfpInputPowerFailureAlarmSeverity,
			ommp82PlusSfpOutputPowerFailureAlarmSeverity,
			ommp82PlusSfpHighTemperatureAlarmSeverity,
			ommp82PlusSfpLowTemperatureAlarmSeverity,
			ommp82PlusSfpHighTemperatureWarningSeverity,
			ommp82PlusSfpLowTemperatureWarningSeverity,
			ommp82PlusSfpHighBiasCurrentAlarmSeverity,
			ommp82PlusSfpLowBiasCurrentAlarmSeverity,
			ommp82PlusSfpHighBiasCurrentWarningSeverity,
			ommp82PlusSfpLowBiasCurrentWarningSeverity,
			ommp82PlusSfpInputHighPowerAlarmSeverity,
			ommp82PlusSfpInputLowPowerAlarmSeverity,
			ommp82PlusSfpInputHighPowerWarningSeverity,
			ommp82PlusSfpInputLowPowerWarningSeverity,
			ommp82PlusSfpOutputHighPowerAlarmSeverity,
			ommp82PlusSfpOutputLowPowerAlarmSeverity,
			ommp82PlusSfpOutputHighPowerWarningSeverity,
			ommp82PlusSfpOutputLowPowerWarningSeverity,
			ommp82PlusSfpHighSupplyVoltageAlarmSeverity,
			ommp82PlusSfpLowSupplyVoltageAlarmSeverity,
			ommp82PlusSfpHighSupplyVoltageWarningSeverity,
			ommp82PlusSfpLowSupplyVoltageWarningSeverity,
			ommp82PlusSfpPresenceAbsenceNotificationSeverity,
			ommp82PlusSfpTransmitFaultPresenceAlarmSeverity,
			ommp82PlusOtuLossOfSignalAlarmSeverity,
			ommp82PlusOtuLossOfFrameAlarmSeverity,
			ommp82PlusOtuOutOfFrameAlarmSeverity,
			ommp82PlusOtuLossOfMultiFrameAlarmSeverity,
			ommp82PlusOtuOutOfMultiFrameAlarmSeverity,
			ommp82PlusOtuSignalFailAlarmSeverity,
			ommp82PlusOtuSignalDegradeAlarmSeverity,
			ommp82PlusOtuAlarmIndicationSignalAlarmSeverity,
			ommp82PlusOtuIncomingAlignmentErrorAlarmSeverity,
			ommp82PlusOtuTraceIdentifierMismatchAlarmSeverity,
			ommp82PlusOtuBackwardIncomingAlignmentErrorAlarmSeverity,
			ommp82PlusOtuBackwardDefectIndicationAlarmSeverity,
			ommp82PlusOduSignalFailAlarmSeverity,
			ommp82PlusOduSignalDegradeAlarmSeverity,
			ommp82PlusOduAlarmIndicationSignalAlarmSeverity,
			ommp82PlusOduTcm1IncomingAlignmentErrorAlarmSeverity,
			ommp82PlusOduTcm2IncomingAlignmentErrorAlarmSeverity,
			ommp82PlusOduTcm3IncomingAlignmentErrorAlarmSeverity,
			ommp82PlusOduTcm4IncomingAlignmentErrorAlarmSeverity,
			ommp82PlusOduTcm5IncomingAlignmentErrorAlarmSeverity,
			ommp82PlusOduTcm6IncomingAlignmentErrorAlarmSeverity,
			ommp82PlusOduTraceIdentifierMismatchAlarmSeverity,
			ommp82PlusOduLockedDefectAlarmSeverity,
			ommp82PlusOduOpenConnectionIndicationAlarmSeverity,
			ommp82PlusOduBackwardDefectIndicationAlarmSeverity,
			ommp82PlusOduTcm1BackwardIncomingAlignmentErrorAlarmSeverity,
			ommp82PlusOduTcm2BackwardIncomingAlignmentErrorAlarmSeverity,
			ommp82PlusOduTcm3BackwardIncomingAlignmentErrorAlarmSeverity,
			ommp82PlusOduTcm4BackwardIncomingAlignmentErrorAlarmSeverity,
			ommp82PlusOduTcm5BackwardIncomingAlignmentErrorAlarmSeverity,
			ommp82PlusOduTcm6BackwardIncomingAlignmentErrorAlarmSeverity,
			ommp82PlusOduLossOfFrameLossOfMultiframeAlarmSeverity,
			ommp82PlusOpuPayloadMismatchAlarmSeverity,
			ommp82PlusOchLossOfPayloadAlarmSeverity,
			ommp82PlusSdhLossOfSignalAlarmSeverity,
			ommp82PlusSdhOutOfFrameAlarmSeverity,
			ommp82PlusSdhLossOfFrameAlarmSeverity,
			ommp82PlusSdhRsAlarmIndicationSignalAlarmSeverity,
			ommp82PlusSdhRsTraceIdentifierMismatchAlarmSeverity,
			ommp82PlusSdhAuAlarmIndicationSignalAlarmSeverity,
			ommp82PlusSdhAuLossOfPointerAlarmSeverity,
			ommp82PlusSdhMsAlarmIndicationSignalAlarmSeverity,
			ommp82PlusSdhMsRemoteErrorIndicationAlarmSeverity,
			ommp82PlusSdhMsRemoteDefectIndicationAlarmSeverity,
			ommp82PlusSdhMsRemoteFailureIndicationAlarmSeverity,
			ommp82PlusSdhMsB2ExcessiveErrorAlarmSeverity,
			ommp82PlusSdhMsB2SignalDegradeAlarmSeverity,
			ommp82PlusSdhLossOfSequenceSynchronisationAlarmSeverity,
			ommp82PlusSdhLowerOrderPathPayloadLabelMismatchAlarmSeverity,
			ommp82PlusSdhLowerOrderPathUnequippedAlarmSeverity,
			ommp82PlusEthernetLossOfSignalAlarmSeverity,
			ommp82PlusEthernetLossOfSignalSyncAlarmSeverity,
			ommp82PlusEthernetLinkFailureAlarmSeverity,
			ommp82PlusEthernetAutoNegotiationAlarmSeverity,
			ommp82PlusEthernetFrameCheckSequenceAlarmSeverity,
			ommp82PlusEthernetCarrierStatusAlarmSeverity,
			ommp82PlusEthernetHighBerAlarmSeverity,
			ommp82PlusEthernetLocalFaultAlarmSeverity,
			ommp82PlusEthernetRemoteFaultAlarmSeverity,
			ommp82PlusFcTransmitDisparityInversionDefectAlarmSeverity,
			ommp82PlusFcTransmitDigitalLossOfLinkDefectAlarmSeverity,
			ommp82PlusFcTrasnmitLossOfSynchronizationDefectAlarmSeverity,
			ommp82PlusFcReceiveDigitalLossOfLinkDefectAlarmSeverity,
			ommp82PlusFcReceiveLossOfSynchronizationDefectAlarmSeverity,
			ommp82PlusFcReceiveTransitionDetectDefectAlarmSeverity,
			ommp82PlusFcReceiveAnalogLossOfSignalDefectAlarmSeverity,
			ommp82PlusFcReceiveLineCodeViolationDefectAlarmSeverity,
			ommp82PlusGfpCsfSignalFailAlarmSeverity,
			ommp82PlusGfpCsfLinkFailAlarmSeverity,
			ommp82PlusGfpCoreHeaderErrorAlarmSeverity,
			ommp82PlusGfpExtentionHeaderErrorAlarmSeverity,
			ommp82PlusConfigurationTableRowStatus,
			ommp82PlusXfpInputPowerFailureAlarm,
			ommp82PlusXfpOutputPowerFailureAlarm,
			ommp82PlusXfpHighTemperatureAlarm,
			ommp82PlusXfpLowTemperatureAlarm,
			ommp82PlusXfpHighTemperatureWarning,
			ommp82PlusXfpLowTemperatureWarning,
			ommp82PlusXfpHighBiasCurrentAlarm,
			ommp82PlusXfpLowBiasCurrentAlarm,
			ommp82PlusXfpHighBiasCurrentWarning,
			ommp82PlusXfpLowBiasCurrentWarning,
			ommp82PlusXfpInputHighPowerAlarm,
			ommp82PlusXfpInputLowPowerAlarm,
			ommp82PlusXfpInputHighPowerWarning,
			ommp82PlusXfpInputLowPowerWarning,
			ommp82PlusXfpOutputHighPowerAlarm,
			ommp82PlusXfpOutputLowPowerAlarm,
			ommp82PlusXfpOutputHighPowerWarning,
			ommp82PlusXfpOutputLowPowerWarning,
			ommp82PlusXfpHighSupplyVoltageAlarm,
			ommp82PlusXfpLowSupplyVoltageAlarm,
			ommp82PlusXfpHighSupplyVoltageWarning,
			ommp82PlusXfpLowSupplyVoltageWarning,
			ommp82PlusXfpPresenceAbsenceNotification,
			ommp82PlusSfpInputPowerFailureAlarm,
			ommp82PlusSfpOutputPowerFailureAlarm,
			ommp82PlusSfpHighTemperatureAlarm,
			ommp82PlusSfpLowTemperatureAlarm,
			ommp82PlusSfpHighTemperatureWarning,
			ommp82PlusSfpLowTemperatureWarning,
			ommp82PlusSfpHighBiasCurrentAlarm,
			ommp82PlusSfpLowBiasCurrentAlarm,
			ommp82PlusSfpHighBiasCurrentWarning,
			ommp82PlusSfpLowBiasCurrentWarning,
			ommp82PlusSfpInputHighPowerAlarm,
			ommp82PlusSfpInputLowPowerAlarm,
			ommp82PlusSfpInputHighPowerWarning,
			ommp82PlusSfpInputLowPowerWarning,
			ommp82PlusSfpOutputHighPowerAlarm,
			ommp82PlusSfpOutputLowPowerAlarm,
			ommp82PlusSfpOutputHighPowerWarning,
			ommp82PlusSfpOutputLowPowerWarning,
			ommp82PlusSfpHighSupplyVoltageAlarm,
			ommp82PlusSfpLowSupplyVoltageAlarm,
			ommp82PlusSfpHighSupplyVoltageWarning,
			ommp82PlusSfpLowSupplyVoltageWarning,
			ommp82PlusSfpPresenceAbsenceNotification,
			ommp82PlusSfpTransmitFaultPresenceAlarm,
			ommp82PlusOtuLossOfSignalAlarm,
			ommp82PlusOtuLossOfFrameAlarm,
			ommp82PlusOtuOutOfFrameAlarm,
			ommp82PlusOtuLossOfMultiFrameAlarm,
			ommp82PlusOtuOutOfMultiFrameAlarm,
			ommp82PlusOtuSignalFailAlarm,
			ommp82PlusOtuSignalDegradeAlarm,
			ommp82PlusOtuAlarmIndicationSignalAlarm,
			ommp82PlusOtuIncomingAlignmentErrorAlarm,
			ommp82PlusOtuTraceIdentifierMismatchAlarm,
			ommp82PlusOtuBackwardIncomingAlignmentErrorAlarm,
			ommp82PlusOtuBackwardDefectIndicationAlarm,
			ommp82PlusOduSignalFailAlarm,
			ommp82PlusOduSignalDegradeAlarm,
			ommp82PlusOduAlarmIndicationSignalAlarm,
			ommp82PlusOduTcm1IncomingAlignmentErrorAlarm,
			ommp82PlusOduTcm2IncomingAlignmentErrorAlarm,
			ommp82PlusOduTcm3IncomingAlignmentErrorAlarm,
			ommp82PlusOduTcm4IncomingAlignmentErrorAlarm,
			ommp82PlusOduTcm5IncomingAlignmentErrorAlarm,
			ommp82PlusOduTcm6IncomingAlignmentErrorAlarm,
			ommp82PlusOduTraceIdentifierMismatchAlarm,
			ommp82PlusOduLockedDefectAlarm,
			ommp82PlusOduOpenConnectionIndicationAlarm,
			ommp82PlusOduBackwardDefectIndicationAlarm,
			ommp82PlusOduTcm1BackwardIncomingAlignmentErrorAlarm,
			ommp82PlusOduTcm2BackwardIncomingAlignmentErrorAlarm,
			ommp82PlusOduTcm3BackwardIncomingAlignmentErrorAlarm,
			ommp82PlusOduTcm4BackwardIncomingAlignmentErrorAlarm,
			ommp82PlusOduTcm5BackwardIncomingAlignmentErrorAlarm,
			ommp82PlusOduTcm6BackwardIncomingAlignmentErrorAlarm,
			ommp82PlusOduLossOfFrameLossOfMultiframeAlarm,
			ommp82PlusOpuPayloadMismatchAlarm,
			ommp82PlusOchLossOfPayloadAlarm,
			ommp82PlusSdhLossOfSignalAlarm,
			ommp82PlusSdhOutOfFrameAlarm,
			ommp82PlusSdhLossOfFrameAlarm,
			ommp82PlusSdhRsAlarmIndicationSignalAlarm,
			ommp82PlusSdhRsTraceIdentifierMismatchAlarm,
			ommp82PlusSdhAuAlarmIndicationSignalAlarm,
			ommp82PlusSdhAuLossOfPointerAlarm,
			ommp82PlusSdhMsAlarmIndicationSignalAlarm,
			ommp82PlusSdhMsRemoteErrorIndicationAlarm,
			ommp82PlusSdhMsRemoteDefectIndicationAlarm,
			ommp82PlusSdhMsRemoteFailureIndicationAlarm,
			ommp82PlusSdhMsB2ExcessiveErrorAlarm,
			ommp82PlusSdhMsB2SignalDegradeAlarm,
			ommp82PlusSdhLossOfSequenceSynchronisationAlarm,
			ommp82PlusSdhLowerOrderPathPayloadLabelMismatchAlarm,
			ommp82PlusSdhLowerOrderPathUnequippedAlarm,
			ommp82PlusEthernetLossOfSignalAlarm,
			ommp82PlusEthernetLossOfSignalSyncAlarm,
			ommp82PlusEthernetLinkFailureAlarm,
			ommp82PlusEthernetAutoNegotiationAlarm,
			ommp82PlusEthernetFrameCheckSequenceAlarm,
			ommp82PlusEthernetCarrierStatusAlarm,
			ommp82PlusEthernetHighBerAlarm,
			ommp82PlusEthernetLocalFaultAlarm,
			ommp82PlusEthernetRemoteFaultAlarm,
			ommp82PlusFcTransmitDisparityInversionDefectAlarm,
			ommp82PlusFcTransmitDigitalLossOfLinkDefectAlarm,
			ommp82PlusFcTrasnmitLossOfSynchronizationDefectAlarm,
			ommp82PlusFcReceiveDigitalLossOfLinkDefectAlarm,
			ommp82PlusFcReceiveLossOfSynchronizationDefectAlarm,
			ommp82PlusFcReceiveTransitionDetectDefectAlarm,
			ommp82PlusFcReceiveAnalogLossOfSignalDefectAlarm,
			ommp82PlusFcReceiveLineCodeViolationDefectAlarm,
			ommp82PlusGfpCsfSignalFailAlarm,
			ommp82PlusGfpCsfLinkFailAlarm,
			ommp82PlusGfpCoreHeaderErrorAlarm,
			ommp82PlusGfpExtentionHeaderErrorAlarm,
			ommp82PlusAlarmQueryTableRowStatus,
			ommp82PlusXfpInputPower,
			ommp82PlusXfpOutputPower,
			ommp82PlusXfpBiasCurrent,
			ommp82PlusXfpSupplyVoltage,
			ommp82PlusXfpTemperature,
			ommp82PlusSfpInputPower,
			ommp82PlusSfpOutputPower,
			ommp82PlusSfpBiasCurrent,
			ommp82PlusSfpSupplyVoltage,
			ommp82PlusSfpTemperature,
			ommp82PlusOtnFecUncorrectedWords,
			ommp82PlusOtnFecCorrectedBits,
			ommp82PlusOtnFecZerosCorrectedBits,
			ommp82PlusOtnFecOnesCorrectedBits,
			ommp82PlusOtuBitInterleavedParityErrors,
			ommp82PlusOtuIncomingAlignmentErrorSeconds,
			ommp82PlusOtuBackwardErrorIndicationErrorCount,
			ommp82PlusOtuBackwardIncomingAlignmentErrorSeconds,
			ommp82PlusOtuErrorFreeSeconds,
			ommp82PlusOtuErrorSeconds,
			ommp82PlusOtuBackgroundBlockErrors,
			ommp82PlusOtuSevereErrorSeconds,
			ommp82PlusOtuUnavailableSeconds,
			ommp82PlusOtuBackgroundBlockErrorRatio,
			ommp82PlusOtuSevereErrorSecondsErrorRatio,
			ommp82PlusOtuFarEndErrorFreeSeconds,
			ommp82PlusOtuFarEndErrorSeconds,
			ommp82PlusOtuFarEndBackgroundBlockErrors,
			ommp82PlusOtuFarEndSevereErrorSeconds,
			ommp82PlusOtuFarEndUnavailableSeconds,
			ommp82PlusOtuFarEndBackgroundBlockErrorRatio,
			ommp82PlusOtuFarEndSevereErrorSecondsErrorRatio,
			ommp82PlusOtuErrorRatio,
			ommp82PlusOtuBitErrorRate,
			ommp82PlusOtuFramesReceived,
			ommp82PlusOduBitInterleavedParityErrors,
			ommp82PlusOduTcm1BitInterleavedParityErrors,
			ommp82PlusOduTcm2BitInterleavedParityErrors,
			ommp82PlusOduTcm3BitInterleavedParityErrors,
			ommp82PlusOduTcm4BitInterleavedParityErrors,
			ommp82PlusOduTcm5BitInterleavedParityErrors,
			ommp82PlusOduTcm6BitInterleavedParityErrors,
			ommp82PlusOduTcm1IncomingAlignmentErrorSeconds,
			ommp82PlusOduBackwardErrorIndicationErrorCount,
			ommp82PlusOduTcm1BackwardErrorIndicationErrorCount,
			ommp82PlusOduTcm2BackwardErrorIndicationErrorCount,
			ommp82PlusOduTcm3BackwardErrorIndicationErrorCount,
			ommp82PlusOduTcm4BackwardErrorIndicationErrorCount,
			ommp82PlusOduTcm5BackwardErrorIndicationErrorCount,
			ommp82PlusOduTcm6BackwardErrorIndicationErrorCount,
			ommp82PlusOduTcm1BackwardIncomingAlignmentErrorSeconds,
			ommp82PlusOduDelayMeasurement,
			ommp82PlusOduErrorFreeSeconds,
			ommp82PlusOduErrorSeconds,
			ommp82PlusOduBackgroundBlockErrors,
			ommp82PlusOduSevereErrorSeconds,
			ommp82PlusOduUnavailableSeconds,
			ommp82PlusOduBackgroundBlockErrorRatio,
			ommp82PlusOduSevereErrorSecondsErrorRatio,
			ommp82PlusOduFarEndErrorFreeSeconds,
			ommp82PlusOduFarEndErrorSeconds,
			ommp82PlusOduFarEndBackgroundBlockErrors,
			ommp82PlusOduFarEndSevereErrorSeconds,
			ommp82PlusOduFarEndUnavailableSeconds,
			ommp82PlusOduFarEndBackgroundBlockErrorRatio,
			ommp82PlusOduFarEndSevereErrorSecondsErrorRatio,
			ommp82PlusSdhRsB1BitInterleavedParityErrors,
			ommp82PlusSdhMsB2BitInterleavedParityErrors,
			ommp82PlusSdhMsB3BitInterleavedParityErrors,
			ommp82PlusSdhMsRemoteErrorIndicationErrorCount,
			ommp82PlusSdhMsRemoteDefectIndicationErrorCount,
			ommp82PlusSdhErrorFreeSeconds,
			ommp82PlusSdhErrorSeconds,
			ommp82PlusSdhBackgroundBlockErrors,
			ommp82PlusSdhSevereErrorSeconds,
			ommp82PlusSdhUnavailableSeconds,
			ommp82PlusSdhErrorSecondsErrorRatio,
			ommp82PlusSdhBackgroundBlockErrorRatio,
			ommp82PlusSdhSevereErrorSecondsErrorRatio,
			ommp82PlusEthernetMacTerminatedFramesTransmitted,
			ommp82PlusEthernetMacTerminatedFramesReceived,
			ommp82PlusEthernetMacTerminatedPauseFramesTransmitted,
			ommp82PlusEthernetMacTerminatedPauseFramesReceived,
			ommp82PlusEthernetMacTerminatedUnicastFramesTransmitted,
			ommp82PlusEthernetMacTerminatedUnicastFramesReceived,
			ommp82PlusEthernetMacTerminatedMulticastFramesTransmitted,
			ommp82PlusEthernetMacTerminatedMulticastFramesReceived,
			ommp82PlusEthernetMacTerminatedBroadcastFramesTransmitted,
			ommp82PlusEthernetMacTerminatedBroadcastFramesReceived,
			ommp82PlusEthernetMacTerminatedUnderSizeFramesTransmitted,
			ommp82PlusEthernetMacTerminatedUnderSizeFramesReceived,
			ommp82PlusEthernetMacTerminatedOverSizeFramesTransmitted,
			ommp82PlusEthernetMacTerminatedOverSizeFramesReceived,
			ommp82PlusEthernetMacTerminatedVlanTaggedFramesTransmitted,
			ommp82PlusEthernetMacTerminatedVlanTaggedFramesReceived,
			ommp82PlusEthernetMacTerminatedFrameSymbolErrorsReceived,
			ommp82PlusEthernetMacTerminatedFragmentFramesReceived,
			ommp82PlusEthernetMacTerminatedFrameCheckSequenceErrorsReceived,
			ommp82PlusEthernetMacTerminatedFramesReceivedWithNoDefect,
			ommp82PlusEthernetMacTerminatedBytesTransmitted,
			ommp82PlusEthernetMacTerminatedBytesReceived,
			ommp82PlusEthernetMacTerminatedControlFramesTransmitted,
			ommp82PlusEthernetMacTerminatedControlFramesReceived,
			ommp82PlusEthernetTransparentTransmitLcvCount,
			ommp82PlusEthernetTransparentTransmitPropagationErrorDeletionCount,
			ommp82PlusEthernetTransparentTransmitIdleDeletionCount,
			ommp82PlusEthernetTransparentTransmitConfDeletionCount,
			ommp82PlusEthernetTransparentTransmitPropagationInsertionCount,
			ommp82PlusEthernetTransparentTransmitIdleInsertionCount,
			ommp82PlusEthernetTransparentTransmitConfInsertionCount,
			ommp82PlusEthernetTransparentReceiveLcvCount,
			ommp82PlusEthernetTransparentReceivePropagationErrorDeletionCount,
			ommp82PlusEthernetTransparentReceiveIdleDeletionCount,
			ommp82PlusEthernetTransparentReceiveConfDeletionCount,
			ommp82PlusEthernetTransparentReceivePacketDeletionCount,
			ommp82PlusGfpCoreHeaderErrorCount,
			ommp82PlusGfpExtentionHeaderErrorCount,
			ommp82PlusGfpFrameCountWithSingleBitError,
			ommp82PlusGfpTypeHeaderErrorCount,
			ommp82PlusGfpReceiveDropFrameCount,
			ommp82PlusGfpReceiveExtensionHeaderIdentifierFilterDropCount,
			ommp82PlusFcTransmitWordCount,
			ommp82PlusFcReceiveWordCount,
			ommp82PlusFcTransmitTotalPackets,
			ommp82PlusFcReceiveTotalPackets,
			ommp82PlusFcTransmitBadCrc,
			ommp82PlusFcReceiveBadCrc,
			ommp82PlusFcTransmitLcvCount,
			ommp82PlusFcReceiveLcvCount,
			ommp82PlusFcTransmitFillWordInsertionCount,
			ommp82PlusFcTransmitPrimitiveSequenceInsertionCount,
			ommp82PlusFcTransmitFillWordDeletionCount,
			ommp82PlusFcTransmitPrimitiveSequenceDeletionCount,
			ommp82PlusPerformanceTableRowStatus,
			ommp82PlusAccessHyphyRegister,
			ommp82PlusCnodeCrashCount,
			ommp82PlusKernelState,
			ommp82PlusDiagnosticTableRowStatus
		}
    STATUS  current
    DESCRIPTION
            "A collection of objects from RFC 1213 made current by this MIB module."
    ::= { utlrnd 2 }

	
END

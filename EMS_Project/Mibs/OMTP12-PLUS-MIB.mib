--*****************************************************************************
--			MIB FILE FOR THE OMTP12-PLUS CARD
--*****************************************************************************

	OMTP12-PLUS-MIB DEFINITIONS ::= BEGIN

	IMPORTS

	RowStatus                               FROM STANDARD-MIB
	DisplayString                           FROM RFC1213-MIB
	   
	OBJECT-IDENTITY, 
	NOTIFICATION-TYPE, 
	MODULE-IDENTITY, 
	Integer32, 
	Unsigned32,
	IpAddress,

	TimeTicks		                FROM SNMPv2-SMI
	OBJECT-TYPE                             FROM RFC-1212

	MODULE-COMPLIANCE, 
	OBJECT-GROUP, 
	NOTIFICATION-GROUP                      FROM SNMPv2-CONF

	node, 
	rack, 
	subRack, 
	slot                                    FROM SCC-MIB 

	enterprises                             FROM RFC1155-SMI		

	;

	utl   MODULE-IDENTITY
		LAST-UPDATED    	"1807130630Z"
		ORGANIZATION    	"United Telecoms Limited, Bangalore-560048."
		CONTACT-INFO    	"Website: http://www.utlindia.com."                                           
		DESCRIPTION     	"MIB module for NFS."
		REVISION 	    	"1807130630Z"
		DESCRIPTION    	    	"MIB module for OMTP12-PLUS Card."
		::= { enterprises 18036 }

	utlrnd  OBJECT-IDENTITY
		STATUS  current
		DESCRIPTION "UTL Research and Development."
		::= { utl 1 }

	dwdm OBJECT IDENTIFIER				::=	{ utlrnd 1 }
	indus OBJECT IDENTIFIER				::=	{ dwdm 1 }
	omtp12Plus OBJECT IDENTIFIER 			::=	{ indus 73 }

	omtp12PlusCardGeneralDetails OBJECT IDENTIFIER	::=	{ omtp12Plus 1 }
	omtp12PlusConfiguration OBJECT IDENTIFIER	::=	{ omtp12Plus 2 }
	omtp12PlusAlarm OBJECT IDENTIFIER		::=	{ omtp12Plus 3 }
	omtp12PlusPerformance OBJECT IDENTIFIER		::=	{ omtp12Plus 4 }
	omtp12PlusDiagnostics OBJECT IDENTIFIER 	::=	{ omtp12Plus 5 }
	
	omtp12PlusAlarmQuery OBJECT IDENTIFIER		::=	{ omtp12PlusAlarm 1 }
	omtp12PlusAlarmNotification OBJECT IDENTIFIER	::=	{ omtp12PlusAlarm 2 }

--*****************************************************************************
--				   CARD GENERAL DETAILS
--*****************************************************************************

	omtp12PlusCardGeneralDetailsTable OBJECT-TYPE
		SYNTAX SEQUENCE OF Omtp12PlusCardGeneralDetailsEntry
		MAX-ACCESS not-accessible
		STATUS current
		DESCRIPTION
			"Contains card general details' queries for the OMTP12-PLUS card"
		::= { omtp12PlusCardGeneralDetails 1 }

	omtp12PlusCardGeneralDetailsEntry OBJECT-TYPE
		SYNTAX Omtp12PlusCardGeneralDetailsEntry
		MAX-ACCESS not-accessible
		STATUS current
		DESCRIPTION
			""				  	
		INDEX   { node, rack , subRack , slot , omtp12PlusInterfaceNumber}
		::= { omtp12PlusCardGeneralDetailsTable 1 }

	Omtp12PlusCardGeneralDetailsEntry ::= 
		SEQUENCE { 
				omtp12PlusInterfaceNumber					INTEGER,
				omtp12PlusEepromCardId					        INTEGER,
				omtp12PlusEepromCardName					DisplayString,
				omtp12PlusEepromPartCode					DisplayString,
				omtp12PlusEepromCardSerialNumber				DisplayString,
				omtp12PlusEepromHardwareExternalReleaseVersion		        DisplayString,
				omtp12PlusSoftwareExternalReleaseVersion		        DisplayString,
				omtp12PlusEepromHardwareInternalReleaseVersion		        DisplayString,
				omtp12PlusSoftwareInternalReleaseVersion		        DisplayString,
				omtp12PlusEepromCardUidNumber			                DisplayString,
				omtp12PlusEepromCardEui48Number				        DisplayString,
				omtp12PlusEepromCardEui64Number				        DisplayString,
				omtp12PlusCardRootFileSystemVersion				DisplayString,
				omtp12PlusCardInstallationDate				        DisplayString,
				omtp12PlusCardCommissionDate				        DisplayString,
				omtp12PlusCardRunningTime					DisplayString,
				omtp12PlusCardRestartCount					INTEGER,
				omtp12PlusXfpReadyForOperation				        INTEGER,
				omtp12PlusXfpI2cCommunicationStatus				INTEGER,
				omtp12PlusXfpEepromPage					        INTEGER,
				omtp12PlusCheckCodeOfXfpEepromPage				INTEGER,
				omtp12PlusExtendedCheckCodeOfXfpEepromPage			INTEGER,
				omtp12PlusXfpVendorName					        DisplayString,
				omtp12PlusXfpVendorIeeeId					DisplayString,
				omtp12PlusXfpPartNumber					        DisplayString,
				omtp12PlusXfpSerialNumber					DisplayString,
				omtp12PlusXfpRevisionNumber					DisplayString,
				omtp12PlusXfpManufacturingDate				        DisplayString,
				omtp12PlusFixedXfpLaserWavelength				DisplayString,
				omtp12PlusXfpLaserWavelengthTolerance				DisplayString,
				omtp12PlusXfpWavelengthTunabilitySupported			INTEGER,
				omtp12PlusTunableXfpLaserWavelengthError			DisplayString,
				omtp12PlusTunableXfpLaserFrequencyError			        DisplayString,
				omtp12PlusTunableXfpLaserFirstFrequency			        DisplayString,
				omtp12PlusTunableXfpLaserLastFrequency			        DisplayString,
				omtp12PlusTunableXfpWavelengthGridSpacing			DisplayString,
				omtp12PlusXfpConnectorType					DisplayString,
				omtp12PlusXfpLinkLength					        DisplayString,
				omtp12PlusXfpCdrRateSupported				        INTEGER,
				omtp12PlusXfpSignalEncodingTypeSupported			INTEGER,
				omtp12PlusXfpTransceiverCodesSupported			        INTEGER,
				omtp12PlusXfpMaximumBitrateSupported			        DisplayString,
				omtp12PlusXfpMinimumBitrateSupported			        DisplayString,
				omtp12PlusXfpMaximumCaseTemperatureSupported		        INTEGER,
				omtp12PlusXfpMaximumPowerDissipationSupported			INTEGER,
				omtp12PlusXfpMaximumPowerDissipationSupportedAtPowerDownMode	INTEGER,
				omtp12PlusXfpMaximumCurrentLimitSupportedAtPlus5vSupply		INTEGER,
				omtp12PlusXfpMaximumCurrentLimitSupportedAtPlus3Point3vSupply	INTEGER,
				omtp12PlusXfpMaximumCurrentLimitSupportedAtPlus1Point8vSupply	INTEGER,
				omtp12PlusXfpMaximumCurrentLimitSupportedAtMinus5Point2vSupply	INTEGER,
				omtp12PlusXfpLineLoopbackSupported				INTEGER,
				omtp12PlusXfpXfiLoopbackSupported				INTEGER,
				omtp12PlusXfpOptionalVpsSupported				INTEGER,
				omtp12PlusXfpLaserDisableThroughI2cSupported			INTEGER,
				omtp12PlusXfpPowerDownThroughI2cSupported			INTEGER,
				omtp12PlusXfpVpsLvRegulatorModeSupported			INTEGER,
				omtp12PlusXfpVpsBypassedRegulatorModeSupported			INTEGER,
				omtp12PlusXfpActiveFecControlSupported				INTEGER,
				omtp12PlusXfpOptionalCmuModeSupported				INTEGER,
				omtp12PlusXfpFecBerSupported					INTEGER,
				omtp12PlusXfpReceivePowerMeasurementIsInOmaOrAverage		INTEGER,
				omtp12PlusXfpActiveWavelengthControlSupported			INTEGER,
				omtp12PlusXfpTransmitterIsCooledOrUncooled			INTEGER,
				omtp12PlusXfpReceiverTypeIsPinOrApd				INTEGER,
				omtp12PlusCardGeneralDetailsTableRowStatus			RowStatus
		}

	omtp12PlusInterfaceNumber OBJECT-TYPE
		SYNTAX INTEGER
		MAX-ACCESS not-accessible
		STATUS current
		DESCRIPTION
			"Interface number represents the port number
			InterfaceNumber to port mapping is as follows:
			1 - CLIENT-1
			2 - LINE-1(Primary)
			3 - LINE-2(Secondary)
			-----------------------------
			For properties which do not apply on any interface,
			the interface number must be passed as 0
			-----------------------------"

		::= { omtp12PlusCardGeneralDetailsEntry 1 }
		
	omtp12PlusEepromCardId OBJECT-TYPE
		SYNTAX INTEGER
		MAX-ACCESS read-only
		STATUS current
		DESCRIPTION
			"Tells the card ID of the OMTP12-PLUS card, present in the EEPROM
			-----------------------------
			omtp12PlusInterfaceNumber: 0
			-----------------------------"
		::= { omtp12PlusCardGeneralDetailsEntry 2 }
		
	omtp12PlusEepromCardName OBJECT-TYPE
		SYNTAX DisplayString
		MAX-ACCESS read-only
		STATUS current
		DESCRIPTION
			"Tells the card name of the OMTP12-PLUS card, present in the EEPROM
			-----------------------------
			omtp12PlusInterfaceNumber: 0
			-----------------------------"
		::= { omtp12PlusCardGeneralDetailsEntry 3 }
		
	omtp12PlusEepromPartCode OBJECT-TYPE
		SYNTAX DisplayString
		MAX-ACCESS read-only
		STATUS current
		DESCRIPTION
			"Tells the part code of the OMTP12-PLUS card, present in the EEPROM
			-----------------------------
			omtp12PlusInterfaceNumber: 0
			-----------------------------"
		::= { omtp12PlusCardGeneralDetailsEntry 4 }
		
	omtp12PlusEepromCardSerialNumber OBJECT-TYPE
		SYNTAX DisplayString
		MAX-ACCESS read-write
		STATUS current
		DESCRIPTION
			"This property get / set the information about 
			OMTP12-PLUS Card's Serial Number.
			-----------------------------
			omtp12PlusInterfaceNumber: 0
			-----------------------------
			Values:
			eg: 123456
			-----------------------------"
		::= { omtp12PlusCardGeneralDetailsEntry 5 }
		
	omtp12PlusEepromHardwareExternalReleaseVersion OBJECT-TYPE
		SYNTAX DisplayString
		MAX-ACCESS read-only
		STATUS current
		DESCRIPTION
			"Get the Card's Hardware External Release Version. 
			This detail will be displayed to the customer.
			This version will increment only if there are significant
			architectural changes in the product
			-----------------------------
			omtp12PlusInterfaceNumber: 0
			-----------------------------
			Values:
			eg: 0.1
			-----------------------------"
		::= { omtp12PlusCardGeneralDetailsEntry 6 }
		
	omtp12PlusSoftwareExternalReleaseVersion OBJECT-TYPE
		SYNTAX DisplayString
		MAX-ACCESS read-only
		STATUS current
		DESCRIPTION
			"Get the Card's Software External Release Version. 
			This detail will be displayed to the customer.
			This version will increment only if there are
			significant architectural changes in the product
			-----------------------------
			omtp12PlusInterfaceNumber: 0
			-----------------------------
			Values:
			eg: 0.1
			-----------------------------"
		::= { omtp12PlusCardGeneralDetailsEntry 7 }
		
	omtp12PlusEepromHardwareInternalReleaseVersion OBJECT-TYPE
		SYNTAX DisplayString
		MAX-ACCESS read-only
		STATUS current
		DESCRIPTION
			"Get the Card's Hardware Internal Release Version.
			This detail is used for development purposes only.
			It differs from the external hardware version.
			-----------------------------
			omtp12PlusInterfaceNumber: 0
			-----------------------------
			Values:
			eg: 4.1
			-----------------------------"
		::= { omtp12PlusCardGeneralDetailsEntry 8 }
		
	omtp12PlusSoftwareInternalReleaseVersion OBJECT-TYPE
		SYNTAX DisplayString
		MAX-ACCESS read-only
		STATUS current
		DESCRIPTION
			"Gets the Card's Software Internal Release Version.
			This detail is used for development purposes only.
			It differs from the external software version.
		      	-----------------------------
			omtp12PlusInterfaceNumber: 0
			-----------------------------
			Values:
			eg: 5.1
			-----------------------------"
		::= { omtp12PlusCardGeneralDetailsEntry 9 }
		
	omtp12PlusEepromCardUidNumber OBJECT-TYPE
		SYNTAX DisplayString
		MAX-ACCESS read-only
		STATUS current
		DESCRIPTION
			"Tells the Card Unique IDentifier. It is a 4 byte
			address used to uniquely identify a card.
			----------------------------
			omtp12PlusInterfaceNumber: 0
			------------------------------
			Values:
		      	eg: 12345678
			-----------------------------"
		::= { omtp12PlusCardGeneralDetailsEntry 10 }
		
	omtp12PlusEepromCardEui48Number OBJECT-TYPE
		SYNTAX DisplayString
		MAX-ACCESS read-only
		STATUS current
		DESCRIPTION
			"Tells the Card EUI-48 Number. It’s a 6 byte address
			used to uniquely identify a card.
			-----------------------------
			omtp12PlusInterfaceNumber: 0
			-----------------------------
			Values:
		      	eg: 0004A3123456
			-----------------------------"
		::= { omtp12PlusCardGeneralDetailsEntry 11 }
		
	omtp12PlusEepromCardEui64Number OBJECT-TYPE
		SYNTAX DisplayString
		MAX-ACCESS read-only
		STATUS current
		DESCRIPTION
			"Tells the Card EUI-64 Number. It’s a 8 byte address
			used to uniquely identify a card.
			-----------------------------
			omtp12PlusInterfaceNumber: 0
			-----------------------------
			Values:
		      	eg: 0004A31234567890
			-----------------------------"
		::= { omtp12PlusCardGeneralDetailsEntry 12 }
		
        omtp12PlusCardRootFileSystemVersion OBJECT-TYPE		 
		SYNTAX  DisplayString
		MAX-ACCESS  read-only
		STATUS current
		DESCRIPTION
			"Tells the Card's Root File System Version
			-----------------------------
			omtp12PlusInterfaceNumber: 0
			-----------------------------
			Value:
		      	eg: 8
			-----------------------------"
		::= { omtp12PlusCardGeneralDetailsEntry 13 }
		
	omtp12PlusCardInstallationDate OBJECT-TYPE
		SYNTAX DisplayString
		MAX-ACCESS read-write
		STATUS current
		DESCRIPTION
			"Get the card's installation date in
			dd/mm/yyyy format
			-----------------------------
			omtp12PlusInterfaceNumber: 0
			-----------------------------
			Values:
		      	eg: 12/03/2016
			-----------------------------"
		::= { omtp12PlusCardGeneralDetailsEntry 21 }

	omtp12PlusCardCommissionDate OBJECT-TYPE
		SYNTAX DisplayString
		MAX-ACCESS read-write
		STATUS current
		DESCRIPTION
			"Get the card's commission date in
			dd/mm/yyyy format
			-----------------------------
			omtp12PlusInterfaceNumber: 0
			-----------------------------
			Values:
		      	eg: 20/03/2016
			-----------------------------"
		::= { omtp12PlusCardGeneralDetailsEntry 22 }

	omtp12PlusCardRunningTime OBJECT-TYPE
		SYNTAX DisplayString
		MAX-ACCESS read-only
		STATUS current
		DESCRIPTION
			"Get the duration of time for which the card is
			operational/running
			-----------------------------
			omtp12PlusInterfaceNumber: 0
			-----------------------------
			Values:
		      	eg: 3d 2h 1m
			-----------------------------"
		::= { omtp12PlusCardGeneralDetailsEntry 23 }
		
	omtp12PlusCardRestartCount OBJECT-TYPE
		SYNTAX INTEGER
		MAX-ACCESS read-only
		STATUS current
		DESCRIPTION
			"Get the number of times the card has been soft reset.
			This value will get reset to 0 on factory reset.
			-----------------------------
			omtp12PlusInterfaceNumber: 0
			-----------------------------
			Values:
		      	eg: 10
			-----------------------------"
		::= { omtp12PlusCardGeneralDetailsEntry 24 }
		
	omtp12PlusXfpReadyForOperation OBJECT-TYPE
		SYNTAX INTEGER
		MAX-ACCESS read-only
		STATUS current
		DESCRIPTION
			"Module not ready indicates that the XFP
			has detected a condition that tells
			transmit or receive data is invalid.
			It shall consist of logical OR of the
			following signals:
			> Transmit Signal Conditioner Loss of Lock
			> Transmitter Laser Fault
			> Receiver Signal Conditioner Loss of Lock
			(Ref: INF-8077 2.4.1)
			-----------------------------
			omtp12PlusInterfaceNumber:
			1 - CLIENT-1
			2 - LINE-1
			3 - LINE-2
			-----------------------------
			Values:		
			1 - XFP is ready for operation 
			0 - XFP is not ready for operation
			-----------------------------"
		::= { omtp12PlusCardGeneralDetailsEntry 31 }
		
	omtp12PlusXfpI2cCommunicationStatus OBJECT-TYPE
		SYNTAX INTEGER
		MAX-ACCESS read-write
		STATUS current
		DESCRIPTION
			"Tells whether the XFP can be accessed
			on a single 2-wire interface bus or not.
			(Ref: INF-8077 2.4.2)
			-----------------------------
			omtp12PlusInterfaceNumber:
			1 - CLIENT-1
			2 - LINE-1
			3 - LINE-2
			-----------------------------
			Values:			
			1 - Enable I2C communication for XFP
				i.e. the XFP responds to 2-wire serial
				communication commands.
			0 - Disable I2C communication for XFP
				i.e. the XFP will not respond to or
				acknowledge any 2-wire interface communication
				from the host.
			-----------------------------"
		::= { omtp12PlusCardGeneralDetailsEntry 32 }
		
	omtp12PlusXfpEepromPage OBJECT-TYPE
		SYNTAX INTEGER
		MAX-ACCESS read-write
		STATUS current
		DESCRIPTION
			"This property sets/gets the XFP EEPROM page, 
			the value represents the XFP EEPROM page number.
			-----------------------------
			omtp12PlusInterfaceNumber:
			1 - CLIENT-1
			2 - LINE-1
			3 - LINE-2
			-----------------------------
			Values:			
			eg: 1(EEPROM Page number)
			-----------------------------"
		::= { omtp12PlusCardGeneralDetailsEntry 33 }
		
	omtp12PlusCheckCodeOfXfpEepromPage OBJECT-TYPE
		SYNTAX INTEGER
		MAX-ACCESS read-only
		STATUS current
		DESCRIPTION
			"This property provides the XFP
			check code(checksum) value for bytes 128 to 190
			present in XFP EEPROM Page number 1. 
			-----------------------------
			omtp12PlusInterfaceNumber:
			1 - CLIENT-1
			2 - LINE-1
			3 - LINE-2
			-----------------------------
			Values:			
			eg: 1(EEPROM Page number)
			-----------------------------"
		::= { omtp12PlusCardGeneralDetailsEntry 34 }
		
	omtp12PlusExtendedCheckCodeOfXfpEepromPage OBJECT-TYPE
		SYNTAX INTEGER
		MAX-ACCESS read-only
		STATUS current
		DESCRIPTION
			"This property provides the XFP
			extended check code(checksum) value for bytes 192 to 222
			present in XFP EEPROM Page number 1. 
			-----------------------------
			omtp12PlusInterfaceNumber:
			1 - CLIENT-1
			2 - LINE-1
			3 - LINE-2
			-----------------------------
			Values:			
			eg: 1(EEPROM Page number)
			-----------------------------"
		::= { omtp12PlusCardGeneralDetailsEntry 35 }
		
	omtp12PlusXfpVendorName OBJECT-TYPE
		SYNTAX DisplayString
		MAX-ACCESS read-only
		STATUS current
		DESCRIPTION
			"This property provides Vendor Name for given XFP. 
			The vendor name shall be the full name of the 
			corporation, a commonly accepted abbreviation of 
			the name of the corporation, the SCSI company code
			for the corporation, or the stock exchange code for
			the corporation.
			-----------------------------
			omtp12PlusInterfaceNumber:
			1 - CLIENT-1
			2 - LINE-1
			3 - LINE-2
			-----------------------------
			Values:			
			eg: WTD
			-----------------------------"
		::= { omtp12PlusCardGeneralDetailsEntry 36 }
		
	omtp12PlusXfpVendorIeeeId OBJECT-TYPE
		SYNTAX DisplayString
		MAX-ACCESS read-only
		STATUS current
		DESCRIPTION
			"This property defines the IEEE company Identifier for
			the vendor of XFP. A value of all zero in the 3-byte
			field indicates that the Vendor OUI is unspecified.
			-----------------------------
			omtp12PlusInterfaceNumber:
			1 - CLIENT-1
			2 - LINE-1
			3 - LINE-2
			-----------------------------
			Values:			
			eg: 010
			-----------------------------"
		::= { omtp12PlusCardGeneralDetailsEntry 37 }
		
	omtp12PlusXfpPartNumber OBJECT-TYPE
		SYNTAX DisplayString
		MAX-ACCESS read-only
		STATUS current
		DESCRIPTION
			"This property defines the vendor part number or
			product name of the XFP. A value of all zero
			indicates that the vendor Part Number is unspecified.
			-----------------------------
			omtp12PlusInterfaceNumber:
			1 - CLIENT-1
			2 - LINE-1
			3 - LINE-2
			-----------------------------
			Values:			
			eg: FTRX-1811-2D2
			-----------------------------"
		::= { omtp12PlusCardGeneralDetailsEntry 38 }
		
	omtp12PlusXfpSerialNumber OBJECT-TYPE
		SYNTAX DisplayString
		MAX-ACCESS read-only
		STATUS current
		DESCRIPTION
			"This property provides vendor serial number defining
			the vendor’s serial number for the XFP. A value of all
			zero in the 16-byte field indicates that the vendor
			serial number is unspecified.
			-----------------------------
			omtp12PlusInterfaceNumber:
			1 - CLIENT-1
			2 - LINE-1
			3 - LINE-2
			-----------------------------
			Values:			
			eg: KBG02CU
			-----------------------------"
		::= { omtp12PlusCardGeneralDetailsEntry 39 }
		
	omtp12PlusXfpRevisionNumber OBJECT-TYPE
		SYNTAX DisplayString
		MAX-ACCESS read-only
		STATUS current
		DESCRIPTION
			"The vendor revision number defining the vendor’s
			 product revision number. A value of all zero indicates
			 that the vendor revision number is unspecified
			-----------------------------
			omtp12PlusInterfaceNumber:
			1 - CLIENT-1
			2 - LINE-1
			3 - LINE-2
			-----------------------------
			Values:			
			eg: RT
			-----------------------------"
		::= { omtp12PlusCardGeneralDetailsEntry 40 }
		
	omtp12PlusXfpManufacturingDate OBJECT-TYPE
		SYNTAX DisplayString
		MAX-ACCESS read-only
		STATUS current
		DESCRIPTION
			"This property defines the manufacturing date for 
			XFP. A value of 8-byte field in ASCII which represents
			year, month and date of each two bytes. 
			Extra two bytes may be blank
			-----------------------------
			omtp12PlusInterfaceNumber:
			1 - CLIENT-1
			2 - LINE-1
			3 - LINE-2
			-----------------------------
			Values:			
			eg: 160224
			-----------------------------"
		::= { omtp12PlusCardGeneralDetailsEntry 41 }
		
	omtp12PlusFixedXfpLaserWavelength OBJECT-TYPE
		SYNTAX DisplayString
		MAX-ACCESS read-only
		STATUS current
		DESCRIPTION
			"This property provides transmitter LASER wavelength(nm)
			of the XFP
			-----------------------------
			omtp12PlusInterfaceNumber:
			1 - CLIENT-1
			2 - LINE-1
			3 - LINE-2
			-----------------------------
			Values:			
			eg: 1310
			-----------------------------"
		::= { omtp12PlusCardGeneralDetailsEntry 42 }
		
	omtp12PlusXfpLaserWavelengthTolerance OBJECT-TYPE
		SYNTAX DisplayString
		MAX-ACCESS read-only
		STATUS current
		DESCRIPTION
			"This property provides XFP wavelength tolerance in GhZ
			-----------------------------
			omtp12PlusInterfaceNumber:
			1 - CLIENT-1
			2 - LINE-1
			3 - LINE-2
			-----------------------------
			Values:			
			eg: 0.02
			-----------------------------"
		::= { omtp12PlusCardGeneralDetailsEntry 43 }
		
	omtp12PlusXfpWavelengthTunabilitySupported OBJECT-TYPE
		SYNTAX INTEGER
		MAX-ACCESS read-only
		STATUS current
		DESCRIPTION
			"This property provides information whether the XFP
			supports wavelength tunability or not.
			-----------------------------
			omtp12PlusInterfaceNumber:
			1 - CLIENT-1
			2 - LINE-1
			3 - LINE-2
			-----------------------------
			Values:			
			1 - XFP supports wavelength tunability
			0 - XFP not supports wavelength tunability
			-----------------------------"
		::= { omtp12PlusCardGeneralDetailsEntry 44 }

	omtp12PlusTunableXfpLaserWavelengthError OBJECT-TYPE
		SYNTAX DisplayString
		MAX-ACCESS read-only
		STATUS current
		DESCRIPTION
			"This property provides wavelength error in pm
			-----------------------------
			omtp12PlusInterfaceNumber:
			1 - CLIENT-1
			2 - LINE-1
			3 - LINE-2
			-----------------------------
			Values:			
			eg: 0.02
			-----------------------------"
		::= { omtp12PlusCardGeneralDetailsEntry 45 }
		
	omtp12PlusTunableXfpLaserFrequencyError OBJECT-TYPE
		SYNTAX DisplayString
		MAX-ACCESS read-only
		STATUS current
		DESCRIPTION
			"This property defines the monitor of current frequency
			Error of XFP. Frequency error is reported in Ghz.
			-----------------------------
			omtp12PlusInterfaceNumber:
			1 - CLIENT-1
			2 - LINE-1
			3 - LINE-2
			-----------------------------
			Values:			
			eg: 0.03
			-----------------------------"
		::= { omtp12PlusCardGeneralDetailsEntry 46 }
		
	omtp12PlusTunableXfpLaserFirstFrequency OBJECT-TYPE
		SYNTAX DisplayString
		MAX-ACCESS read-only
		STATUS current
		DESCRIPTION
			"This property defines the first LASER frequency of XFP.
			The two byte value is specified in units of THz.
			-----------------------------
			omtp12PlusInterfaceNumber:
			1 - CLIENT-1
			2 - LINE-1
			3 - LINE-2
			-----------------------------
			Values:			
			eg: 1529.45
			-----------------------------"
		::= { omtp12PlusCardGeneralDetailsEntry 47 }
		
	omtp12PlusTunableXfpLaserLastFrequency OBJECT-TYPE
		SYNTAX DisplayString
		MAX-ACCESS read-only
		STATUS current
		DESCRIPTION
			"This property defines the last laser frequency of XFP.
		 	 The two byte value is specified in units of THz.
			-----------------------------
			omtp12PlusInterfaceNumber:
			1 - CLIENT-1
			2 - LINE-1
			3 - LINE-2
			-----------------------------
			Values:			
			eg: 1563.45
			-----------------------------"
		::= { omtp12PlusCardGeneralDetailsEntry 48 }
		
	omtp12PlusTunableXfpWavelengthGridSpacing OBJECT-TYPE
		SYNTAX DisplayString
		MAX-ACCESS read-only
		STATUS current
		DESCRIPTION
			"This property gives difference in the wavelength
			between two channels In GhZ
			-----------------------------
			omtp12PlusInterfaceNumber:
			1 - CLIENT-1
			2 - LINE-1
			3 - LINE-2
			-----------------------------
			Values:
			eg: 50
			-----------------------------"
		::= { omtp12PlusCardGeneralDetailsEntry 49 }
		
	omtp12PlusXfpConnectorType OBJECT-TYPE
		SYNTAX DisplayString
		MAX-ACCESS read-only
		STATUS current
		DESCRIPTION
			"This property provides information of the XFP
			connector, value indicates the external connector
			provided on the XFP.
			-----------------------------
			omtp12PlusInterfaceNumber:
			1 - CLIENT-1
			2 - LINE-1
			3 - LINE-2
			-----------------------------
			Values:
			00h 	Unknown or unspecified
			01h 	SC
			02h 	Fibre Channel Style 1 copper connector
			03h 	Fibre Channel Style 2 copper connector
			04h 	BNC/TNC
			05h 	Fibre Channel coaxial headers
			06h 	FiberJack
			07h 	LC
			08h 	MT-RJ
			09h 	MU
			0Ah 	SG
			0Bh 	Optical pigtail
			0C-1Fh 	Reserved
			20h 	HSSDC II
			21h 	Copper Pigtail
			22h-7Fh Reserved
			80-FFh 	Vendor specific
			-----------------------------"
		::= { omtp12PlusCardGeneralDetailsEntry 50 }
		
	omtp12PlusXfpLinkLength OBJECT-TYPE
		SYNTAX DisplayString
		MAX-ACCESS read-only
		STATUS current
		DESCRIPTION
			"This property provides link length suported by the XFP
			-----------------------------
			omtp12PlusInterfaceNumber:
			1 - CLIENT-1
			2 - LINE-1
			3 - LINE-2
			-----------------------------
			Values:
			eg: 80.00
			-----------------------------"
		::= { omtp12PlusCardGeneralDetailsEntry 51 }
		
	omtp12PlusXfpCdrRateSupported OBJECT-TYPE
		SYNTAX INTEGER
		MAX-ACCESS read-only
		STATUS current
		DESCRIPTION
			"This property indicates which rates are supported by
			the CDR present in XFP.
			-----------------------------
			omtp12PlusInterfaceNumber:
			1 - CLIENT-1
			2 - LINE-1
			3 - LINE-2
			-----------------------------
			Values:

			Return value 1-Byte represetation:
			Byte-1  CDR Rates
			Bit-7	9.95 Gb/s
			Bit-6	10.3 Gb/s
			Bit-5	10.5 Gb/s
			Bit-4	10.7 Gb/s
			Bit-3	11.1 Gb/s
			Bit-2	Reserved
			Bit-1	Dont care for this property
			Bit-0	Dont care for this property
			-----------------------------"
		::= { omtp12PlusCardGeneralDetailsEntry 52 }
		
	omtp12PlusXfpSignalEncodingTypeSupported OBJECT-TYPE
		SYNTAX INTEGER
		MAX-ACCESS read-only
		STATUS current
		DESCRIPTION
			"This property indicates the serial encoding mechanisms
			that are supported by the XFP.
			-----------------------------
			omtp12PlusInterfaceNumber:
			1 - CLIENT-1
			2 - LINE-1
			3 - LINE-2
			-----------------------------
			Values:

			Return value 1-Byte represetation:
			Byte-1  Encoding Type
			Bit-7	64B/66B          
			Bit-6	8B10B     	 	 
			Bit-5	SONET Scrambled  
			Bit-4	NRZ              
			Bit-3	RZ              
			Bit-2	Reserved        
			Bit-1	Reserved         
			Bit-0	Reserved 
			-----------------------------"
		::= { omtp12PlusCardGeneralDetailsEntry 53 }
		
	omtp12PlusXfpTransceiverCodesSupported OBJECT-TYPE
		SYNTAX INTEGER
		MAX-ACCESS read-only
		STATUS current
		DESCRIPTION
			"The identifier value specifies which transceiver
			codes are supported by the XFP
			-----------------------------
			omtp12PlusInterfaceNumber:
			1 - CLIENT-1
			2 - LINE-1
			3 - LINE-2
			-----------------------------
			Values:

			Return value 8-Byte represetation:
			---------------------------------------------------------------------------------------------------------------------------------------
				  Byte-1	  Byte-2	          Byte-3	  Byte-4	          Byte-5    Byte-6    Byte-7	        Byte-8
			---------------------------------------------------------------------------------------------------------------------------------------
			Bit-7	 10GBASE-SR	 1200-MX-SN-I        	 Reserved	 1000BASE-SX/1xFC MMF	 I-64.1r   S-64.1    L-64.1	       V-64.2a
			Bit-6	 10GBASE-LR	 1200-SM-LL-L	         Reserved	 1000BASE-LX/1xFC-SMF	 I-64.1	   S-64.2a   L-64.2a	       V-64.2b
			Bit-5	 10GBASE-ER	 Extended 1550 nm	 Reserved	 2xFC-MMF/2xFC-SMF	 I-64.2r   S-64.2b   L-64.2b	       V-64.3
			Bit-4	 10GBASE-LRM	 Intermediate 1300 nm	 Reserved	 OC-48-SR	         I-64.2	   S-64.3a   L-64.2c	       Reserved
			Bit-3	 10GBASE-SW	 Reserved	         Reserved	 OC-48-IR	         I-64.3	   S-64.3b   L-64.3	       Reserved
			Bit-2	 10GBASE-LW	 Reserved	         Reserved	 OC-48-LR	         I-64.5	   S-64.5a   G.959.1 P1L1-2D2  Reserved
			Bit-1	 10GBASE-EW	 Reserved	         Reserved	 Reserved	         Reserved  S-64.5b   Reserved	       Reserved
			Bit-0	 Reserved	 Reserved	         Reserved	 Reserved	         Reserved  Reserved  Reserved	       Reserved
			-----------------------------"
		::= { omtp12PlusCardGeneralDetailsEntry 54 }
		
	omtp12PlusXfpMaximumBitrateSupported OBJECT-TYPE
		SYNTAX DisplayString
		MAX-ACCESS read-only
		STATUS current
		DESCRIPTION
			"This property provides maximum bit rate value of the
			given XFP
			-----------------------------
			omtp12PlusInterfaceNumber:
			1 - CLIENT-1
			2 - LINE-1
			3 - LINE-2
			-----------------------------
			Values: 9.5
			-----------------------------"
		::= { omtp12PlusCardGeneralDetailsEntry 55 }
		
	omtp12PlusXfpMinimumBitrateSupported OBJECT-TYPE
		SYNTAX DisplayString
		MAX-ACCESS read-only
		STATUS current
		DESCRIPTION
			"This property provides minimum bit rate value of the 
			given XFP
			-----------------------------
			omtp12PlusInterfaceNumber:
			1 - CLIENT-1
			2 - LINE-1
			3 - LINE-2
			-----------------------------
			Values: 5.5
			-----------------------------"
		::= { omtp12PlusCardGeneralDetailsEntry 56 }
		
	omtp12PlusXfpMaximumCaseTemperatureSupported OBJECT-TYPE
		SYNTAX INTEGER
		MAX-ACCESS read-only
		STATUS current
		DESCRIPTION
			"This property provides the maximum case temperature
			(degree celcius) supported by XFP.
			-----------------------------
			omtp12PlusInterfaceNumber:
			1 - CLIENT-1
			2 - LINE-1
			3 - LINE-2
			-----------------------------
			Values:
			eg: 70
			-----------------------------"

		::= { omtp12PlusCardGeneralDetailsEntry 57 }
		
	omtp12PlusXfpMaximumPowerDissipationSupported OBJECT-TYPE
		SYNTAX INTEGER
		MAX-ACCESS read-only
		STATUS current
		DESCRIPTION
			"This property provides the maximum power dissipation(mW)
			supported from XFP.
			-----------------------------
			omtp12PlusInterfaceNumber:
			1 - CLIENT-1
			2 - LINE-1
			3 - LINE-2
			-----------------------------
			Values:
			eg: 25
			-----------------------------"
		::= { omtp12PlusCardGeneralDetailsEntry 58 }
		
	omtp12PlusXfpMaximumPowerDissipationSupportedAtPowerDownMode OBJECT-TYPE
		SYNTAX INTEGER
		MAX-ACCESS read-only
		STATUS current
		DESCRIPTION
			"This property provides the maximum power dissipation(mW)
			supported from XFP in power-down mode.
			-----------------------------
			omtp12PlusInterfaceNumber:
			1 - CLIENT-1
			2 - LINE-1
			3 - LINE-2
			-----------------------------
			Values:
			eg: 20
			-----------------------------"
		::= { omtp12PlusCardGeneralDetailsEntry 59 }
		
	omtp12PlusXfpMaximumCurrentLimitSupportedAtPlus5vSupply OBJECT-TYPE
		SYNTAX INTEGER
		MAX-ACCESS read-only
		STATUS current
		DESCRIPTION
			"This property defines the maximum current(mA) required
			by XFP at +5V power supply.
			-----------------------------
			omtp12PlusInterfaceNumber:
			1 - CLIENT-1
			2 - LINE-1
			3 - LINE-2
			-----------------------------
			Values:
			eg: 50
			-----------------------------"
		::= { omtp12PlusCardGeneralDetailsEntry 60 }
		
	omtp12PlusXfpMaximumCurrentLimitSupportedAtPlus3Point3vSupply OBJECT-TYPE
		SYNTAX INTEGER
		MAX-ACCESS read-only
		STATUS current
		DESCRIPTION
			"This property defines the maximum current(mA) required
			by XFP at +3.3V power supply.
			-----------------------------
			omtp12PlusInterfaceNumber:
			1 - CLIENT-1
			2 - LINE-1
			3 - LINE-2
			-----------------------------
			Values:
			eg: 50
			-----------------------------"
		::= { omtp12PlusCardGeneralDetailsEntry 61 }
		
	omtp12PlusXfpMaximumCurrentLimitSupportedAtPlus1Point8vSupply OBJECT-TYPE
		SYNTAX INTEGER
		MAX-ACCESS read-only
		STATUS current
		DESCRIPTION
			"This property defines the maximum current(mA) required
			by XFP at +1.8V power supply.
			-----------------------------
			omtp12PlusInterfaceNumber:
			1 - CLIENT-1
			2 - LINE-1
			3 - LINE-2
			-----------------------------
			Values:
			eg: 50
			-----------------------------"
		::= { omtp12PlusCardGeneralDetailsEntry 62 }
		
	omtp12PlusXfpMaximumCurrentLimitSupportedAtMinus5Point2vSupply OBJECT-TYPE
		SYNTAX INTEGER
		MAX-ACCESS read-only
		STATUS current
		DESCRIPTION
			"This property defines the maximum current(mA) required
			by XFP at -5.2V power supply.
			-----------------------------
			omtp12PlusInterfaceNumber:
			1 - CLIENT-1
			2 - LINE-1
			3 - LINE-2
			-----------------------------
			Values:
			eg: 50
			-----------------------------"
		::= { omtp12PlusCardGeneralDetailsEntry 63 }
		
	omtp12PlusXfpLineLoopbackSupported OBJECT-TYPE
		SYNTAX INTEGER
		MAX-ACCESS read-only
		STATUS current
		DESCRIPTION
			"This property provides information whether Line side
			loopback is supported or not.
			-----------------------------
			omtp12PlusInterfaceNumber:
			1 - CLIENT-1
			2 - LINE-1
			3 - LINE-2
			-----------------------------
			Values:
			1 - Lineside Loopback is supported in XFP
			0 - No Lineside Loopback is supported
			-----------------------------"
		::= { omtp12PlusCardGeneralDetailsEntry 64 }
		
	omtp12PlusXfpXfiLoopbackSupported OBJECT-TYPE
		SYNTAX INTEGER
		MAX-ACCESS read-only
		STATUS current
		DESCRIPTION
			"This property provides information whether Line side
			loopback at the Xfi level is supported or not.
			-----------------------------
			omtp12PlusInterfaceNumber:
			1 - CLIENT-1
			2 - LINE-1
			3 - LINE-2
			-----------------------------
			Values:
			1 - Xfi Loopback is supported in XFP
			0 - No Xfi Loopback is supported
			-----------------------------"
		::= { omtp12PlusCardGeneralDetailsEntry 65 }
		
	omtp12PlusXfpOptionalVpsSupported OBJECT-TYPE
		SYNTAX INTEGER
		MAX-ACCESS read-only
		STATUS current
		DESCRIPTION
			"This property provides information whether XFP
			supports optional variable power supply or not.
			-----------------------------
			omtp12PlusInterfaceNumber:
			1 - CLIENT-1
			2 - LINE-1
			3 - LINE-2
			-----------------------------
			Values:
			1 - XFP supports optional vps
			0 - XFP not supports optional vps
			-----------------------------"
		::= { omtp12PlusCardGeneralDetailsEntry 66 }
		
	omtp12PlusXfpLaserDisableThroughI2cSupported OBJECT-TYPE
		SYNTAX INTEGER
		MAX-ACCESS read-only
		STATUS current
		DESCRIPTION
			"This property provides information whether XFP
			LASER can be operated through single 2-wire interface
			bus or not.
			-----------------------------
			omtp12PlusInterfaceNumber:
			1 - CLIENT-1
			2 - LINE-1
			3 - LINE-2
			-----------------------------
			Values:
			1 - XFP supports LASER disable through I2C
			0 - XFP does not support LASER disable through I2C
			-----------------------------"
		::= { omtp12PlusCardGeneralDetailsEntry 67 }
		
	omtp12PlusXfpPowerDownThroughI2cSupported OBJECT-TYPE
		SYNTAX INTEGER
		MAX-ACCESS read-only
		STATUS current
		DESCRIPTION
			"This property provides information whether XFP-
			Power-down can be operated through single 2-wire 
			interface bus or not.
			-----------------------------
			omtp12PlusInterfaceNumber:
			1 - CLIENT-1
			2 - LINE-1
			3 - LINE-2
			-----------------------------
			Values:
			1 - XFP Supports XFP-power-down through I2C  
			0 - XFP does not supports XFP-power-down through I2C  
			-----------------------------"
		::= { omtp12PlusCardGeneralDetailsEntry 68 }
		
	omtp12PlusXfpVpsLvRegulatorModeSupported OBJECT-TYPE
		SYNTAX INTEGER
		MAX-ACCESS read-only
		STATUS current
		DESCRIPTION
			"This property provides information whether XFP
			supports VPS_LV_regulator_mode or not.
			-----------------------------
			omtp12PlusInterfaceNumber:
			1 - CLIENT-1
			2 - LINE-1
			3 - LINE-2
			-----------------------------
			Values:
			1 - XFP supports VPS_LV_regulator_mode
			0 - XFP not supports VPS_LV_regulator_mode
			-----------------------------"
		::= { omtp12PlusCardGeneralDetailsEntry 69 }
		
	omtp12PlusXfpVpsBypassedRegulatorModeSupported OBJECT-TYPE
		SYNTAX INTEGER
		MAX-ACCESS read-only
		STATUS current
		DESCRIPTION
			"This property provides information whether XFP
			supports VPS bypassed regulator mode or not.
			-----------------------------
			omtp12PlusInterfaceNumber:
			1 - CLIENT-1
			2 - LINE-1
			3 - LINE-2
			-----------------------------
			Values:
			1 - XFP supports VPS bypassed regulator mode
			0 - XFP not supports active VPS bypassed regulator mode
			-----------------------------"
		::= { omtp12PlusCardGeneralDetailsEntry 70 }
		
	omtp12PlusXfpActiveFecControlSupported OBJECT-TYPE
		SYNTAX INTEGER
		MAX-ACCESS read-only
		STATUS current
		DESCRIPTION
			"This property provides information whether XFP
			supports active FEC control functions or not.
			-----------------------------
			omtp12PlusInterfaceNumber:
			1 - CLIENT-1
			2 - LINE-1
			3 - LINE-2
			-----------------------------
			Values:
			1 - XFP supports active FEC control functions
			0 - XFP not supports active FEC control functions
			-----------------------------"
		::= { omtp12PlusCardGeneralDetailsEntry 71 }
		
	omtp12PlusXfpOptionalCmuModeSupported OBJECT-TYPE
		SYNTAX INTEGER
		MAX-ACCESS read-only
		STATUS current
		DESCRIPTION
			"This property provides information whether XFP
			supports CMU mode or not.
			-----------------------------
			omtp12PlusInterfaceNumber:
			1 - CLIENT-1
			2 - LINE-1
			3 - LINE-2
			-----------------------------
			Values:
			1 - XFP supports CMU mode
			0 - XFP not supports CMU mode
			-----------------------------"
		::= { omtp12PlusCardGeneralDetailsEntry 72 }
		
	omtp12PlusXfpFecBerSupported OBJECT-TYPE
		SYNTAX INTEGER
		MAX-ACCESS read-only
		STATUS current
		DESCRIPTION
			"This property provides information whether XFP
			supports FEC BER or not.
			-----------------------------
			omtp12PlusInterfaceNumber:
			1 - CLIENT-1
			2 - LINE-1
			3 - LINE-2
			-----------------------------
			Values:
			1 - XFP supports FEC BER
			0 - XFP not supports FEC BER
			-----------------------------"
		::= { omtp12PlusCardGeneralDetailsEntry 73 }
		
	omtp12PlusXfpReceivePowerMeasurementIsInOmaOrAverage OBJECT-TYPE
		SYNTAX INTEGER
		MAX-ACCESS read-only
		STATUS current
		DESCRIPTION
			"This property tells whether the received power  
			measurement from XFP is given as Oma or Average.
			-----------------------------
			omtp12PlusInterfaceNumber:
			1 - CLIENT-1
			2 - LINE-1
			3 - LINE-2
			-----------------------------
			Values:
			1 - OMA
			0 - Average Power
			-----------------------------"
		::= { omtp12PlusCardGeneralDetailsEntry 74 }
		
	omtp12PlusXfpActiveWavelengthControlSupported OBJECT-TYPE
		SYNTAX INTEGER
		MAX-ACCESS read-only
		STATUS current
		DESCRIPTION
			"This property provides whether the XFP wavelength 
			controlling state is active or not
			-----------------------------
			omtp12PlusInterfaceNumber:
			1 - CLIENT-1
			2 - LINE-1
			3 - LINE-2
			-----------------------------
			Values:
			1 - active
			0 - not active
			-----------------------------"
		::= { omtp12PlusCardGeneralDetailsEntry 75 }
		
	omtp12PlusXfpTransmitterIsCooledOrUncooled OBJECT-TYPE
		SYNTAX INTEGER
		MAX-ACCESS read-only
		STATUS current
		DESCRIPTION
			"This property provide information on which type of
			diode used in transmitter of the XFP
			-----------------------------
			omtp12PlusInterfaceNumber:
			1 - CLIENT-1
			2 - LINE-1
			3 - LINE-2
			-----------------------------
			Values:
			1 - Cooling circuit supported for XFP transmitter. 
			0 - Cooling circuit not supported for XFP transmitter.
			-----------------------------"
		::= { omtp12PlusCardGeneralDetailsEntry 76 }
		
	omtp12PlusXfpReceiverTypeIsPinOrApd OBJECT-TYPE
		SYNTAX INTEGER
		MAX-ACCESS read-only
		STATUS current
		DESCRIPTION
			"This property provide information on which type of
			diode used in transmitter of the XFP.
			-----------------------------
			omtp12PlusInterfaceNumber:
			1 - CLIENT-1
			2 - LINE-1
			3 - LINE-2
			-----------------------------
			Values:
			1 - PIN detector
			0 - APD detector			 
			-----------------------------"
		::= { omtp12PlusCardGeneralDetailsEntry 77 }

	omtp12PlusCardGeneralDetailsTableRowStatus OBJECT-TYPE
              SYNTAX      RowStatus
              MAX-ACCESS  read-write
              STATUS      current
              DESCRIPTION
                      "	This is MIB realted property,
			NOT to be considered as a card property"
              ::= { omtp12PlusCardGeneralDetailsEntry 78 }	

--*****************************************************************************
--				CONFIGURATION
--*****************************************************************************

        omtp12PlusConfigurationTable OBJECT-TYPE
                SYNTAX SEQUENCE OF Omtp12PlusConfigurationEntry
                MAX-ACCESS not-accessible
                STATUS current
                DESCRIPTION
                	"Contains configuration queries of the OMTP12-PLUS card"
                ::= { omtp12PlusConfiguration 1 }

	omtp12PlusConfigurationEntry OBJECT-TYPE
		SYNTAX  Omtp12PlusConfigurationEntry
		MAX-ACCESS  not-accessible
		STATUS  current
		DESCRIPTION 
			""
		INDEX   { node, rack , subRack , slot , omtp12PlusInterfaceNumber}
		::= { omtp12PlusConfigurationTable 1 }

	Omtp12PlusConfigurationEntry ::= 
		SEQUENCE { 
				omtp12PlusCardSoftwareUpgrade						DisplayString,
				omtp12PlusCardSignalMonitorState					INTEGER,
				omtp12PlusCardOpticalMonitorState					INTEGER,
				omtp12PlusCardSoftReset							INTEGER,
				omtp12PlusCardFactoryReset						INTEGER,
				omtp12PlusCardAccessStatus						INTEGER,
				omtp12PlusSyncSystemTimeWithNtpServer				DisplayString,
				omtp12PlusSyncRtcWithNtpServer						DisplayString,
				omtp12PlusSyncRtcWithSystemTime						DisplayString,
				omtp12PlusUpdateGivenTimeIntoSystem					DisplayString,
				omtp12PlusUpdateGivenTimeIntoRtc					DisplayString,
				omtp12PlusSystemTimeAndRtcTime						DisplayString,
				omtp12PlusApsLinePathSwitchingMode					INTEGER,
				omtp12PlusApsUserChoiceOfLinePath					INTEGER,
				omtp12PlusApsCurrentOperationalLinePath					INTEGER,
				omtp12PlusTrafficConfiguration						INTEGER,
				omtp12PlusLoopbackState							INTEGER,
				omtp12PlusPortSignalMonitorState					INTEGER,
				omtp12PlusPortOpticalMonitorState					INTEGER,
				omtp12PlusClearSignalPerformance					INTEGER,
				omtp12PlusAlsState							INTEGER,
				omtp12PlusAlsPulseRepetitionTime					INTEGER,
				omtp12PlusOtuFecConfiguration						INTEGER,
				omtp12PlusOtuSignalFailThreshold					INTEGER,
				omtp12PlusOtuSignalDegradeThreshold					INTEGER,
				omtp12PlusOtuAlarmIndicationSignalAlarmInsertion			INTEGER,
				omtp12PlusOtuSapiTransmitTraceMessage					DisplayString,
				omtp12PlusOtuDapiTransmitTraceMessage					DisplayString,
				omtp12PlusOtuOperatorSpecificTransmitTraceMessage			DisplayString,
				omtp12PlusOtuSapiExpectedTraceMessage					DisplayString,
				omtp12PlusOtuDapiExpectedTraceMessage					DisplayString,
				omtp12PlusOtuOperatorSpecificExpectedTraceMessage			DisplayString,
				omtp12PlusOtuSapiReceivedTraceMessage					DisplayString,
				omtp12PlusOtuDapiReceivedTraceMessage					DisplayString,
				omtp12PlusOtuOperatorSpecificReceivedTraceMessage			DisplayString,
				omtp12PlusOduSignalFailThreshold					INTEGER,
				omtp12PlusOduSignalDegradeThreshold					INTEGER,
				omtp12PlusOduAlarmIndicationSignalAlarmInsertion			INTEGER,
				omtp12PlusOduLockedDefectAlarmInsertion					INTEGER,
				omtp12PlusOduOpenConnectionIndicationAlarmInsertion			INTEGER,
				omtp12PlusOduSapiTransmitTraceMessage					DisplayString,
				omtp12PlusOduDapiTransmitTraceMessage					DisplayString,
				omtp12PlusOduOperatorSpecificTransmitTraceMessage			DisplayString,
				omtp12PlusOduSapiExpectedTraceMessage					DisplayString,
				omtp12PlusOduDapiExpectedTraceMessage					DisplayString,
				omtp12PlusOduOperatorSpecificExpectedTraceMessage			DisplayString,
				omtp12PlusOduSapiReceivedTraceMessage					DisplayString,
				omtp12PlusOduDapiReceivedTraceMessage					DisplayString,
				omtp12PlusOduOperatorSpecificReceivedTraceMessage			DisplayString,
				omtp12PlusOpuTransmitPayloadType					INTEGER,
				omtp12PlusOpuReceivedPayloadType					INTEGER,
				omtp12PlusSdhMsB2ExcessiveErrorThreshold				INTEGER,
				omtp12PlusSdhMsB2SignalDegradeThreshold					INTEGER,
				omtp12PlusWan10gMsB2ExcessiveErrorThreshold					INTEGER,
				omtp12PlusWan10gMsB2SignalDegradeThreshold				INTEGER,
				omtp12PlusTunableXfpLaserWavelength					INTEGER,
				omtp12PlusTunableXfpLaserChannelNumber					INTEGER,
				omtp12PlusXfpLaserState							INTEGER,
				omtp12PlusXfpReset							INTEGER,
				omtp12PlusXfpPowerDownMode						INTEGER,
				omtp12PlusXfpLineLoopback						INTEGER,
				omtp12PlusXfpXfiLoopback						INTEGER,
				omtp12PlusXfpAmplitudeThresholdOfReceiverForFecControl			INTEGER,
				omtp12PlusXfpPhaseInEyeDiagramForFecControl				INTEGER,
				omtp12PlusXfpSystemReportingBer						INTEGER,
				omtp12PlusXfpHighTemperatureAlarmThreshold				DisplayString,
				omtp12PlusXfpLowTemperatureAlarmThreshold				DisplayString,
				omtp12PlusXfpHighTemperatureWarningThreshold				DisplayString,
				omtp12PlusXfpLowTemperatureWarningThreshold				DisplayString,
				omtp12PlusXfpHighBiasCurrentAlarmThreshold				DisplayString,
				omtp12PlusXfpLowBiasCurrentAlarmThreshold				DisplayString,
				omtp12PlusXfpHighBiasCurrentWarningThreshold				DisplayString,
				omtp12PlusXfpLowBiasCurrentWarningThreshold				DisplayString,
				omtp12PlusXfpInputHighPowerAlarmThreshold				DisplayString,
				omtp12PlusXfpInputLowPowerAlarmThreshold				DisplayString,
				omtp12PlusXfpInputHighPowerWarningThreshold				DisplayString,
				omtp12PlusXfpInputLowPowerWarningThreshold				DisplayString,
				omtp12PlusXfpOutputHighPowerAlarmThreshold				DisplayString,
				omtp12PlusXfpOutputLowPowerAlarmThreshold				DisplayString,
				omtp12PlusXfpOutputHighPowerWarningThreshold				DisplayString,
				omtp12PlusXfpOutputLowPowerWarningThreshold				DisplayString,
				omtp12PlusXfpHighSupplyVoltageAlarmThreshold				DisplayString,
				omtp12PlusXfpLowSupplyVoltageAlarmThreshold				DisplayString,
				omtp12PlusXfpHighSupplyVoltageWarningThreshold				DisplayString,
				omtp12PlusXfpLowSupplyVoltageWarningThreshold				DisplayString,
				omtp12PlusXfpInputPowerFailureAlarmInhibit				INTEGER,
				omtp12PlusXfpOutputPowerFailureAlarmInhibit				INTEGER,
				omtp12PlusXfpHighTemperatureAlarmInhibit				INTEGER,
				omtp12PlusXfpLowTemperatureAlarmInhibit					INTEGER,
				omtp12PlusXfpHighTemperatureWarningInhibit				INTEGER,
				omtp12PlusXfpLowTemperatureWarningInhibit				INTEGER,
				omtp12PlusXfpHighBiasCurrentAlarmInhibit				INTEGER,
				omtp12PlusXfpLowBiasCurrentAlarmInhibit					INTEGER,
				omtp12PlusXfpHighBiasCurrentWarningInhibit				INTEGER,
				omtp12PlusXfpLowBiasCurrentWarningInhibit				INTEGER,
				omtp12PlusXfpInputHighPowerAlarmInhibit					INTEGER,
				omtp12PlusXfpInputLowPowerAlarmInhibit					INTEGER,
				omtp12PlusXfpInputHighPowerWarningInhibit				INTEGER,
				omtp12PlusXfpInputLowPowerWarningInhibit				INTEGER,
				omtp12PlusXfpOutputHighPowerAlarmInhibit				INTEGER,
				omtp12PlusXfpOutputLowPowerAlarmInhibit					INTEGER,
				omtp12PlusXfpOutputHighPowerWarningInhibit				INTEGER,
				omtp12PlusXfpOutputLowPowerWarningInhibit				INTEGER,
				omtp12PlusXfpHighSupplyVoltageAlarmInhibit				INTEGER,
				omtp12PlusXfpLowSupplyVoltageAlarmInhibit				INTEGER,
				omtp12PlusXfpHighSupplyVoltageWarningInhibit				INTEGER,
				omtp12PlusXfpLowSupplyVoltageWarningInhibit				INTEGER,
				omtp12PlusXfpPresenceAbsenceNotificationInhibit				INTEGER,
				omtp12PlusOtuLossOfSignalAlarmInhibit					INTEGER,
				omtp12PlusOtuLossOfFrameAlarmInhibit					INTEGER,
				omtp12PlusOtuOutOfFrameAlarmInhibit					INTEGER,
				omtp12PlusOtuLossOfMultiFrameAlarmInhibit				INTEGER,
				omtp12PlusOtuOutOfMultiFrameAlarmInhibit				INTEGER,
				omtp12PlusOtuSignalFailAlarmInhibit					INTEGER,
				omtp12PlusOtuSignalDegradeAlarmInhibit					INTEGER,
				omtp12PlusOtuAlarmIndicationSignalAlarmInhibit				INTEGER,
				omtp12PlusOtuIncomingAlignmentErrorAlarmInhibit				INTEGER,
				omtp12PlusOtuTraceIdentifierMismatchAlarmInhibit			INTEGER,
				omtp12PlusOtuBackwardIncomingAlignmentErrorAlarmInhibit			INTEGER,
				omtp12PlusOtuBackwardDefectIndicationAlarmInhibit			INTEGER,
				omtp12PlusOduSignalFailAlarmInhibit					INTEGER,
				omtp12PlusOduSignalDegradeAlarmInhibit					INTEGER,
				omtp12PlusOduAlarmIndicationSignalAlarmInhibit				INTEGER,
				omtp12PlusOduTcm1IncomingAlignmentErrorAlarmInhibit			INTEGER,
				omtp12PlusOduTcm2IncomingAlignmentErrorAlarmInhibit			INTEGER,
				omtp12PlusOduTcm3IncomingAlignmentErrorAlarmInhibit			INTEGER,
				omtp12PlusOduTcm4IncomingAlignmentErrorAlarmInhibit			INTEGER,
				omtp12PlusOduTcm5IncomingAlignmentErrorAlarmInhibit			INTEGER,
				omtp12PlusOduTcm6IncomingAlignmentErrorAlarmInhibit			INTEGER,
				omtp12PlusOduTraceIdentifierMismatchAlarmInhibit			INTEGER,
				omtp12PlusOduLockedDefectAlarmInhibit					INTEGER,
				omtp12PlusOduOpenConnectionIndicationAlarmInhibit			INTEGER,
				omtp12PlusOduBackwardDefectIndicationAlarmInhibit			INTEGER,
				omtp12PlusOduTcm1BackwardIncomingAlignmentErrorAlarmInhibit		INTEGER,
				omtp12PlusOduTcm2BackwardIncomingAlignmentErrorAlarmInhibit		INTEGER,
				omtp12PlusOduTcm3BackwardIncomingAlignmentErrorAlarmInhibit		INTEGER,
				omtp12PlusOduTcm4BackwardIncomingAlignmentErrorAlarmInhibit		INTEGER,
				omtp12PlusOduTcm5BackwardIncomingAlignmentErrorAlarmInhibit		INTEGER,
				omtp12PlusOduTcm6BackwardIncomingAlignmentErrorAlarmInhibit		INTEGER,
				omtp12PlusOpuPayloadMismatchAlarmInhibit				INTEGER,
				omtp12PlusOchLossOfPayloadAlarmInhibit					INTEGER,
				omtp12PlusSdhLossOfSignalAlarmInhibit					INTEGER,
				omtp12PlusSdhOutOfFrameAlarmInhibit					INTEGER,
				omtp12PlusSdhLossOfFrameAlarmInhibit					INTEGER,
				omtp12PlusSdhRsAlarmIndicationSignalAlarmInhibit			INTEGER,
				omtp12PlusSdhRsTraceIdentifierMismatchAlarmInhibit			INTEGER,
				omtp12PlusSdhAuAlarmIndicationSignalAlarmInhibit			INTEGER,
				omtp12PlusSdhAuLossOfPointerAlarmInhibit				INTEGER,
				omtp12PlusSdhMsAlarmIndicationSignalAlarmInhibit			INTEGER,
				omtp12PlusSdhMsRemoteErrorIndicationAlarmInhibit			INTEGER,
				omtp12PlusSdhMsRemoteDefectIndicationAlarmInhibit			INTEGER,
				omtp12PlusSdhMsRemoteFailureIndicationAlarmInhibit			INTEGER,
				omtp12PlusSdhMsB2ExcessiveErrorAlarmInhibit                             INTEGER,
				omtp12PlusSdhMsB2SignalDegradeAlarmInhibit				INTEGER,
				omtp12PlusSdhLossOfSequenceSynchronisationAlarmInhibit			INTEGER,
				omtp12PlusSdhHigherOrderPathPayloadLabelMismatchAlarmInhibit		INTEGER,
				omtp12PlusSdhHigherOrderPathUnequippedAlarmInhibit			INTEGER,
				omtp12PlusWan10gLossOfSignalAlarmInhibit				INTEGER,
				omtp12PlusWan10gOutOfFrameAlarmInhibit					INTEGER,
				omtp12PlusWan10gLossOfFrameAlarmInhibit					INTEGER,
				omtp12PlusWan10gRsAlarmIndicationSignalAlarmInhibit			INTEGER,
				omtp12PlusWan10gRsTraceIdentifierMismatchAlarmInhibit			INTEGER,
				omtp12PlusWan10gAuAlarmIndicationSignalAlarmInhibit			INTEGER,
				omtp12PlusWan10gAuLossOfPointerAlarmInhibit				INTEGER,
				omtp12PlusWan10gMsAlarmIndicationSignalAlarmInhibit			INTEGER,
				omtp12PlusWan10gMsRemoteErrorIndicationAlarmInhibit			INTEGER,
				omtp12PlusWan10gMsRemoteDefectIndicationAlarmInhibit			INTEGER,
				omtp12PlusWan10gMsRemoteFailureIndicationAlarmInhibit			INTEGER,
				omtp12PlusWan10gMsB2ExcessiveErrorAlarmInhibit				INTEGER,
				omtp12PlusWan10gMsB2SignalDegradeAlarmInhibit				INTEGER,
				omtp12PlusWan10gLossOfSequenceSynchronisationAlarmInhibit		INTEGER,
				omtp12PlusWan10gHigherOrderPathPayloadLabelMismatchAlarmInhibit		INTEGER,
				omtp12PlusWan10gHigherOrderPathUnequippedAlarmInhibit			INTEGER,
				omtp12PlusLan10gLossOfSignalAlarmInhibit				INTEGER,
				omtp12PlusLan10gLossOfSignalSyncAlarmInhibit				INTEGER,
				omtp12PlusLan10gLinkFailureAlarmInhibit					INTEGER,
				omtp12PlusLan10gFrameCheckSequenceAlarmInhibit				INTEGER,
				omtp12PlusLan10gCarrierStatusAlarmInhibit				INTEGER,
				omtp12PlusLan10gHighBerAlarmInhibit					INTEGER,
				omtp12PlusLan10gLocalFaultAlarmInhibit					INTEGER,
				omtp12PlusLan10gRemoteFaultAlarmInhibit					INTEGER,
				omtp12PlusFcTransmitDisparityInversionDefectAlarmInhibit		INTEGER,
				omtp12PlusFcTransmitDigitalLossOfLinkDefectAlarmInhibit			INTEGER,
				omtp12PlusFcTrasnmitLossofSynchronizationDefectAlarmInhibit		INTEGER,
				omtp12PlusFcReceiveDigitalLossofLinkDefectAlarmInhibit			INTEGER,
				omtp12PlusFcReceiveLossofSynchronizationDefectAlarmInhibit		INTEGER,
				omtp12PlusFcReceiveTransitionDetectDefectAlarmInhibit			INTEGER,
				omtp12PlusFcReceiveAnalogLossofSignalDefectAlarmInhibit			INTEGER,
				omtp12PlusFcReceiveLineCodeViolationDefectAlarmInhibit			INTEGER,
				omtp12PlusGfpCsfSignalFailAlarmInhibit					INTEGER,
				omtp12PlusGfpCsfLinkFailAlarmInhibit					INTEGER,
				omtp12PlusGfpCoreHeaderErrorAlarmInhibit				INTEGER,
				omtp12PlusGfpExtentionHeaderErrorAlarmInhibit				INTEGER,
				omtp12PlusXfpInputPowerFailureAlarmSeverity				DisplayString,
				omtp12PlusXfpOutputPowerFailureAlarmSeverity				DisplayString,
				omtp12PlusXfpHighTemperatureAlarmSeverity				DisplayString,
				omtp12PlusXfpLowTemperatureAlarmSeverity				DisplayString,
				omtp12PlusXfpHighTemperatureWarningSeverity				DisplayString,
				omtp12PlusXfpLowTemperatureWarningSeverity				DisplayString,
				omtp12PlusXfpHighBiasCurrentAlarmSeverity				DisplayString,
				omtp12PlusXfpLowBiasCurrentAlarmSeverity				DisplayString,
				omtp12PlusXfpHighBiasCurrentWarningSeverity				DisplayString,
				omtp12PlusXfpLowBiasCurrentWarningSeverity				DisplayString,
				omtp12PlusXfpInputHighPowerAlarmSeverity				DisplayString,
				omtp12PlusXfpInputLowPowerAlarmSeverity					DisplayString,
				omtp12PlusXfpInputHighPowerWarningSeverity				DisplayString,
				omtp12PlusXfpInputLowPowerWarningSeverity				DisplayString,
				omtp12PlusXfpOutputHighPowerAlarmSeverity				DisplayString,
				omtp12PlusXfpOutputLowPowerAlarmSeverity				DisplayString,
				omtp12PlusXfpOutputHighPowerWarningSeverity				DisplayString,
				omtp12PlusXfpOutputLowPowerWarningSeverity				DisplayString,
				omtp12PlusXfpHighSupplyVoltageAlarmSeverity				DisplayString,
				omtp12PlusXfpLowSupplyVoltageAlarmSeverity				DisplayString,
				omtp12PlusXfpHighSupplyVoltageWarningSeverity				DisplayString,
				omtp12PlusXfpLowSupplyVoltageWarningSeverity				DisplayString,
				omtp12PlusXfpPresenceAbsenceNotificationSeverity			DisplayString,
				omtp12PlusOtuLossOfSignalAlarmSeverity					DisplayString,
				omtp12PlusOtuLossOfFrameAlarmSeverity					DisplayString,
				omtp12PlusOtuOutOfFrameAlarmSeverity					DisplayString,
				omtp12PlusOtuLossOfMultiFrameAlarmSeverity				DisplayString,
				omtp12PlusOtuOutOfMultiFrameAlarmSeverity				DisplayString,
				omtp12PlusOtuSignalFailAlarmSeverity					DisplayString,
				omtp12PlusOtuSignalDegradeAlarmSeverity					DisplayString,
				omtp12PlusOtuAlarmIndicationSignalAlarmSeverity				DisplayString,
				omtp12PlusOtuIncomingAlignmentErrorAlarmSeverity			DisplayString,
				omtp12PlusOtuTraceIdentifierMismatchAlarmSeverity			DisplayString,
				omtp12PlusOtuBackwardIncomingAlignmentErrorAlarmSeverity		DisplayString,
				omtp12PlusOtuBackwardDefectIndicationAlarmSeverity			DisplayString,
				omtp12PlusOduSignalFailAlarmSeverity					DisplayString,
				omtp12PlusOduSignalDegradeAlarmSeverity					DisplayString,
				omtp12PlusOduAlarmIndicationSignalAlarmSeverity				DisplayString,
				omtp12PlusOduTcm1IncomingAlignmentErrorAlarmSeverity			DisplayString,
				omtp12PlusOduTcm2IncomingAlignmentErrorAlarmSeverity			DisplayString,
				omtp12PlusOduTcm3IncomingAlignmentErrorAlarmSeverity			DisplayString,
				omtp12PlusOduTcm4IncomingAlignmentErrorAlarmSeverity			DisplayString,
				omtp12PlusOduTcm5IncomingAlignmentErrorAlarmSeverity			DisplayString,
				omtp12PlusOduTcm6IncomingAlignmentErrorAlarmSeverity			DisplayString,
				omtp12PlusOduTraceIdentifierMismatchAlarmSeverity			DisplayString,
				omtp12PlusOduLockedDefectAlarmSeverity					DisplayString,
				omtp12PlusOduOpenConnectionIndicationAlarmSeverity			DisplayString,
				omtp12PlusOduBackwardDefectIndicationAlarmSeverity			DisplayString,
				omtp12PlusOduTcm1BackwardIncomingAlignmentErrorAlarmSeverity		DisplayString,
				omtp12PlusOduTcm2BackwardIncomingAlignmentErrorAlarmSeverity		DisplayString,
				omtp12PlusOduTcm3BackwardIncomingAlignmentErrorAlarmSeverity		DisplayString,
				omtp12PlusOduTcm4BackwardIncomingAlignmentErrorAlarmSeverity		DisplayString,
				omtp12PlusOduTcm5BackwardIncomingAlignmentErrorAlarmSeverity		DisplayString,
				omtp12PlusOduTcm6BackwardIncomingAlignmentErrorAlarmSeverity		DisplayString,
				omtp12PlusOpuPayloadMismatchAlarmSeverity				DisplayString,
				omtp12PlusOchLossOfPayloadAlarmSeverity					DisplayString,
				omtp12PlusSdhLossOfSignalAlarmSeverity					DisplayString,
				omtp12PlusSdhOutOfFrameAlarmSeverity					DisplayString,
				omtp12PlusSdhLossOfFrameAlarmSeverity					DisplayString,
				omtp12PlusSdhRsAlarmIndicationSignalAlarmSeverity			DisplayString,
				omtp12PlusSdhRsTraceIdentifierMismatchAlarmSeverity			DisplayString,
				omtp12PlusSdhAuAlarmIndicationSignalAlarmSeverity			DisplayString,
				omtp12PlusSdhAuLossOfPointerAlarmSeverity				DisplayString,
				omtp12PlusSdhMsAlarmIndicationSignalAlarmSeverity			DisplayString,
				omtp12PlusSdhMsRemoteErrorIndicationAlarmSeverity			DisplayString,
				omtp12PlusSdhMsRemoteDefectIndicationAlarmSeverity			DisplayString,
				omtp12PlusSdhMsRemoteFailureIndicationAlarmSeverity			DisplayString,
				omtp12PlusSdhMsB2ExcessiveErrorAlarmSeverity                            DisplayString,
				omtp12PlusSdhMsB2SignalDegradeAlarmSeverity				DisplayString,
				omtp12PlusSdhLossOfSequenceSynchronisationAlarmSeverity			DisplayString,
				omtp12PlusSdhHigherOrderPathPayloadLabelMismatchAlarmSeverity		DisplayString,
				omtp12PlusSdhHigherOrderPathUnequippedAlarmSeverity			DisplayString,
				omtp12PlusWan10gLossOfSignalAlarmSeverity				DisplayString,
				omtp12PlusWan10gOutOfFrameAlarmSeverity					DisplayString,
				omtp12PlusWan10gLossOfFrameAlarmSeverity				DisplayString,
				omtp12PlusWan10gRsAlarmIndicationSignalAlarmSeverity			DisplayString,
				omtp12PlusWan10gRsTraceIdentifierMismatchAlarmSeverity			DisplayString,
				omtp12PlusWan10gAuAlarmIndicationSignalAlarmSeverity			DisplayString,
				omtp12PlusWan10gAuLossOfPointerAlarmSeverity				DisplayString,
				omtp12PlusWan10gMsAlarmIndicationSignalAlarmSeverity			DisplayString,
				omtp12PlusWan10gMsRemoteErrorIndicationAlarmSeverity			DisplayString,
				omtp12PlusWan10gMsRemoteDefectIndicationAlarmSeverity			DisplayString,
				omtp12PlusWan10gMsRemoteFailureIndicationAlarmSeverity			DisplayString,
				omtp12PlusWan10gMsB2ExcessiveErrorAlarmSeverity				DisplayString,
				omtp12PlusWan10gMsB2SignalDegradeAlarmSeverity				DisplayString,
				omtp12PlusWan10gLossOfSequenceSynchronisationAlarmSeverity		DisplayString,
				omtp12PlusWan10gHigherOrderPathPayloadLabelMismatchAlarmSeverity	DisplayString,            
				omtp12PlusWan10gHigherOrderPathUnequippedAlarmSeverity			DisplayString,
				omtp12PlusLan10gLossOfSignalAlarmSeverity				DisplayString,
				omtp12PlusLan10gLossOfSignalSyncAlarmSeverity				DisplayString,
				omtp12PlusLan10gLinkFailureAlarmSeverity				DisplayString,
				omtp12PlusLan10gFrameCheckSequenceAlarmSeverity				DisplayString,
				omtp12PlusLan10gCarrierStatusAlarmSeverity				DisplayString,
				omtp12PlusLan10gHighBerAlarmSeverity					DisplayString,
				omtp12PlusLan10gLocalFaultAlarmSeverity					DisplayString,
				omtp12PlusLan10gRemoteFaultAlarmSeverity				DisplayString,
				omtp12PlusFcTransmitDisparityInversionDefectAlarmSeverity		DisplayString,
				omtp12PlusFcTransmitDigitalLossOfLinkDefectAlarmSeverity		DisplayString,
				omtp12PlusFcTrasnmitLossofSynchronizationDefectAlarmSeverity		DisplayString,
				omtp12PlusFcReceiveDigitalLossofLinkDefectAlarmSeverity			DisplayString,
				omtp12PlusFcReceiveLossofSynchronizationDefectAlarmSeverity		DisplayString,
				omtp12PlusFcReceiveTransitionDetectDefectAlarmSeverity			DisplayString,
				omtp12PlusFcReceiveAnalogLossofSignalDefectAlarmSeverity		DisplayString,
				omtp12PlusFcReceiveLineCodeViolationDefectAlarmSeverity			DisplayString,
				omtp12PlusGfpCsfSignalFailAlarmSeverity					DisplayString,
				omtp12PlusGfpCsfLinkFailAlarmSeverity					DisplayString,
				omtp12PlusGfpCoreHeaderErrorAlarmSeverity				DisplayString,
				omtp12PlusGfpExtentionHeaderErrorAlarmSeverity				DisplayString,
				omtp12PlusConfigurationTableRowStatus					RowStatus
		}
		
	omtp12PlusCardSoftwareUpgrade OBJECT-TYPE
		SYNTAX DisplayString
		MAX-ACCESS read-write
		STATUS current
		DESCRIPTION
			"Valid only as SET command.
			This property upgrades the software of the OMTP12-PLUS card
			It takes the path of the software release as
			a value
			-----------------------------
			omtp12PlusInterfaceNumber: 0
			-----------------------------
			Values:
			eg: /root/home/rel-2.0.0.tar.gz
			-----------------------------"

		::= { omtp12PlusConfigurationEntry 1 }
		
	omtp12PlusCardSignalMonitorState OBJECT-TYPE
		SYNTAX INTEGER
		MAX-ACCESS read-write
		STATUS current
		DESCRIPTION
			"This property sets or gets the card's signal
			monitoring state. Disabling card signal monitoring 
			will not provide any signal alarms and performances
			information to the user.
			-----------------------------
			omtp12PlusInterfaceNumber: 0
			-----------------------------
			Values:
			1 - Card Signal Monitoring is enabled
			0 - Card Signal Monitoring is disabled
			-----------------------------"
		::= { omtp12PlusConfigurationEntry 2 }

	omtp12PlusCardOpticalMonitorState OBJECT-TYPE
		SYNTAX INTEGER
		MAX-ACCESS read-write
		STATUS current
		DESCRIPTION
			"This property sets or gets the card's optical
			monitoring state. Disabling card signal monitoring 
			will not provide any signal alarms and performances
			information to the user.
			-----------------------------
			omtp12PlusInterfaceNumber: 0
			-----------------------------
			Values:
			1 - Card Optical Monitoring is enabled
			0 - Card Optical Monitoring is disabled
			-----------------------------"
		::= { omtp12PlusConfigurationEntry 3 }
		
	omtp12PlusCardSoftReset OBJECT-TYPE
		SYNTAX INTEGER
		MAX-ACCESS read-write
		STATUS current
		DESCRIPTION
			"Valid only as a SET command.
			Reboots the Card, Reconfigures the Card 
			i.e All Configuration Parameter	like Laser State,
			Traffic configuration, Loopback, FEC, optical and 
			signal thresholds, switching mode,
			user choice of line path, TTI messages
			will be restored to previous state
			-----------------------------
			omtp12PlusInterfaceNumber: 0
			-----------------------------
			Values:
			Dont care, any value
			eg: 0
			-----------------------------"
		::= { omtp12PlusConfigurationEntry 4 }
		
	omtp12PlusCardFactoryReset OBJECT-TYPE
		SYNTAX INTEGER
		MAX-ACCESS read-write
		STATUS current
		DESCRIPTION
			"Valid only as a SET command.
			Sets the Card To Factory Default State
			i.e All User Configuration Parameters like Laser State,
			Traffic configuration, Loopback, FEC, optical and 
			signal thresholds, switching mode,
			user choice of line path, TTI messages
			will be set to default state
			-----------------------------
			omtp12PlusInterfaceNumber: 0
			-----------------------------
			Values:
			Dont care, any value
			eg: 0
			-----------------------------"
		::= { omtp12PlusConfigurationEntry 5 }
		
	omtp12PlusCardAccessStatus OBJECT-TYPE
		SYNTAX INTEGER
		MAX-ACCESS read-write
		STATUS current
		DESCRIPTION
			"This property will tell whether the card is 
			accessible from EMS/LCT or not. Turning off the
			accessbility to the card, will not allow the user
			to access any configuration, alarm or performance
			of the card and also turns off fast alarm
			triggering, global alarm led indication
			-----------------------------
			omtp12PlusInterfaceNumber: 0
			-----------------------------
			Values:
			1 - Card is accessible from EMS/LCT
			0 - Card is inaccessible from EMS/LCT
			-----------------------------"
		::= { omtp12PlusConfigurationEntry 6 }

	omtp12PlusSyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that ilarticular server. 
					If we are not providing NTP server IP address 
					then the system will be synced with the NTP server 
					which is already been registered with card. 
					If both are absent then error message will be returned
					-----------------------------
						Interface : 0
					-----------------------------
						If we want to provide NTP server IP address then
						Value should be a valid IP address as shown below
						: 192.168.21.25
						
						If we don't want to provide NTP server address then no
						need to pass any value. 
					---------------------------"
  						
  		::= { omtp12PlusConfigurationEntry 7 }
  		
  	omtp12PlusSyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 192.168.21.25
							
						If we don't want to provide NTP server address, then no
						need to ilass any value. 
						---------------------------"
  						
  		::= { omtp12PlusConfigurationEntry 8 }
  		
  	omtp12PlusSyncRtcWithSystemTime	 OBJECT-TYPE
		SYNTAX  		DisplayString
  		MAX-ACCESS  	read-write
  		STATUS  		current
  		DESCRIPTION	 	" when we want to manually sync the time value
  						present in RTC with the time value in linux kernel
  						we can use this OID. With this set operation, 
  						the time available with linux kernel will be updated
  						into RTC. It is not required to provide any value for 
  						this operation"
  						
  		::= { omtp12PlusConfigurationEntry 9 }
  		
  	omtp12PlusUpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2017-10-31 15:20:44
						---------------------------"
						
  		::= { omtp12PlusConfigurationEntry 10 }
  		
  	omtp12PlusUpdateGivenTimeIntoRtc	 OBJECT-TYPE
		SYNTAX  		DisplayString
  		MAX-ACCESS  	read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD H:M:S
						
						Example: 2017-10-31 15:20:44
						---------------------------"
						
  		::= { omtp12PlusConfigurationEntry 11 }
  		
  	omtp12PlusSystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { omtp12PlusConfigurationEntry 12 }

	omtp12PlusApsLinePathSwitchingMode OBJECT-TYPE
		SYNTAX INTEGER
		MAX-ACCESS read-write
		STATUS current
		DESCRIPTION
			"Set or Get the line path switching mode.
			-----------------------------
			omtp12PlusInterfaceNumber: 0
			-----------------------------
			Values:
			1 - Automatic mode of switching
			Keeps monitoring for OTU2-LOF periodically and switch to
			the secondary line path once LOF detected on the primary line path
			2 - Manual mode of switching
			The working path will be as per the user's choice
			of line path. Does not switch to the alternate path
			even though OTU2-LOF is present.
			-----------------------------"
		::= { omtp12PlusConfigurationEntry 21 }

	omtp12PlusApsUserChoiceOfLinePath OBJECT-TYPE
		SYNTAX INTEGER
		MAX-ACCESS read-write
		STATUS current
		DESCRIPTION
			"Set or Get the user's choice of line path.
			Valid only when 'omtp12PlusApsLinePathSwitchingMode' is set to
			Manual Mode. In manual mode, user has the previlege to
			set the LINE-1/LINE-2 as the working path
			-----------------------------
			omtp12PlusInterfaceNumber: 0
			-----------------------------
			Values:
			2 - LINE-1 as working path
			3 - LINE-2 as working path
			-----------------------------"
		::= { omtp12PlusConfigurationEntry 22 }
		
	omtp12PlusApsCurrentOperationalLinePath OBJECT-TYPE
		SYNTAX INTEGER
		MAX-ACCESS read-only
		STATUS current
		DESCRIPTION
			"Get the currently operational working path
			between LINE-1/LINE-2
			-----------------------------
			omtp12PlusInterfaceNumber: 0
			-----------------------------
			Values:
			2 - LINE-1 as working path
			3 - LINE-2 as working path
			-----------------------------"
		::= { omtp12PlusConfigurationEntry 23 }

	omtp12PlusTrafficConfiguration OBJECT-TYPE
		SYNTAX INTEGER
		MAX-ACCESS read-write
		STATUS current
		DESCRIPTION
			"Set or get the traffic configuration for the
			requested port
			-----------------------------
			omtp12PlusInterfaceNumber:
			1 - CLIENT-1
			2 - LINE-1
			3 - LINE-2
			-----------------------------
			Values: 
			00 - Un-configure
			01 - STM64
			02 - WAN10G
			04 - LAN10G
			06 - OTU2
			-----------------------------"
		::= { omtp12PlusConfigurationEntry 41 }
		
	omtp12PlusLoopbackState OBJECT-TYPE
		SYNTAX INTEGER
		MAX-ACCESS read-write
		STATUS current
		DESCRIPTION
			"Set or get the loopback state for the
			requested port
			-----------------------------
			omtp12PlusInterfaceNumber:
			1 - CLIENT-1
			2 - LINE-1
			3 - LINE-2
			-----------------------------
			Values: 
			00 - No Loopback   
			01 - Near End Loopback
			02 - Far End Loopback
			-----------------------------"
		::= { omtp12PlusConfigurationEntry 42 }
		
	omtp12PlusPortSignalMonitorState OBJECT-TYPE
		SYNTAX INTEGER
		MAX-ACCESS read-write
		STATUS current
		DESCRIPTION
			"This property sets or gets the port's signal
			monitoring state. Disabling port signal monitoring 
			will not provide any signal alarms and performances
			information to the user.
			-----------------------------
			omtp12PlusInterfaceNumber:
			1 - CLIENT-1
			2 - LINE-1
			3 - LINE-2
			-----------------------------
			Values:
			1 - Port Signal Monitoring is enabled
			0 - Port Signal Monitoring is disabled
			-----------------------------"

		::= { omtp12PlusConfigurationEntry 43 }
		
	omtp12PlusPortOpticalMonitorState OBJECT-TYPE
		SYNTAX INTEGER
		MAX-ACCESS read-write
		STATUS current
		DESCRIPTION
			"This property sets or gets the port's optical
			monitoring state. Disabling port optical monitoring 
			will not provide any optical alarms and performances
			information to the user.
			-----------------------------
			omtp12PlusInterfaceNumber:
			1 - CLIENT-1
			2 - LINE-1
			3 - LINE-2
			-----------------------------
			Values:
			1 - Port Optical Monitoring is enabled
			0 - Port Optical Monitoring is disabled
			-----------------------------"
		::= { omtp12PlusConfigurationEntry 44 }

	omtp12PlusClearSignalPerformance OBJECT-TYPE
		SYNTAX INTEGER
		MAX-ACCESS read-write
		STATUS current
		DESCRIPTION
			"Valid only as a SET command.
			Clears signal performance for the requested port
			-----------------------------
			omtp12PlusInterfaceNumber:
			1 - CLIENT-1
			2 - LINE-1
			3 - LINE-2
			-----------------------------
			Values:
			Dont care, any value
			eg: 0
			-----------------------------"
		::= { omtp12PlusConfigurationEntry 45 }
		
	omtp12PlusAlsState OBJECT-TYPE
		SYNTAX INTEGER
		MAX-ACCESS read-write
		STATUS current
		DESCRIPTION
			"Set the Automatic Laser Switching(ALS) mode for
			for requested port. Based on the RX LOS state of the
			port, the transmit LASER state will be controlled
			according to the algorithm defined for ALS in
			ITUT 664 Standard
			-----------------------------
			omtp12PlusInterfaceNumber:
			1 - CLIENT-1
			2 - LINE-1
			3 - LINE-2
			-----------------------------
			Values: 
			1 - Enable ALS state
			0 - Disable ALS state
			-----------------------------" 
		::= { omtp12PlusConfigurationEntry 46 }
		
	omtp12PlusAlsPulseRepetitionTime OBJECT-TYPE
		SYNTAX INTEGER
		MAX-ACCESS read-write
		STATUS current
		DESCRIPTION
			"Pulse repetition time is the time for automatic 
			restart of XFP LASER once the ALS algorithm starts.
			-----------------------------
			omtp12PlusInterfaceNumber:
			1 - CLIENT-1
			2 - LINE-1
			3 - LINE-2
			-----------------------------
			Values: 
			100 seconds to 300 seconds
			-----------------------------" 
		::= { omtp12PlusConfigurationEntry 47 }
		
	omtp12PlusOtuFecConfiguration OBJECT-TYPE
		SYNTAX INTEGER
		MAX-ACCESS read-write
		STATUS current
		DESCRIPTION
			"Set or Get FEC type for requested port configured with
			 OTU2 traffic.
			-----------------------------
			omtp12PlusInterfaceNumber:
			1 - CLIENT-1
			2 - LINE-1
			3 - LINE-2
			-----------------------------
			Values: 
			00 - UFEC (I.7 FEC)
			13 - Reed-Solomon GFEC
			14 - Zero FEC 
			-----------------------------" 
		::= { omtp12PlusConfigurationEntry 61 }

	omtp12PlusOtuSignalFailThreshold OBJECT-TYPE
		SYNTAX INTEGER
		MAX-ACCESS read-write
		STATUS current
		DESCRIPTION
			"Set or Get SM Signal Failure 
			Threshold value for the requested port configured with 
			OTU2 traffic.
			-----------------------------
			omtp12PlusInterfaceNumber:
			1 - CLIENT-1
			2 - LINE-1
			3 - LINE-2
			-----------------------------
			Values: 
			03 - 1.E -03
			04 - 1.E -04
			05 - 1.E -05
			-----------------------------" 
		::= { omtp12PlusConfigurationEntry 62 }
		
	omtp12PlusOtuSignalDegradeThreshold OBJECT-TYPE
		SYNTAX INTEGER
		MAX-ACCESS read-write
		STATUS current
		DESCRIPTION
			"Set or Get SM Signal Degrade 
			Threshold value for the requested port configured with 
			OTU2 traffic.
			-----------------------------
			omtp12PlusInterfaceNumber:
			1 - CLIENT-1
			2 - LINE-1
			3 - LINE-2
			-----------------------------
			Values:
			05 - 1.E -05
			06 - 1.E -06
			07 - 1.E -07
			08 - 1.E -08
			09 - 1.E -09
			10 - 1.E -10
			-----------------------------" 
		::= { omtp12PlusConfigurationEntry 63 }
		
	omtp12PlusOtuAlarmIndicationSignalAlarmInsertion OBJECT-TYPE
		SYNTAX INTEGER
		MAX-ACCESS read-write
		STATUS current
		DESCRIPTION
			"Inserts OTU-AIS maitainance signal for the requested
			port configured with OTU2 traffic.
			-----------------------------
			omtp12PlusInterfaceNumber:
			1 - CLIENT-1
			2 - LINE-1
			3 - LINE-2
			-----------------------------
			Values: 
			0 - Disable Insertion  
			1 - Enable Insertion
			-----------------------------" 
		::= { omtp12PlusConfigurationEntry 64 }
		
	omtp12PlusOtuSapiTransmitTraceMessage OBJECT-TYPE
		SYNTAX DisplayString
		MAX-ACCESS read-write
		STATUS current
		DESCRIPTION
			"Set or get the 15 characters SAPI Transmit TTI message
			which is put into the outgoing OTU2 frame. 
			-----------------------------
			omtp12PlusInterfaceNumber:
			1 - CLIENT-1
			2 - LINE-1
			3 - LINE-2
			-----------------------------
			Values:
			eg: 123451234512345
			-----------------------------" 
		::= { omtp12PlusConfigurationEntry 65 }

	omtp12PlusOtuDapiTransmitTraceMessage OBJECT-TYPE
		SYNTAX DisplayString
		MAX-ACCESS read-write
		STATUS current
		DESCRIPTION
			"Set or get the 15 characters DAPI Transmit TTI message
			which is put into the outgoing OTU2 frame. 
			-----------------------------
			omtp12PlusInterfaceNumber:
			1 - CLIENT-1
			2 - LINE-1
			3 - LINE-2
			-----------------------------
			Values:
			eg: 123451234512345
			-----------------------------" 
		::= { omtp12PlusConfigurationEntry 66 }
		
	omtp12PlusOtuOperatorSpecificTransmitTraceMessage OBJECT-TYPE
		SYNTAX DisplayString
		MAX-ACCESS read-write
		STATUS current
		DESCRIPTION
			"Set or get the 32 characters Operator Specific Transmit
			TTI message which is put into the outgoing OTU2 frame. 
			-----------------------------
			omtp12PlusInterfaceNumber:
			1 - CLIENT-1
			2 - LINE-1
			3 - LINE-2
			-----------------------------
			Values:
			eg: 12345123451234512345123451234500
			-----------------------------" 
		::= { omtp12PlusConfigurationEntry 67 }
		
	omtp12PlusOtuSapiExpectedTraceMessage OBJECT-TYPE
		SYNTAX DisplayString
		MAX-ACCESS read-write
		STATUS current
		DESCRIPTION
			"15 characters SM SAPI Expected TTI message - Message
			set here is used for comparison with the message present
			in SM SAPI field of the incoming OTU2 frames.
			-----------------------------
			omtp12PlusInterfaceNumber:
			1 - CLIENT-1
			2 - LINE-1
			3 - LINE-2
			-----------------------------
			Values:
			eg: 123451234512345
			-----------------------------" 
		::= { omtp12PlusConfigurationEntry 68 }
		
	omtp12PlusOtuDapiExpectedTraceMessage OBJECT-TYPE
		SYNTAX DisplayString
		MAX-ACCESS read-write
		STATUS current
		DESCRIPTION
			"15 characters SM DAPI Expected TTI message - Message
			set here is used for comparison with the message present
			in SM DAPI field of the incoming OTU2 frames.
			-----------------------------
			omtp12PlusInterfaceNumber:
			1 - CLIENT-1
			2 - LINE-1
			3 - LINE-2
			-----------------------------
			Values:
			eg: 123451234512345
			-----------------------------" 
		::= { omtp12PlusConfigurationEntry 69 }

	omtp12PlusOtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU2 frames.
			-----------------------------
			omtp12PlusInterfaceNumber:
			1 - CLIENT-1
			2 - LINE-1
			3 - LINE-2
			-----------------------------
			Values:
			eg: 12345123451234512345123451234500
			-----------------------------" 
		::= { omtp12PlusConfigurationEntry 70 }
		
	omtp12PlusOtuSapiReceivedTraceMessage OBJECT-TYPE
		SYNTAX DisplayString
		MAX-ACCESS read-only
		STATUS current
		DESCRIPTION
			"Gets the 15 characters SAPI TTI message
			which is extracted from the incoming OTU2
			data stream.
			-----------------------------
			omtp12PlusInterfaceNumber:
			1 - CLIENT-1
			2 - LINE-1
			3 - LINE-2
			-----------------------------
			Values:
			eg: 123451234512345
			-----------------------------" 
		::= { omtp12PlusConfigurationEntry 71 }

	omtp12PlusOtuDapiReceivedTraceMessage OBJECT-TYPE
		SYNTAX DisplayString
		MAX-ACCESS read-only
		STATUS current
		DESCRIPTION
			"Gets the 15 characters DAPI TTI message
			which is extracted from the incoming OTU2 data
			stream.
			-----------------------------
			omtp12PlusInterfaceNumber:
			1 - CLIENT-1
			2 - LINE-1
			3 - LINE-2
			-----------------------------
			Values:
			eg: 123451234512345
			-----------------------------" 
		::= { omtp12PlusConfigurationEntry 72 }
		
	omtp12PlusOtuOperatorSpecificReceivedTraceMessage OBJECT-TYPE
		SYNTAX DisplayString
		MAX-ACCESS read-only
		STATUS current
		DESCRIPTION
			"Gets the 32 characters DAPI TTI message
			which is extracted from the incoming OTU2 data
			stream. 
			-----------------------------
			omtp12PlusInterfaceNumber:
			1 - CLIENT-1
			2 - LINE-1
			3 - LINE-2
			-----------------------------
			Values:
			eg: 12345123451234512345123451234500
			-----------------------------" 
		::= { omtp12PlusConfigurationEntry 73 }

	omtp12PlusOduSignalFailThreshold OBJECT-TYPE
		SYNTAX INTEGER
		MAX-ACCESS read-write
		STATUS current
		DESCRIPTION
			"Set or Get PM Signal Failure 
			Threshold value for the requested port configured with 
			OTU2 traffic.
			-----------------------------
			omtp12PlusInterfaceNumber:
			1 - CLIENT-1
			2 - LINE-1
			3 - LINE-2
			-----------------------------
			Values: 
			03 - 1.E -03
			04 - 1.E -04
			05 - 1.E -05
			-----------------------------" 
		::= { omtp12PlusConfigurationEntry 81 }
		
	omtp12PlusOduSignalDegradeThreshold OBJECT-TYPE
		SYNTAX INTEGER
		MAX-ACCESS read-write
		STATUS current
		DESCRIPTION
			"Set or Get PM Signal Degrade 
			Threshold value for the requested port configured with 
			OTU2 traffic.
			-----------------------------
			omtp12PlusInterfaceNumber:
			1 - CLIENT-1
			2 - LINE-1
			3 - LINE-2
			-----------------------------
			Values:
			05 - 1.E -05
			06 - 1.E -06
			07 - 1.E -07
			08 - 1.E -08
			09 - 1.E -09
			10 - 1.E -10
			-----------------------------" 
		::= { omtp12PlusConfigurationEntry 82 }
		
	omtp12PlusOduAlarmIndicationSignalAlarmInsertion OBJECT-TYPE
		SYNTAX INTEGER
		MAX-ACCESS read-write
		STATUS current
		DESCRIPTION
			"Inserts ODU-AIS maintenance signal for the requested 
			port configured with OTU2 traffic.
			-----------------------------
			omtp12PlusInterfaceNumber:
			1 - CLIENT-1
			2 - LINE-1
			3 - LINE-2
			-----------------------------
			Values: 
			1 - Enable Insertion
			0 - Disable Insertion  
			-----------------------------"
		::= { omtp12PlusConfigurationEntry 83 }

	omtp12PlusOduLockedDefectAlarmInsertion OBJECT-TYPE
		SYNTAX INTEGER
		MAX-ACCESS read-write
		STATUS current
		DESCRIPTION
			"Inserts ODU-LCK maintenance signal for the requested 
			port configured with OTU2 traffic.
			-----------------------------
			omtp12PlusInterfaceNumber:
			1 - CLIENT-1
			2 - LINE-1
			3 - LINE-2
			-----------------------------
			Values: 
			1 - Enable Insertion
			0 - Disable Insertion  
			-----------------------------"
		::= { omtp12PlusConfigurationEntry 84 }
		
	omtp12PlusOduOpenConnectionIndicationAlarmInsertion OBJECT-TYPE
		SYNTAX INTEGER
		MAX-ACCESS read-write
		STATUS current
		DESCRIPTION
			"Inserts ODU-OCI maintenance signal for the requested 
			port configured with OTU2 traffic.
			-----------------------------
			omtp12PlusInterfaceNumber:
			1 - CLIENT-1
			2 - LINE-1
			3 - LINE-2
			-----------------------------
			Values: 
			1 - Enable Insertion
			0 - Disable Insertion  
			-----------------------------"
		::= { omtp12PlusConfigurationEntry 85 }
		
	omtp12PlusOduSapiTransmitTraceMessage OBJECT-TYPE
		SYNTAX DisplayString
		MAX-ACCESS read-write
		STATUS current
		DESCRIPTION
			"Set or get the 15 characters SAPI Transmit TTI message
			which is put into the outgoing OTU2 frame at the PM level. 
			-----------------------------
			omtp12PlusInterfaceNumber:
			1 - CLIENT-1
			2 - LINE-1
			3 - LINE-2
			-----------------------------
			Values:
			eg: 123451234512345
			-----------------------------" 
		::= { omtp12PlusConfigurationEntry 86 }
		
	omtp12PlusOduDapiTransmitTraceMessage OBJECT-TYPE
		SYNTAX DisplayString
		MAX-ACCESS read-write
		STATUS current
		DESCRIPTION
			"Set or get the 15 characters DAPI Transmit TTI message
			which is put into the outgoing OTU2 frame at the PM level. 
			-----------------------------
			omtp12PlusInterfaceNumber:
			1 - CLIENT-1
			2 - LINE-1
			3 - LINE-2
			-----------------------------
			Values:
			eg: 123451234512345
			-----------------------------" 
		::= { omtp12PlusConfigurationEntry 87 }
		
	omtp12PlusOduOperatorSpecificTransmitTraceMessage OBJECT-TYPE
		SYNTAX DisplayString
		MAX-ACCESS read-write
		STATUS current
		DESCRIPTION
			"Set or get the 32 characters Operator Specific Transmit
			TTI message which is put into the outgoing OTU2 frame at
			the PM level. 
			-----------------------------
			omtp12PlusInterfaceNumber:
			1 - CLIENT-1
			2 - LINE-1
			3 - LINE-2
			-----------------------------
			Values:
			eg: 12345123451234512345123451234500
			-----------------------------" 
		::= { omtp12PlusConfigurationEntry 88 }
		
	omtp12PlusOduSapiExpectedTraceMessage OBJECT-TYPE
		SYNTAX DisplayString
		MAX-ACCESS read-write
		STATUS current
		DESCRIPTION
			"15 characters PM SAPI Expected TTI message - Message
			set here is used for comparison with the message present
			in PM SAPI field of the incoming OTU2 frames.
			-----------------------------
			omtp12PlusInterfaceNumber:
			1 - CLIENT-1
			2 - LINE-1
			3 - LINE-2
			-----------------------------
			Values:
			eg: 123451234512345
			-----------------------------" 
		::= { omtp12PlusConfigurationEntry 89 }

	omtp12PlusOduDapiExpectedTraceMessage OBJECT-TYPE
		SYNTAX DisplayString
		MAX-ACCESS read-write
		STATUS current
		DESCRIPTION
			"15 characters PM DAPI Expected TTI message - Message
			set here is used for comparison with the message present
			in PM DAPI field of the incoming OTU2 frames.
			-----------------------------
			omtp12PlusInterfaceNumber:
			1 - CLIENT-1
			2 - LINE-1
			3 - LINE-2
			-----------------------------
			Values:
			eg: 123451234512345
			-----------------------------" 
		::= { omtp12PlusConfigurationEntry 90 }
		
	omtp12PlusOduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU2 frames.
			-----------------------------
			omtp12PlusInterfaceNumber:
			1 - CLIENT-1
			2 - LINE-1
			3 - LINE-2
			-----------------------------
			Values:
			eg: 12345123451234512345123451234500
			-----------------------------" 
		::= { omtp12PlusConfigurationEntry 91 }

	omtp12PlusOduSapiReceivedTraceMessage OBJECT-TYPE
		SYNTAX DisplayString
		MAX-ACCESS read-only
		STATUS current
		DESCRIPTION
			"Gets the 15 characters SAPI TTI message
			which is extracted from the incoming OTU2 data
			stream.
			-----------------------------
			omtp12PlusInterfaceNumber:
			1 - CLIENT-1
			2 - LINE-1
			3 - LINE-2
			-----------------------------
			Values:
			eg: 123451234512345
			-----------------------------" 
		::= { omtp12PlusConfigurationEntry 92 }

	omtp12PlusOduDapiReceivedTraceMessage OBJECT-TYPE
		SYNTAX DisplayString
		MAX-ACCESS read-only
		STATUS current
		DESCRIPTION
			"Gets the 15 characters DAPI TTI message
			which is extracted from the incoming OTU2
			data stream.
			-----------------------------
			omtp12PlusInterfaceNumber:
			1 - CLIENT-1
			2 - LINE-1
			3 - LINE-2
			-----------------------------
			Values:
			eg: 123451234512345
			-----------------------------" 
		::= {omtp12PlusConfigurationEntry 93 }
		
	omtp12PlusOduOperatorSpecificReceivedTraceMessage OBJECT-TYPE
		SYNTAX DisplayString
		MAX-ACCESS read-only
		STATUS current
		DESCRIPTION
			"Gets the 32 characters DAPI TTI message
			which is extracted from the incoming OTU2
			data stream.
			-----------------------------
			omtp12PlusInterfaceNumber:
			1 - CLIENT-1
			2 - LINE-1
			3 - LINE-2
			-----------------------------
			Values:
			eg: 12345123451234512345123451234500
			-----------------------------" 
		::= { omtp12PlusConfigurationEntry 94 }

	omtp12PlusOpuTransmitPayloadType OBJECT-TYPE
		SYNTAX INTEGER
		MAX-ACCESS read-only
		STATUS current
		DESCRIPTION
			"A one-byte payload type signal is defined in the PSI[0]
			byte of the payload structure identifier to indicate the
			composition of the OPUk signal. Gets the payload type
			that is put into the outgoing OTU2 datastream.
			-----------------------------
			omtp12PlusInterfaceNumber:
			1 - CLIENT-1
			2 - LINE-1
			3 - LINE-2
			-----------------------------
			Values:
			eg: 20
			-----------------------------" 
		::= { omtp12PlusConfigurationEntry 95 }
		
	omtp12PlusOpuReceivedPayloadType OBJECT-TYPE
		SYNTAX INTEGER
		MAX-ACCESS read-only
		STATUS current
		DESCRIPTION
			"Gives Payload Type present in Opu overhead that tells
			about the mapping informations.
			-----------------------------
			omtp12PlusInterfaceNumber:
			1 - CLIENT-1
			2 - LINE-1
			3 - LINE-2
			-----------------------------
			Values:
			eg: 21
			-----------------------------" 
		::= { omtp12PlusConfigurationEntry 96 }
		
	omtp12PlusSdhMsB2ExcessiveErrorThreshold OBJECT-TYPE
		SYNTAX INTEGER
		MAX-ACCESS read-write
		STATUS current
		DESCRIPTION
			"Set or Get B2 Signal Failure Threshold value for the 
			requested port configured with SDH traffic.
			-----------------------------
			omtp12PlusInterfaceNumber:
			1 - CLIENT-1
			-----------------------------
			Values:
			03 - 1.E -03
			04 - 1.E -04
			05 - 1.E -05
			-----------------------------" 
		::= { omtp12PlusConfigurationEntry 101 }

	omtp12PlusSdhMsB2SignalDegradeThreshold OBJECT-TYPE
		SYNTAX INTEGER
		MAX-ACCESS read-write
		STATUS current
		DESCRIPTION
			"Set or Get B2 Signal Degrade Threshold value for the 
			requested port configured with SDH traffic.
			-----------------------------
			omtp12PlusInterfaceNumber:
			1 - CLIENT-1
			-----------------------------
			Values:
			06 - 1.E -06
			07 - 1.E -07
			08 - 1.E -08
			09 - 1.E -09
			10 - 1.E -10
			-----------------------------" 
		::= { omtp12PlusConfigurationEntry 102 }
		
	omtp12PlusWan10gMsB2ExcessiveErrorThreshold OBJECT-TYPE
		SYNTAX INTEGER
		MAX-ACCESS read-write
		STATUS current
		DESCRIPTION
			"Set or Get B2 Signal Failure Threshold value for the 
			requested port configured with WAN traffic.
			-----------------------------
			omtp12PlusInterfaceNumber:
			1 - CLIENT-1
			-----------------------------
			Values:
			03 - 1.E -03
			04 - 1.E -04
			05 - 1.E -05
			-----------------------------" 

		::= { omtp12PlusConfigurationEntry 111 }
		
	omtp12PlusWan10gMsB2SignalDegradeThreshold OBJECT-TYPE
		SYNTAX INTEGER
		MAX-ACCESS read-write
		STATUS current
		DESCRIPTION
			"Set or Get B2 Signal Degrade Threshold value for the 
			requested port configured with WAN traffic.
			-----------------------------
			omtp12PlusInterfaceNumber:
			1 - CLIENT-1
			-----------------------------
			Values:
			06 - 1.E -06
			07 - 1.E -07
			08 - 1.E -08
			09 - 1.E -09
			10 - 1.E -10
			-----------------------------" 
		::= { omtp12PlusConfigurationEntry 112 }
				
	omtp12PlusTunableXfpLaserWavelength OBJECT-TYPE
		SYNTAX INTEGER
		MAX-ACCESS read-write
		STATUS current
		DESCRIPTION
			"Set or Get the XFP wavelength for the requested port
			-----------------------------
			omtp12PlusInterfaceNumber:
			1 - CLIENT-1
			2 - LINE-1
			3 - LINE-2
			-----------------------------
			Values:
			eg: 1529.944
			-----------------------------" 
		::= { omtp12PlusConfigurationEntry 113 }
		
	omtp12PlusTunableXfpLaserChannelNumber OBJECT-TYPE
		SYNTAX INTEGER
		MAX-ACCESS read-write
		STATUS current
		DESCRIPTION
			"Set or Get the XFP Channel Number for the the requested
			port
			-----------------------------
			omtp12PlusInterfaceNumber:
			1 - CLIENT-1
			2 - LINE-1
			3 - LINE-2
			-----------------------------
			Values:
			eg: 10
			-----------------------------" 
		::= { omtp12PlusConfigurationEntry 114 }

	omtp12PlusXfpLaserState OBJECT-TYPE
		SYNTAX INTEGER
		MAX-ACCESS read-write
		STATUS current
		DESCRIPTION
			"Set or Get the XFP LASER state for the the requested
			port
			-----------------------------
			omtp12PlusInterfaceNumber:
			1 - CLIENT-1
			2 - LINE-1
			3 - LINE-2
			-----------------------------
			Values: 
			00 - Laser OFF
			01 - Laser ON
			-----------------------------" 
		::= { omtp12PlusConfigurationEntry 115 }
		
	omtp12PlusXfpReset OBJECT-TYPE
		SYNTAX INTEGER
		MAX-ACCESS read-write
		STATUS current
		DESCRIPTION
			"Valid only as a SET command.
			Resets the XFP.
			-----------------------------
			omtp12PlusInterfaceNumber:
			1 - CLIENT-1
			2 - LINE-1
			3 - LINE-2
			-----------------------------
			Values: 
			Dont care, any value
			eg: 0
			-----------------------------" 
		::= { omtp12PlusConfigurationEntry 116 }
		
	omtp12PlusXfpPowerDownMode OBJECT-TYPE
		SYNTAX INTEGER
		MAX-ACCESS read-write
		STATUS current
		DESCRIPTION
			"Valid only as a SET command.
			Sets the XFP in the Power Down mode i.e. low power 
			consumption mode.
			-----------------------------
			omtp12PlusInterfaceNumber:
			1 - CLIENT-1
			2 - LINE-1
			3 - LINE-2
			-----------------------------
			Values: 
			01 - power down XFP
			-----------------------------" 
		::= { omtp12PlusConfigurationEntry 117 }
		
	omtp12PlusXfpLineLoopback OBJECT-TYPE
		SYNTAX INTEGER
		MAX-ACCESS read-write
		STATUS current
		DESCRIPTION
			"Set or Get line loopback in XFP			
			-----------------------------
			omtp12PlusInterfaceNumber:
			1 - CLIENT-1
			2 - LINE-1
			3 - LINE-2
			-----------------------------
			Values: 
			1 - Enable XFP Line Loopback
			0 - Disable XFP Line Loopback
			-----------------------------" 
		::= { omtp12PlusConfigurationEntry 118 }

	omtp12PlusXfpXfiLoopback OBJECT-TYPE
		SYNTAX INTEGER
		MAX-ACCESS read-write
		STATUS current
		DESCRIPTION
			"Set or Get Xfi loopback in XFP			
			-----------------------------
			omtp12PlusInterfaceNumber:
			1 - CLIENT-1
			2 - LINE-1
			3 - LINE-2
			-----------------------------
			Values: 
			1 - Enable XFP Xfi Loopback
			0 - Disable XFP Xfi Loopback
			-----------------------------" 
		::= { omtp12PlusConfigurationEntry 119 }
		
	omtp12PlusXfpAmplitudeThresholdOfReceiverForFecControl OBJECT-TYPE
		SYNTAX INTEGER
		MAX-ACCESS read-write
		STATUS current
		DESCRIPTION
			" Set or Get amplitude threshold of receiver for FEC control			
			-----------------------------
			omtp12PlusInterfaceNumber:
			1 - CLIENT-1
			2 - LINE-1
			3 - LINE-2
			-----------------------------
			Values: 
			eg: Reserved
			-----------------------------" 
		::= { omtp12PlusConfigurationEntry 120 }
		
	omtp12PlusXfpPhaseInEyeDiagramForFecControl OBJECT-TYPE
		SYNTAX INTEGER
		MAX-ACCESS read-write
		STATUS current
		DESCRIPTION
			" Set or Get XFP phase in eye diagram for FEC control			
			-----------------------------
			omtp12PlusInterfaceNumber:
			1 - CLIENT-1
			2 - LINE-1
			3 - LINE-2
			-----------------------------
			Values: 
			eg: Reserved
			-----------------------------" 
		::= { omtp12PlusConfigurationEntry 121 }
		
	omtp12PlusXfpSystemReportingBer OBJECT-TYPE
		SYNTAX INTEGER
		MAX-ACCESS read-write
		STATUS current
		DESCRIPTION
			" Set or Get XFP system reporting BER			
			-----------------------------
			omtp12PlusInterfaceNumber:
			1 - CLIENT-1
			2 - LINE-1
			3 - LINE-2
			-----------------------------
			Values: 
			eg: Reserved
			-----------------------------" 
		::= { omtp12PlusConfigurationEntry 122 }

	omtp12PlusXfpHighTemperatureAlarmThreshold OBJECT-TYPE
		SYNTAX DisplayString
		MAX-ACCESS read-write
		STATUS current
		DESCRIPTION
			"Set or Get High Temperature Alarm Threshold
			(in degree celsius) for the requested port
			-----------------------------
			omtp12PlusInterfaceNumber:
			1 - CLIENT-1
			2 - LINE-1
			3 - LINE-2
			-----------------------------
			Values: 
			eg: 65 
			-----------------------------" 
		::= { omtp12PlusConfigurationEntry 131 }
		
	omtp12PlusXfpLowTemperatureAlarmThreshold OBJECT-TYPE
		SYNTAX DisplayString
		MAX-ACCESS read-write
		STATUS current
		DESCRIPTION
			"Set or Get Low Temperature Alarm Threshold
			(in degree celsius) for the requested port
			-----------------------------
			omtp12PlusInterfaceNumber:
			1 - CLIENT-1
			2 - LINE-1
			3 - LINE-2
			-----------------------------
			Values: 
			eg: 5 
			-----------------------------" 
		::= { omtp12PlusConfigurationEntry 132 }
		
	omtp12PlusXfpHighTemperatureWarningThreshold OBJECT-TYPE
		SYNTAX DisplayString
		MAX-ACCESS read-write
		STATUS current
		DESCRIPTION
			"Set or Get High Temperature Warning Threshold
			(in degree celsius) for the requested port
			-----------------------------
			omtp12PlusInterfaceNumber:
			1 - CLIENT-1
			2 - LINE-1
			3 - LINE-2
			-----------------------------
			Values: 
			eg: 60 
			-----------------------------"
		::= { omtp12PlusConfigurationEntry 133 }
		
	omtp12PlusXfpLowTemperatureWarningThreshold OBJECT-TYPE
		SYNTAX DisplayString
		MAX-ACCESS read-write
		STATUS current
		DESCRIPTION
			"Set or Get Low Temperature Warning Threshold
			(in degree celsius) for the requested port
			-----------------------------
			omtp12PlusInterfaceNumber:
			1 - CLIENT-1
			2 - LINE-1
			3 - LINE-2
			-----------------------------
			Values: 
			eg: 10 
			-----------------------------"
		::= { omtp12PlusConfigurationEntry 134 }

	omtp12PlusXfpHighBiasCurrentAlarmThreshold OBJECT-TYPE
		SYNTAX DisplayString
		MAX-ACCESS read-write
		STATUS current
		DESCRIPTION
			"Set or Get High Bias Current Alarm Threshold
			(in milli ampere) for the requested port
			-----------------------------
			omtp12PlusInterfaceNumber:
			1 - CLIENT-1
			2 - LINE-1
			3 - LINE-2
			-----------------------------
			Values:
			eg: 35.6
			-----------------------------"			
		::= { omtp12PlusConfigurationEntry 135 }
		
	omtp12PlusXfpLowBiasCurrentAlarmThreshold OBJECT-TYPE
		SYNTAX DisplayString
		MAX-ACCESS read-write
		STATUS current
		DESCRIPTION
			"Set or Get Low Bias Current Alarm Threshold
			(in milli ampere) for the requested port
			-----------------------------
			omtp12PlusInterfaceNumber:
			1 - CLIENT-1
			2 - LINE-1
			3 - LINE-2
			-----------------------------
			Values:
			eg: 31.1
			-----------------------------"
		::= { omtp12PlusConfigurationEntry 136 }
		
	omtp12PlusXfpHighBiasCurrentWarningThreshold OBJECT-TYPE
		SYNTAX DisplayString
		MAX-ACCESS read-write
		STATUS current
		DESCRIPTION
			"Set or Get High Bias Current Warning Threshold
			(in milli ampere) for the requested port
			-----------------------------
			omtp12PlusInterfaceNumber:
			1 - CLIENT-1
			2 - LINE-1
			3 - LINE-2
			-----------------------------
			Values:
			eg: 34.5
			-----------------------------"
		::= { omtp12PlusConfigurationEntry 137 }
		
	omtp12PlusXfpLowBiasCurrentWarningThreshold OBJECT-TYPE
		SYNTAX DisplayString
		MAX-ACCESS read-write
		STATUS current
		DESCRIPTION
			"Set or Get Low Bias Current Warning Threshold
			(in milli ampere) for the requested port
			-----------------------------
			omtp12PlusInterfaceNumber:
			1 - CLIENT-1
			2 - LINE-1
			3 - LINE-2
			-----------------------------
			Values:
			eg: 32.8
			-----------------------------"
		::= { omtp12PlusConfigurationEntry 138 }
		
	omtp12PlusXfpInputHighPowerAlarmThreshold OBJECT-TYPE
		SYNTAX DisplayString
		MAX-ACCESS read-write
		STATUS current
		DESCRIPTION
			"Set or Get Input High Power Alarm Threshold
			(in dbm) for the requested port
			-----------------------------
			omtp12PlusInterfaceNumber:
			1 - CLIENT-1
			2 - LINE-1
			3 - LINE-2
			-----------------------------
			Values:
			eg: -9.1
			-----------------------------"
		::= { omtp12PlusConfigurationEntry 139 }

	omtp12PlusXfpInputLowPowerAlarmThreshold OBJECT-TYPE
		SYNTAX DisplayString
		MAX-ACCESS read-write
		STATUS current
		DESCRIPTION
			"Set or Get Input Low Power Alarm Threshold
			(in dbm) for the requested port
			-----------------------------
			omtp12PlusInterfaceNumber:
			1 - CLIENT-1
			2 - LINE-1
			3 - LINE-2
			-----------------------------
			Values:
			eg: -35.6
			-----------------------------"
		::= { omtp12PlusConfigurationEntry 140 }
		
	omtp12PlusXfpInputHighPowerWarningThreshold OBJECT-TYPE
		SYNTAX DisplayString
		MAX-ACCESS read-write
		STATUS current
		DESCRIPTION
			"Set or Get Input High Power Warning Threshold
			(in dbm) for the requested port
			-----------------------------
			omtp12PlusInterfaceNumber:
			1 - CLIENT-1
			2 - LINE-1
			3 - LINE-2
			-----------------------------
			Values:
			eg: -11.2
			-----------------------------"
		::= { omtp12PlusConfigurationEntry 141 }
		
	omtp12PlusXfpInputLowPowerWarningThreshold OBJECT-TYPE
		SYNTAX DisplayString
		MAX-ACCESS read-write
		STATUS current
		DESCRIPTION
			"Set or Get Input Low Power Warning Threshold
			(in dbm) for the requested port
			-----------------------------
			omtp12PlusInterfaceNumber:
			1 - CLIENT-1
			2 - LINE-1
			3 - LINE-2
			-----------------------------
			Values:
			eg: -31.3
			-----------------------------"
		::= { omtp12PlusConfigurationEntry 142 }
		
	omtp12PlusXfpOutputHighPowerAlarmThreshold OBJECT-TYPE
		SYNTAX DisplayString
		MAX-ACCESS read-write
		STATUS current
		DESCRIPTION
			"Set or Get Output High Power Alarm Threshold
			(in dbm) for the requested port
			-----------------------------
			omtp12PlusInterfaceNumber:
			1 - CLIENT-1
			2 - LINE-1
			3 - LINE-2
			-----------------------------
			Values:
			eg: +2.0
			-----------------------------"
		::= { omtp12PlusConfigurationEntry 143 }

	omtp12PlusXfpOutputLowPowerAlarmThreshold OBJECT-TYPE
		SYNTAX DisplayString
		MAX-ACCESS read-write
		STATUS current
		DESCRIPTION
			"Set or Get Output Low Power Alarm Threshold
			(in dbm) for the requested port
			-----------------------------
			omtp12PlusInterfaceNumber:
			1 - CLIENT-1
			2 - LINE-1
			3 - LINE-2
			-----------------------------
			Values:
			eg: -3.5
			-----------------------------"
		::= { omtp12PlusConfigurationEntry 144 }
		
	omtp12PlusXfpOutputHighPowerWarningThreshold OBJECT-TYPE
		SYNTAX DisplayString
		MAX-ACCESS read-write
		STATUS current
		DESCRIPTION
			"Set or Get Output High Power Warning Threshold
			(in dbm) for the requested port
			-----------------------------
			omtp12PlusInterfaceNumber:
			1 - CLIENT-1
			2 - LINE-1
			3 - LINE-2
			-----------------------------
			Values:
			eg: +1.3
			-----------------------------"
		::= { omtp12PlusConfigurationEntry 145 }
		
	omtp12PlusXfpOutputLowPowerWarningThreshold OBJECT-TYPE
		SYNTAX DisplayString
		MAX-ACCESS read-write
		STATUS current
		DESCRIPTION
			"Set or Get Output Low Power Warning Threshold
			(in dbm) for the requested port
			-----------------------------
			omtp12PlusInterfaceNumber:
			1 - CLIENT-1
			2 - LINE-1
			3 - LINE-2
			-----------------------------
			Values:
			eg: -2.5
			-----------------------------"
		::= { omtp12PlusConfigurationEntry 146 }
		
	omtp12PlusXfpHighSupplyVoltageAlarmThreshold OBJECT-TYPE
		SYNTAX DisplayString
		MAX-ACCESS read-write
		STATUS current
		DESCRIPTION
			"Set or Get High Supply Voltage Alarm Threshold
			(in volts) for the requested port
			-----------------------------
			omtp12PlusInterfaceNumber:
			1 - CLIENT-1
			2 - LINE-1
			3 - LINE-2
			-----------------------------
			Values:
			eg: +3.3
			-----------------------------"
		::= { omtp12PlusConfigurationEntry 147 }

	omtp12PlusXfpLowSupplyVoltageAlarmThreshold OBJECT-TYPE
		SYNTAX DisplayString
		MAX-ACCESS read-write
		STATUS current
		DESCRIPTION
			"Set or Get Low Supply Voltage Alarm Threshold
			(in volts) for the requested port
			-----------------------------
			omtp12PlusInterfaceNumber:
			1 - CLIENT-1
			2 - LINE-1
			3 - LINE-2
			-----------------------------
			Values:
			eg: +3.0
			-----------------------------"
		::= { omtp12PlusConfigurationEntry 148 }
		
	omtp12PlusXfpHighSupplyVoltageWarningThreshold OBJECT-TYPE
		SYNTAX DisplayString
		MAX-ACCESS read-write
		STATUS current
		DESCRIPTION
			"Set or Get High Supply Voltage Warning Threshold
			(in volts) for the requested port
			-----------------------------
			omtp12PlusInterfaceNumber:
			1 - CLIENT-1
			2 - LINE-1
			3 - LINE-2
			-----------------------------
			Values:
			eg: +3.2
			-----------------------------"
		::= { omtp12PlusConfigurationEntry 149 }
		
	omtp12PlusXfpLowSupplyVoltageWarningThreshold OBJECT-TYPE
		SYNTAX DisplayString
		MAX-ACCESS read-write
		STATUS current
		DESCRIPTION
			"Set or Get Low Supply Voltage Warning Threshold
			(in volts) for the requested port
			-----------------------------
			omtp12PlusInterfaceNumber:
			1 - CLIENT-1
			2 - LINE-1
			3 - LINE-2
			-----------------------------
			Values:
			eg: +3.1
			-----------------------------"
		::= { omtp12PlusConfigurationEntry 150 }
		
	omtp12PlusXfpInputPowerFailureAlarmInhibit OBJECT-TYPE
	      SYNTAX  INTEGER
	      MAX-ACCESS  read-write
	      STATUS  current
	      DESCRIPTION
			"Inhibits OMTP12-PLUS XFP Input Power Failure Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 201 }

	omtp12PlusXfpOutputPowerFailureAlarmInhibit OBJECT-TYPE
	      SYNTAX  INTEGER
	      MAX-ACCESS  read-write
	      STATUS  current
	      DESCRIPTION
			"Inhibits OMTP12-PLUS XFP Output Power Failure Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 202 }

	omtp12PlusXfpHighTemperatureAlarmInhibit OBJECT-TYPE
	      SYNTAX  INTEGER
	      MAX-ACCESS  read-write
	      STATUS  current
	      DESCRIPTION
			"Inhibits OMTP12-PLUS XFP High Temperature Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 203 }

	omtp12PlusXfpLowTemperatureAlarmInhibit OBJECT-TYPE
	      SYNTAX  INTEGER
	      MAX-ACCESS  read-write
	      STATUS  current
	      DESCRIPTION
			"Inhibits OMTP12-PLUS XFP Low Temperature Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 204 }

	omtp12PlusXfpHighTemperatureWarningInhibit OBJECT-TYPE
	      SYNTAX  INTEGER
	      MAX-ACCESS  read-write
	      STATUS  current
	      DESCRIPTION
			"Inhibits OMTP12-PLUS XFP High Temperature Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 205 }

	omtp12PlusXfpLowTemperatureWarningInhibit OBJECT-TYPE
	      SYNTAX  INTEGER
	      MAX-ACCESS  read-write
	      STATUS  current
	      DESCRIPTION
			"Inhibits OMTP12-PLUS XFP Low Temperature Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 206 }

	omtp12PlusXfpHighBiasCurrentAlarmInhibit OBJECT-TYPE
	      SYNTAX  INTEGER
	      MAX-ACCESS  read-write
	      STATUS  current
	      DESCRIPTION
			"Inhibits OMTP12-PLUS XFP High Bias Current Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 207 }

	omtp12PlusXfpLowBiasCurrentAlarmInhibit OBJECT-TYPE
	      SYNTAX  INTEGER
	      MAX-ACCESS  read-write
	      STATUS  current
	      DESCRIPTION
			"Inhibits OMTP12-PLUS XFP Low Bias Current Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 208 }

	omtp12PlusXfpHighBiasCurrentWarningInhibit OBJECT-TYPE
	      SYNTAX  INTEGER
	      MAX-ACCESS  read-write
	      STATUS  current
	      DESCRIPTION
			"Inhibits OMTP12-PLUS XFP High Bias Current Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 209 }

	omtp12PlusXfpLowBiasCurrentWarningInhibit OBJECT-TYPE
	      SYNTAX  INTEGER
	      MAX-ACCESS  read-write
	      STATUS  current
	      DESCRIPTION
			"Inhibits OMTP12-PLUS XFP Low Bias Current Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 210 }

	omtp12PlusXfpInputHighPowerAlarmInhibit OBJECT-TYPE
	      SYNTAX  INTEGER
	      MAX-ACCESS  read-write
	      STATUS  current
	      DESCRIPTION
			"Inhibits OMTP12-PLUS XFP Input High Power Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 211 }

	omtp12PlusXfpInputLowPowerAlarmInhibit OBJECT-TYPE
	      SYNTAX  INTEGER
	      MAX-ACCESS  read-write
	      STATUS  current
	      DESCRIPTION
			"Inhibits OMTP12-PLUS XFP Input Low Power Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 212 }

	omtp12PlusXfpInputHighPowerWarningInhibit OBJECT-TYPE
	      SYNTAX  INTEGER
	      MAX-ACCESS  read-write
	      STATUS  current
	      DESCRIPTION
			"Inhibits OMTP12-PLUS XFP Input High Power Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 213 }

	omtp12PlusXfpInputLowPowerWarningInhibit OBJECT-TYPE
	      SYNTAX  INTEGER
	      MAX-ACCESS  read-write
	      STATUS  current
	      DESCRIPTION
			"Inhibits OMTP12-PLUS XFP Input Low Power Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 214 }

	omtp12PlusXfpOutputHighPowerAlarmInhibit OBJECT-TYPE
	      SYNTAX  INTEGER
	      MAX-ACCESS  read-write
	      STATUS  current
	      DESCRIPTION
			"Inhibits OMTP12-PLUS XFP Output High Power Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 215 }

	omtp12PlusXfpOutputLowPowerAlarmInhibit OBJECT-TYPE
	      SYNTAX  INTEGER
	      MAX-ACCESS  read-write
	      STATUS  current
	      DESCRIPTION
			"Inhibits OMTP12-PLUS XFP Output Low Power Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 216 }

	omtp12PlusXfpOutputHighPowerWarningInhibit OBJECT-TYPE
	      SYNTAX  INTEGER
	      MAX-ACCESS  read-write
	      STATUS  current
	      DESCRIPTION
			"Inhibits OMTP12-PLUS XFP Output High Power Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 217 }

	omtp12PlusXfpOutputLowPowerWarningInhibit OBJECT-TYPE
	      SYNTAX  INTEGER
	      MAX-ACCESS  read-write
	      STATUS  current
	      DESCRIPTION
			"Inhibits OMTP12-PLUS XFP Output Low Power Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 218 }

	omtp12PlusXfpHighSupplyVoltageAlarmInhibit OBJECT-TYPE
	      SYNTAX  INTEGER
	      MAX-ACCESS  read-write
	      STATUS  current
	      DESCRIPTION
			"Inhibits OMTP12-PLUS XFP High Supply Voltage Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 219 }

	omtp12PlusXfpLowSupplyVoltageAlarmInhibit OBJECT-TYPE
	      SYNTAX  INTEGER
	      MAX-ACCESS  read-write
	      STATUS  current
	      DESCRIPTION
			"Inhibits OMTP12-PLUS XFP Low Supply Voltage Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 220 }

	omtp12PlusXfpHighSupplyVoltageWarningInhibit OBJECT-TYPE
	      SYNTAX  INTEGER
	      MAX-ACCESS  read-write
	      STATUS  current
	      DESCRIPTION
			"Inhibits OMTP12-PLUS XFP High Supply Voltage Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 221 }

	omtp12PlusXfpLowSupplyVoltageWarningInhibit OBJECT-TYPE
	      SYNTAX  INTEGER
	      MAX-ACCESS  read-write
	      STATUS  current
	      DESCRIPTION
			"Inhibits OMTP12-PLUS XFP Low Supply Voltage Warning
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 222 }

	omtp12PlusXfpPresenceAbsenceNotificationInhibit OBJECT-TYPE
	      SYNTAX  INTEGER
	      MAX-ACCESS  read-write
	      STATUS  current
	      DESCRIPTION
			"Inhibits OMTP12-PLUS XFP Presence Absence Notification
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 223 }

	omtp12PlusOtuLossOfSignalAlarmInhibit OBJECT-TYPE
	      SYNTAX  INTEGER
	      MAX-ACCESS  read-write
	      STATUS  current
	      DESCRIPTION
			"Inhibits OMTP12-PLUS OTU Loss Of Signal Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 231 }

	omtp12PlusOtuLossOfFrameAlarmInhibit OBJECT-TYPE
	      SYNTAX  INTEGER
	      MAX-ACCESS  read-write
	      STATUS  current
	      DESCRIPTION
			"Inhibits OMTP12-PLUS OTU Loss Of Frame Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 232 }

	omtp12PlusOtuOutOfFrameAlarmInhibit OBJECT-TYPE
	      SYNTAX  INTEGER
	      MAX-ACCESS  read-write
	      STATUS  current
	      DESCRIPTION
			"Inhibits OMTP12-PLUS OTU Out Of Frame Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 233 }

	omtp12PlusOtuLossOfMultiFrameAlarmInhibit OBJECT-TYPE
	      SYNTAX  INTEGER
	      MAX-ACCESS  read-write
	      STATUS  current
	      DESCRIPTION
			"Inhibits OMTP12-PLUS OTU Loss Of Multi Frame Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 234 }

	omtp12PlusOtuOutOfMultiFrameAlarmInhibit OBJECT-TYPE
	      SYNTAX  INTEGER
	      MAX-ACCESS  read-write
	      STATUS  current
	      DESCRIPTION
			"Inhibits OMTP12-PLUS OTU Out Of Multi Frame Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 235 }

	omtp12PlusOtuSignalFailAlarmInhibit OBJECT-TYPE
	      SYNTAX  INTEGER
	      MAX-ACCESS  read-write
	      STATUS  current
	      DESCRIPTION
			"Inhibits OMTP12-PLUS OTU Signal Fail Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 236 }

	omtp12PlusOtuSignalDegradeAlarmInhibit OBJECT-TYPE
	      SYNTAX  INTEGER
	      MAX-ACCESS  read-write
	      STATUS  current
	      DESCRIPTION
			"Inhibits OMTP12-PLUS OTU Signal Degrade Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 237 }

	omtp12PlusOtuAlarmIndicationSignalAlarmInhibit OBJECT-TYPE
	      SYNTAX  INTEGER
	      MAX-ACCESS  read-write
	      STATUS  current
	      DESCRIPTION
			"Inhibits OMTP12-PLUS OTU Alarm Indication Signal Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 238 }

	omtp12PlusOtuIncomingAlignmentErrorAlarmInhibit OBJECT-TYPE
	      SYNTAX  INTEGER
	      MAX-ACCESS  read-write
	      STATUS  current
	      DESCRIPTION
			"Inhibits OMTP12-PLUS OTU Incoming Alignment Error Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 239 }

	omtp12PlusOtuTraceIdentifierMismatchAlarmInhibit OBJECT-TYPE
	      SYNTAX  INTEGER
	      MAX-ACCESS  read-write
	      STATUS  current
	      DESCRIPTION
			"Inhibits OMTP12-PLUS OTU Trace Identifier Mismatch Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 240 }

	omtp12PlusOtuBackwardIncomingAlignmentErrorAlarmInhibit OBJECT-TYPE
	      SYNTAX  INTEGER
	      MAX-ACCESS  read-write
	      STATUS  current
	      DESCRIPTION
			"Inhibits OMTP12-PLUS OTU Backward Incoming Alignment Error Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 241 }

	omtp12PlusOtuBackwardDefectIndicationAlarmInhibit OBJECT-TYPE
	      SYNTAX  INTEGER
	      MAX-ACCESS  read-write
	      STATUS  current
	      DESCRIPTION
			"Inhibits OMTP12-PLUS OTU Backward Defect Indication Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 242 }

	omtp12PlusOduSignalFailAlarmInhibit OBJECT-TYPE
	      SYNTAX  INTEGER
	      MAX-ACCESS  read-write
	      STATUS  current
	      DESCRIPTION
			"Inhibits OMTP12-PLUS ODU Signal Fail Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 251 }

	omtp12PlusOduSignalDegradeAlarmInhibit OBJECT-TYPE
	      SYNTAX  INTEGER
	      MAX-ACCESS  read-write
	      STATUS  current
	      DESCRIPTION
			"Inhibits OMTP12-PLUS ODU Signal Degrade Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 252 }

	omtp12PlusOduAlarmIndicationSignalAlarmInhibit OBJECT-TYPE
	      SYNTAX  INTEGER
	      MAX-ACCESS  read-write
	      STATUS  current
	      DESCRIPTION
			"Inhibits OMTP12-PLUS ODU Alarm Indication Signal Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 253 }

	omtp12PlusOduTcm1IncomingAlignmentErrorAlarmInhibit OBJECT-TYPE
	      SYNTAX  INTEGER
	      MAX-ACCESS  read-write
	      STATUS  current
	      DESCRIPTION
			"Inhibits OMTP12-PLUS ODU TCM1 Incoming Alignment Error 
			Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 254 }

	omtp12PlusOduTcm2IncomingAlignmentErrorAlarmInhibit OBJECT-TYPE
	      SYNTAX  INTEGER
	      MAX-ACCESS  read-write
	      STATUS  current
	      DESCRIPTION
			"Inhibits OMTP12-PLUS ODU TCM2 Incoming Alignment Error 
			Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 255 }

	omtp12PlusOduTcm3IncomingAlignmentErrorAlarmInhibit OBJECT-TYPE
	      SYNTAX  INTEGER
	      MAX-ACCESS  read-write
	      STATUS  current
	      DESCRIPTION
			"Inhibits OMTP12-PLUS ODU TCM3 Incoming Alignment Error 
			Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 256 }

	omtp12PlusOduTcm4IncomingAlignmentErrorAlarmInhibit OBJECT-TYPE
	      SYNTAX  INTEGER
	      MAX-ACCESS  read-write
	      STATUS  current
	      DESCRIPTION
			"Inhibits OMTP12-PLUS ODU TCM4 Incoming Alignment Error 
			Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 257 }

	omtp12PlusOduTcm5IncomingAlignmentErrorAlarmInhibit OBJECT-TYPE
	      SYNTAX  INTEGER
	      MAX-ACCESS  read-write
	      STATUS  current
	      DESCRIPTION
			"Inhibits OMTP12-PLUS ODU TCM5 Incoming Alignment Error 
			Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 258 }

	omtp12PlusOduTcm6IncomingAlignmentErrorAlarmInhibit OBJECT-TYPE
	      SYNTAX  INTEGER
	      MAX-ACCESS  read-write
	      STATUS  current
	      DESCRIPTION
			"Inhibits OMTP12-PLUS ODU TCM6 Incoming Alignment Error 
			Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 259 }

	omtp12PlusOduTraceIdentifierMismatchAlarmInhibit OBJECT-TYPE
	      SYNTAX  INTEGER
	      MAX-ACCESS  read-write
	      STATUS  current
	      DESCRIPTION
			"Inhibits OMTP12-PLUS ODU Trace Identifier Mismatch Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 260 }

	omtp12PlusOduLockedDefectAlarmInhibit OBJECT-TYPE
	      SYNTAX  INTEGER
	      MAX-ACCESS  read-write
	      STATUS  current
	      DESCRIPTION
			"Inhibits OMTP12-PLUS ODU Locked Defect Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 261 }

	omtp12PlusOduOpenConnectionIndicationAlarmInhibit OBJECT-TYPE
	      SYNTAX  INTEGER
	      MAX-ACCESS  read-write
	      STATUS  current
	      DESCRIPTION
			"Inhibits OMTP12-PLUS ODU Open Connection Indication Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 262 }

	omtp12PlusOduBackwardDefectIndicationAlarmInhibit OBJECT-TYPE
	      SYNTAX  INTEGER
	      MAX-ACCESS  read-write
	      STATUS  current
	      DESCRIPTION
			"Inhibits OMTP12-PLUS ODU Backward Defect Indication Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 263 }

	omtp12PlusOduTcm1BackwardIncomingAlignmentErrorAlarmInhibit OBJECT-TYPE
	      SYNTAX  INTEGER
	      MAX-ACCESS  read-write
	      STATUS  current
	      DESCRIPTION
			"Inhibits OMTP12-PLUS ODU TCM1 Backward Incoming
			Alignment Error Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 264 }

	omtp12PlusOduTcm2BackwardIncomingAlignmentErrorAlarmInhibit OBJECT-TYPE
	      SYNTAX  INTEGER
	      MAX-ACCESS  read-write
	      STATUS  current
	      DESCRIPTION
			"Inhibits OMTP12-PLUS ODU TCM2 Backward Incoming
			Alignment Error Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 265 }

	omtp12PlusOduTcm3BackwardIncomingAlignmentErrorAlarmInhibit OBJECT-TYPE
	      SYNTAX  INTEGER
	      MAX-ACCESS  read-write
	      STATUS  current
	      DESCRIPTION
			"Inhibits OMTP12-PLUS ODU TCM3 Backward Incoming
			Alignment Error Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 266 }

	omtp12PlusOduTcm4BackwardIncomingAlignmentErrorAlarmInhibit OBJECT-TYPE
	      SYNTAX  INTEGER
	      MAX-ACCESS  read-write
	      STATUS  current
	      DESCRIPTION
			"Inhibits OMTP12-PLUS ODU TCM4 Backward Incoming
			Alignment Error Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 267 }

	omtp12PlusOduTcm5BackwardIncomingAlignmentErrorAlarmInhibit OBJECT-TYPE
	      SYNTAX  INTEGER
	      MAX-ACCESS  read-write
	      STATUS  current
	      DESCRIPTION
			"Inhibits OMTP12-PLUS ODU TCM5 Backward Incoming
			Alignment Error Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 268 }

	omtp12PlusOduTcm6BackwardIncomingAlignmentErrorAlarmInhibit OBJECT-TYPE
	      SYNTAX  INTEGER
	      MAX-ACCESS  read-write
	      STATUS  current
	      DESCRIPTION
			"Inhibits OMTP12-PLUS ODU TCM6 Backward Incoming
			Alignment Error Alarm for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 269 }

	omtp12PlusOpuPayloadMismatchAlarmInhibit OBJECT-TYPE
	      SYNTAX  INTEGER
	      MAX-ACCESS  read-write
	      STATUS  current
	      DESCRIPTION
			"Inhibits OMTP12-PLUS Opu Payload Mismatch Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 270 }

	omtp12PlusOchLossOfPayloadAlarmInhibit OBJECT-TYPE
	      SYNTAX  INTEGER
	      MAX-ACCESS  read-write
	      STATUS  current
	      DESCRIPTION
			"Inhibits OMTP12-PLUS Och Loss Of Payload Alarm
			for the requested port
			-----------------------------
			omtp12PlusInterfaceNumber:
			1 - CLIENT-1
			2 - LINE-1
			3 - LINE-2
			-----------------------------
			Values:
			1 - Inhibit
			0 - Do Not Inhibit
			-----------------------------"
		::= { omtp12PlusConfigurationEntry 271 }

	omtp12PlusSdhLossOfSignalAlarmInhibit OBJECT-TYPE
	      SYNTAX  INTEGER
	      MAX-ACCESS  read-write
	      STATUS  current
	      DESCRIPTION
			"Inhibits OMTP12-PLUS SDH Loss Of Signal Alarm
			for the requested port
			-----------------------------
			omtp12PlusInterfaceNumber:
			1 - CLIENT-1
			-----------------------------
			Values:
			1 - Inhibit
			0 - Do Not Inhibit
			-----------------------------"
		::= { omtp12PlusConfigurationEntry 281 }

	omtp12PlusSdhOutOfFrameAlarmInhibit OBJECT-TYPE
	      SYNTAX  INTEGER
	      MAX-ACCESS  read-write
	      STATUS  current
	      DESCRIPTION
			"Inhibits OMTP12-PLUS SDH Out Of Frame Alarm
			for the requested port
			-----------------------------
			omtp12PlusInterfaceNumber:
			1 - CLIENT-1
			-----------------------------
			Values:
			1 - Inhibit
			0 - Do Not Inhibit
			-----------------------------"
		::= { omtp12PlusConfigurationEntry 282 }

	omtp12PlusSdhLossOfFrameAlarmInhibit OBJECT-TYPE
	      SYNTAX  INTEGER
	      MAX-ACCESS  read-write
	      STATUS  current
	      DESCRIPTION
			"Inhibits OMTP12-PLUS SDH Loss Of Frame Alarm
			for the requested port
			-----------------------------
			omtp12PlusInterfaceNumber:
			1 - CLIENT-1
			-----------------------------
			Values:
			1 - Inhibit
			0 - Do Not Inhibit
			-----------------------------"
		::= { omtp12PlusConfigurationEntry 283 }

	omtp12PlusSdhRsAlarmIndicationSignalAlarmInhibit OBJECT-TYPE
	      SYNTAX  INTEGER
	      MAX-ACCESS  read-write
	      STATUS  current
	      DESCRIPTION
			"Inhibits OMTP12-PLUS SDH RS Alarm Indication Signal Alarm
			for the requested port
			-----------------------------
			omtp12PlusInterfaceNumber:
			1 - CLIENT-1
			-----------------------------
			Values:
			1 - Inhibit
			0 - Do Not Inhibit
			-----------------------------"
		::= { omtp12PlusConfigurationEntry 284 }

	omtp12PlusSdhRsTraceIdentifierMismatchAlarmInhibit OBJECT-TYPE
	      SYNTAX  INTEGER
	      MAX-ACCESS  read-write
	      STATUS  current
	      DESCRIPTION
			"Inhibits OMTP12-PLUS SDH RS Trace Identifier Mismatch Alarm
			for the requested port
			-----------------------------
			omtp12PlusInterfaceNumber:
			1 - CLIENT-1
			-----------------------------
			Values:
			1 - Inhibit
			0 - Do Not Inhibit
			-----------------------------"
		::= { omtp12PlusConfigurationEntry 285 }

	omtp12PlusSdhAuAlarmIndicationSignalAlarmInhibit OBJECT-TYPE
	      SYNTAX  INTEGER
	      MAX-ACCESS  read-write
	      STATUS  current
	      DESCRIPTION
			"Inhibits OMTP12-PLUS SDH AU Alarm Indication Signal Alarm
			for the requested port
			-----------------------------
			omtp12PlusInterfaceNumber:
			1 - CLIENT-1
			-----------------------------
			Values:
			1 - Inhibit
			0 - Do Not Inhibit
			-----------------------------"
		::= { omtp12PlusConfigurationEntry 286 }

	omtp12PlusSdhAuLossOfPointerAlarmInhibit OBJECT-TYPE
	      SYNTAX  INTEGER
	      MAX-ACCESS  read-write
	      STATUS  current
	      DESCRIPTION
			"Inhibits OMTP12-PLUS SDH AU Loss Of Pointer Alarm
			for the requested port
			-----------------------------
			omtp12PlusInterfaceNumber:
			1 - CLIENT-1
			-----------------------------
			Values:
			1 - Inhibit
			0 - Do Not Inhibit
			-----------------------------"
		::= { omtp12PlusConfigurationEntry 287 }

	omtp12PlusSdhMsAlarmIndicationSignalAlarmInhibit OBJECT-TYPE
	      SYNTAX  INTEGER
	      MAX-ACCESS  read-write
	      STATUS  current
	      DESCRIPTION
			"Inhibits OMTP12-PLUS SDH MS Alarm Indication Signal Alarm
			for the requested port
			-----------------------------
			omtp12PlusInterfaceNumber:
			1 - CLIENT-1
			-----------------------------
			Values:
			1 - Inhibit
			0 - Do Not Inhibit
			-----------------------------"
		::= { omtp12PlusConfigurationEntry 288 }

	omtp12PlusSdhMsRemoteErrorIndicationAlarmInhibit OBJECT-TYPE
	      SYNTAX  INTEGER
	      MAX-ACCESS  read-write
	      STATUS  current
	      DESCRIPTION
			"Inhibits OMTP12-PLUS SDH MS Remote Error Indication Alarm
			for the requested port
			-----------------------------
			omtp12PlusInterfaceNumber:
			1 - CLIENT-1
			-----------------------------
			Values:
			1 - Inhibit
			0 - Do Not Inhibit
			-----------------------------"
		::= { omtp12PlusConfigurationEntry 289 }

	omtp12PlusSdhMsRemoteDefectIndicationAlarmInhibit OBJECT-TYPE
	      SYNTAX  INTEGER
	      MAX-ACCESS  read-write
	      STATUS  current
	      DESCRIPTION
			"Inhibits OMTP12-PLUS SDH MS Remote Defect Indication Alarm
			for the requested port
			-----------------------------
			omtp12PlusInterfaceNumber:
			1 - CLIENT-1
			-----------------------------
			Values:
			1 - Inhibit
			0 - Do Not Inhibit
			-----------------------------"
		::= { omtp12PlusConfigurationEntry 290 }

	omtp12PlusSdhMsRemoteFailureIndicationAlarmInhibit OBJECT-TYPE
	      SYNTAX  INTEGER
	      MAX-ACCESS  read-write
	      STATUS  current
	      DESCRIPTION
			"Inhibits OMTP12-PLUS SDH MS Remote Failure Indication Alarm
			for the requested port
			-----------------------------
			omtp12PlusInterfaceNumber:
			1 - CLIENT-1
			-----------------------------
			Values:
			1 - Inhibit
			0 - Do Not Inhibit
			-----------------------------"
		::= { omtp12PlusConfigurationEntry 291 }

	omtp12PlusSdhMsB2ExcessiveErrorAlarmInhibit OBJECT-TYPE
	      SYNTAX  INTEGER
	      MAX-ACCESS  read-write
	      STATUS  current
	      DESCRIPTION
			"Inhibits OMTP12-PLUS SDH MS B2 Signal Fail Alarm
			for the requested port
			-----------------------------
			omtp12PlusInterfaceNumber:
			1 - CLIENT-1
			-----------------------------
			Values:
			1 - Inhibit
			0 - Do Not Inhibit
			-----------------------------"
		::= { omtp12PlusConfigurationEntry 292 }

	omtp12PlusSdhMsB2SignalDegradeAlarmInhibit OBJECT-TYPE
	      SYNTAX  INTEGER
	      MAX-ACCESS  read-write
	      STATUS  current
	      DESCRIPTION
			"Inhibits OMTP12-PLUS SDH MS B2 Signal Degrade Alarm
			for the requested port
			-----------------------------
			omtp12PlusInterfaceNumber:
			1 - CLIENT-1
			-----------------------------
			Values:
			1 - Inhibit
			0 - Do Not Inhibit
			-----------------------------"
		::= { omtp12PlusConfigurationEntry 293 }

	omtp12PlusSdhLossOfSequenceSynchronisationAlarmInhibit OBJECT-TYPE
	      SYNTAX  INTEGER
	      MAX-ACCESS  read-write
	      STATUS  current
	      DESCRIPTION
			"Inhibits OMTP12-PLUS SDH Loss Of Sequence Synchronisation Alarm
			for the requested port
			-----------------------------
			omtp12PlusInterfaceNumber:
			1 - CLIENT-1
			-----------------------------
			Values:
			1 - Inhibit
			0 - Do Not Inhibit
			-----------------------------"
		::= { omtp12PlusConfigurationEntry 294 }

	omtp12PlusSdhHigherOrderPathPayloadLabelMismatchAlarmInhibit OBJECT-TYPE
	      SYNTAX  INTEGER
	      MAX-ACCESS  read-write
	      STATUS  current
	      DESCRIPTION
			"Inhibits OMTP12-PLUS SDH Higher Order Path Payload Label Mismatch Alarm
			for the requested port
			-----------------------------
			omtp12PlusInterfaceNumber:
			1 - CLIENT-1
			-----------------------------
			Values:
			1 - Inhibit
			0 - Do Not Inhibit
			-----------------------------"
		::= { omtp12PlusConfigurationEntry 295 }

	omtp12PlusSdhHigherOrderPathUnequippedAlarmInhibit OBJECT-TYPE
	      SYNTAX  INTEGER
	      MAX-ACCESS  read-write
	      STATUS  current
	      DESCRIPTION
			"Inhibits OMTP12-PLUS SDH Higher Order Path Unequipped Alarm
			for the requested port
			-----------------------------
			omtp12PlusInterfaceNumber:
			1 - CLIENT-1
			-----------------------------
			Values:
			1 - Inhibit
			0 - Do Not Inhibit
			-----------------------------"
		::= { omtp12PlusConfigurationEntry 296 }

	omtp12PlusWan10gLossOfSignalAlarmInhibit OBJECT-TYPE
	      SYNTAX  INTEGER
	      MAX-ACCESS  read-write
	      STATUS  current
	      DESCRIPTION
			"Inhibits OMTP12-PLUS WAN10G Loss Of Signal Alarm
			for the requested port
			-----------------------------
			omtp12PlusInterfaceNumber:
			1 - CLIENT-1
			-----------------------------
			Values:
			1 - Inhibit
			0 - Do Not Inhibit
			-----------------------------"
		::= { omtp12PlusConfigurationEntry 301 }

	omtp12PlusWan10gOutOfFrameAlarmInhibit OBJECT-TYPE
	      SYNTAX  INTEGER
	      MAX-ACCESS  read-write
	      STATUS  current
	      DESCRIPTION
			"Inhibits OMTP12-PLUS WAN10G Out Of Frame Alarm
			for the requested port
			-----------------------------
			omtp12PlusInterfaceNumber:
			1 - CLIENT-1
			-----------------------------
			Values:
			1 - Inhibit
			0 - Do Not Inhibit
			-----------------------------"
		::= { omtp12PlusConfigurationEntry 302 }

	omtp12PlusWan10gLossOfFrameAlarmInhibit OBJECT-TYPE
	      SYNTAX  INTEGER
	      MAX-ACCESS  read-write
	      STATUS  current
	      DESCRIPTION
			"Inhibits OMTP12-PLUS WAN10G Loss Of Frame Alarm
			for the requested port
			-----------------------------
			omtp12PlusInterfaceNumber:
			1 - CLIENT-1
			-----------------------------
			Values:
			1 - Inhibit
			0 - Do Not Inhibit
			-----------------------------"
		::= { omtp12PlusConfigurationEntry 303 }

	omtp12PlusWan10gRsAlarmIndicationSignalAlarmInhibit OBJECT-TYPE
	      SYNTAX  INTEGER
	      MAX-ACCESS  read-write
	      STATUS  current
	      DESCRIPTION
			"Inhibits OMTP12-PLUS WAN10G RS Alarm Indication Signal Alarm
			for the requested port
			-----------------------------
			omtp12PlusInterfaceNumber:
			1 - CLIENT-1
			-----------------------------
			Values:
			1 - Inhibit
			0 - Do Not Inhibit
			-----------------------------"
		::= { omtp12PlusConfigurationEntry 304 }

	omtp12PlusWan10gRsTraceIdentifierMismatchAlarmInhibit OBJECT-TYPE
	      SYNTAX  INTEGER
	      MAX-ACCESS  read-write
	      STATUS  current
	      DESCRIPTION
			"Inhibits OMTP12-PLUS WAN10G RS Trace Identifier Mismatch Alarm
			for the requested port
			-----------------------------
			omtp12PlusInterfaceNumber:
			1 - CLIENT-1
			-----------------------------
			Values:
			1 - Inhibit
			0 - Do Not Inhibit
			-----------------------------"
		::= { omtp12PlusConfigurationEntry 305 }

	omtp12PlusWan10gAuAlarmIndicationSignalAlarmInhibit OBJECT-TYPE
	      SYNTAX  INTEGER
	      MAX-ACCESS  read-write
	      STATUS  current
	      DESCRIPTION
			"Inhibits OMTP12-PLUS WAN10G AU Alarm Indication Signal Alarm
			for the requested port
			-----------------------------
			omtp12PlusInterfaceNumber:
			1 - CLIENT-1
			-----------------------------
			Values:
			1 - Inhibit
			0 - Do Not Inhibit
			-----------------------------"
		::= { omtp12PlusConfigurationEntry 306 }

	omtp12PlusWan10gAuLossOfPointerAlarmInhibit OBJECT-TYPE
	      SYNTAX  INTEGER
	      MAX-ACCESS  read-write
	      STATUS  current
	      DESCRIPTION
			"Inhibits OMTP12-PLUS WAN10G AU Loss Of Pointer Alarm
			for the requested port
			-----------------------------
			omtp12PlusInterfaceNumber:
			1 - CLIENT-1
			-----------------------------
			Values:
			1 - Inhibit
			0 - Do Not Inhibit
			-----------------------------"
		::= { omtp12PlusConfigurationEntry 307 }

	omtp12PlusWan10gMsAlarmIndicationSignalAlarmInhibit OBJECT-TYPE
	      SYNTAX  INTEGER
	      MAX-ACCESS  read-write
	      STATUS  current
	      DESCRIPTION
			"Inhibits OMTP12-PLUS WAN10G MS Alarm Indication Signal Alarm
			for the requested port
			-----------------------------
			omtp12PlusInterfaceNumber:
			1 - CLIENT-1
			-----------------------------
			Values:
			1 - Inhibit
			0 - Do Not Inhibit
			-----------------------------"
		::= { omtp12PlusConfigurationEntry 308 }

	omtp12PlusWan10gMsRemoteErrorIndicationAlarmInhibit OBJECT-TYPE
	      SYNTAX  INTEGER
	      MAX-ACCESS  read-write
	      STATUS  current
	      DESCRIPTION
			"Inhibits OMTP12-PLUS WAN10G MS Remote Error Indication Alarm
			for the requested port
			-----------------------------
			omtp12PlusInterfaceNumber:
			1 - CLIENT-1
			-----------------------------
			Values:
			1 - Inhibit
			0 - Do Not Inhibit
			-----------------------------"
		::= { omtp12PlusConfigurationEntry 309 }

	omtp12PlusWan10gMsRemoteDefectIndicationAlarmInhibit OBJECT-TYPE
	      SYNTAX  INTEGER
	      MAX-ACCESS  read-write
	      STATUS  current
	      DESCRIPTION
			"Inhibits OMTP12-PLUS WAN10G MS Remote Defect Indication Alarm
			for the requested port
			-----------------------------
			omtp12PlusInterfaceNumber:
			1 - CLIENT-1
			-----------------------------
			Values:
			1 - Inhibit
			0 - Do Not Inhibit
			-----------------------------"
		::= { omtp12PlusConfigurationEntry 310 }

	omtp12PlusWan10gMsRemoteFailureIndicationAlarmInhibit OBJECT-TYPE
	      SYNTAX  INTEGER
	      MAX-ACCESS  read-write
	      STATUS  current
	      DESCRIPTION
			"Inhibits OMTP12-PLUS WAN10G MS Remote Failure Indication Alarm
			for the requested port
			-----------------------------
			omtp12PlusInterfaceNumber:
			1 - CLIENT-1
			-----------------------------
			Values:
			1 - Inhibit
			0 - Do Not Inhibit
			-----------------------------"
		::= { omtp12PlusConfigurationEntry 311 }

	omtp12PlusWan10gMsB2ExcessiveErrorAlarmInhibit OBJECT-TYPE
	      SYNTAX  INTEGER
	      MAX-ACCESS  read-write
	      STATUS  current
	      DESCRIPTION
			"Inhibits OMTP12-PLUS WAN10G MS B2 Signal Fail Alarm
			for the requested port
			-----------------------------
			omtp12PlusInterfaceNumber:
			1 - CLIENT-1
			-----------------------------
			Values:
			1 - Inhibit
			0 - Do Not Inhibit
			-----------------------------"
		::= { omtp12PlusConfigurationEntry 312 }

	omtp12PlusWan10gMsB2SignalDegradeAlarmInhibit OBJECT-TYPE
	      SYNTAX  INTEGER
	      MAX-ACCESS  read-write
	      STATUS  current
	      DESCRIPTION
			"Inhibits OMTP12-PLUS WAN10G MS B2 Signal Degrade Alarm
			for the requested port
			-----------------------------
			omtp12PlusInterfaceNumber:
			1 - CLIENT-1
			-----------------------------
			Values:
			1 - Inhibit
			0 - Do Not Inhibit
			-----------------------------"
		::= { omtp12PlusConfigurationEntry 313 }

	omtp12PlusWan10gLossOfSequenceSynchronisationAlarmInhibit OBJECT-TYPE
	      SYNTAX  INTEGER
	      MAX-ACCESS  read-write
	      STATUS  current
	      DESCRIPTION
			"Inhibits OMTP12-PLUS WAN10G Loss Of Sequence Synchronisation Alarm
			for the requested port
			-----------------------------
			omtp12PlusInterfaceNumber:
			1 - CLIENT-1
			-----------------------------
			Values:
			1 - Inhibit
			0 - Do Not Inhibit
			-----------------------------"
		::= { omtp12PlusConfigurationEntry 314 }

	omtp12PlusWan10gHigherOrderPathPayloadLabelMismatchAlarmInhibit OBJECT-TYPE
	      SYNTAX  INTEGER
	      MAX-ACCESS  read-write
	      STATUS  current
	      DESCRIPTION
			"Inhibits OMTP12-PLUS WAN10G Higher Order Path Payload Label Mismatch Alarm
			for the requested port
			-----------------------------
			omtp12PlusInterfaceNumber:
			1 - CLIENT-1
			-----------------------------
			Values:
			1 - Inhibit
			0 - Do Not Inhibit
			-----------------------------"
		::= { omtp12PlusConfigurationEntry 315 }

	omtp12PlusWan10gHigherOrderPathUnequippedAlarmInhibit OBJECT-TYPE
	      SYNTAX  INTEGER
	      MAX-ACCESS  read-write
	      STATUS  current
	      DESCRIPTION
			"Inhibits OMTP12-PLUS WAN10G Higher Order Path Unequipped Alarm
			for the requested port
			-----------------------------
			omtp12PlusInterfaceNumber:
			1 - CLIENT-1
			-----------------------------
			Values:
			1 - Inhibit
			0 - Do Not Inhibit
			-----------------------------"
		::= { omtp12PlusConfigurationEntry 316 }

	omtp12PlusLan10gLossOfSignalAlarmInhibit OBJECT-TYPE
	      SYNTAX  INTEGER
	      MAX-ACCESS  read-write
	      STATUS  current
	      DESCRIPTION
			"Inhibits OMTP12-PLUS LAN10G Loss Of Signal Alarm
			for the requested port
			-----------------------------
			omtp12PlusInterfaceNumber:
			1 - CLIENT-1
			-----------------------------
			Values:
			1 - Inhibit
			0 - Do Not Inhibit
			-----------------------------"
		::= { omtp12PlusConfigurationEntry 331 }

	omtp12PlusLan10gLossOfSignalSyncAlarmInhibit OBJECT-TYPE
	      SYNTAX  INTEGER
	      MAX-ACCESS  read-write
	      STATUS  current
	      DESCRIPTION
			"Inhibits OMTP12-PLUS LAN10G Loss Of Signal Sync Alarm
			for the requested port
			-----------------------------
			omtp12PlusInterfaceNumber:
			1 - CLIENT-1
			-----------------------------
			Values:
			1 - Inhibit
			0 - Do Not Inhibit
			-----------------------------"
		::= { omtp12PlusConfigurationEntry 332 }

	omtp12PlusLan10gLinkFailureAlarmInhibit OBJECT-TYPE
	      SYNTAX  INTEGER
	      MAX-ACCESS  read-write
	      STATUS  current
	      DESCRIPTION
			"Inhibits OMTP12-PLUS LAN10G Link Failure Alarm
			for the requested port
			-----------------------------
			omtp12PlusInterfaceNumber:
			1 - CLIENT-1
			-----------------------------
			Values:
			1 - Inhibit
			0 - Do Not Inhibit
			-----------------------------"
		::= { omtp12PlusConfigurationEntry 333 }

	omtp12PlusLan10gFrameCheckSequenceAlarmInhibit OBJECT-TYPE
	      SYNTAX  INTEGER
	      MAX-ACCESS  read-write
	      STATUS  current
	      DESCRIPTION
			"Inhibits OMTP12-PLUS LAN10G Frame Check Sequence Alarm
			for the requested port
			-----------------------------
			omtp12PlusInterfaceNumber:
			1 - CLIENT-1
			-----------------------------
			Values:
			1 - Inhibit
			0 - Do Not Inhibit
			-----------------------------"
		::= { omtp12PlusConfigurationEntry 334 }

	omtp12PlusLan10gCarrierStatusAlarmInhibit OBJECT-TYPE
	      SYNTAX  INTEGER
	      MAX-ACCESS  read-write
	      STATUS  current
	      DESCRIPTION
			"Inhibits OMTP12-PLUS LAN10G Carrier Status Alarm
			for the requested port
			-----------------------------
			omtp12PlusInterfaceNumber:
			1 - CLIENT-1
			-----------------------------
			Values:
			1 - Inhibit
			0 - Do Not Inhibit
			-----------------------------"
		::= { omtp12PlusConfigurationEntry 335 }

	omtp12PlusLan10gHighBerAlarmInhibit OBJECT-TYPE
	      SYNTAX  INTEGER
	      MAX-ACCESS  read-write
	      STATUS  current
	      DESCRIPTION
			"Inhibits OMTP12-PLUS LAN10G High Ber Alarm
			for the requested port
			-----------------------------
			omtp12PlusInterfaceNumber:
			1 - CLIENT-1
			-----------------------------
			Values:
			1 - Inhibit
			0 - Do Not Inhibit
			-----------------------------"
		::= { omtp12PlusConfigurationEntry 336 }

	omtp12PlusLan10gLocalFaultAlarmInhibit OBJECT-TYPE
	      SYNTAX  INTEGER
	      MAX-ACCESS  read-write
	      STATUS  current
	      DESCRIPTION
			"Inhibits OMTP12-PLUS LAN10G Local Fault Alarm
			for the requested port
			-----------------------------
			omtp12PlusInterfaceNumber:
			1 - CLIENT-1
			-----------------------------
			Values:
			1 - Inhibit
			0 - Do Not Inhibit
			-----------------------------"
		::= { omtp12PlusConfigurationEntry 337 }

	omtp12PlusLan10gRemoteFaultAlarmInhibit OBJECT-TYPE
	      SYNTAX  INTEGER
	      MAX-ACCESS  read-write
	      STATUS  current
	      DESCRIPTION
			"Inhibits OMTP12-PLUS LAN10G Remote Fault Alarm
			for the requested port
			-----------------------------
			omtp12PlusInterfaceNumber:
			1 - CLIENT-1
			-----------------------------
			Values:
			1 - Inhibit
			0 - Do Not Inhibit
			-----------------------------"
		::= { omtp12PlusConfigurationEntry 338 }

	omtp12PlusFcTransmitDisparityInversionDefectAlarmInhibit OBJECT-TYPE
	      SYNTAX  INTEGER
	      MAX-ACCESS  read-write
	      STATUS  current
	      DESCRIPTION
			"Inhibits OMTP12-PLUS FC Transmit Display Invert Alarm
			for the requested port
			-----------------------------
			omtp12PlusInterfaceNumber:
			1 - CLIENT-1
			-----------------------------
			Values:
			1 - Inhibit
			0 - Do Not Inhibit
			-----------------------------"
		::= { omtp12PlusConfigurationEntry 351 }

	omtp12PlusFcTransmitDigitalLossOfLinkDefectAlarmInhibit OBJECT-TYPE
	      SYNTAX  INTEGER
	      MAX-ACCESS  read-write
	      STATUS  current
	      DESCRIPTION
			"Inhibits OMTP12-PLUS FC Transmit Dlolb Alarm
			for the requested port
			-----------------------------
			omtp12PlusInterfaceNumber:
			1 - CLIENT-1
			-----------------------------
			Values:
			1 - Inhibit
			0 - Do Not Inhibit
			-----------------------------"
		::= { omtp12PlusConfigurationEntry 352 }

	omtp12PlusFcTrasnmitLossofSynchronizationDefectAlarmInhibit OBJECT-TYPE
	      SYNTAX  INTEGER
	      MAX-ACCESS  read-write
	      STATUS  current
	      DESCRIPTION
			"Inhibits OMTP12-PLUS FC Transmit Sync Alarm
			for the requested port
			-----------------------------
			omtp12PlusInterfaceNumber:
			1 - CLIENT-1
			-----------------------------
			Values:
			1 - Inhibit
			0 - Do Not Inhibit
			-----------------------------"
		::= { omtp12PlusConfigurationEntry 353 }

	omtp12PlusFcReceiveDigitalLossofLinkDefectAlarmInhibit OBJECT-TYPE
	      SYNTAX  INTEGER
	      MAX-ACCESS  read-write
	      STATUS  current
	      DESCRIPTION
			"Inhibits OMTP12-PLUS FC Receive Dlolb Alarm
			for the requested port
			-----------------------------
			omtp12PlusInterfaceNumber:
			1 - CLIENT-1
			-----------------------------
			Values:
			1 - Inhibit
			0 - Do Not Inhibit
			-----------------------------"
		::= { omtp12PlusConfigurationEntry 354 }

	omtp12PlusFcReceiveLossofSynchronizationDefectAlarmInhibit OBJECT-TYPE
	      SYNTAX  INTEGER
	      MAX-ACCESS  read-write
	      STATUS  current
	      DESCRIPTION
			"Inhibits OMTP12-PLUS FC Receive Sync Alarm
			for the requested port
			-----------------------------
			omtp12PlusInterfaceNumber:
			1 - CLIENT-1
			-----------------------------
			Values:
			1 - Inhibit
			0 - Do Not Inhibit
			-----------------------------"
		::= { omtp12PlusConfigurationEntry 355 }

	omtp12PlusFcReceiveTransitionDetectDefectAlarmInhibit OBJECT-TYPE
	      SYNTAX  INTEGER
	      MAX-ACCESS  read-write
	      STATUS  current
	      DESCRIPTION
			"Inhibits OMTP12-PLUS FC Receive Xdet Alarm
			for the requested port
			-----------------------------
			omtp12PlusInterfaceNumber:
			1 - CLIENT-1
			-----------------------------
			Values:
			1 - Inhibit
			0 - Do Not Inhibit
			-----------------------------"
		::= { omtp12PlusConfigurationEntry 356 }

	omtp12PlusFcReceiveAnalogLossofSignalDefectAlarmInhibit OBJECT-TYPE
	      SYNTAX  INTEGER
	      MAX-ACCESS  read-write
	      STATUS  current
	      DESCRIPTION
			"Inhibits OMTP12-PLUS FC Receive Asd Alarm
			for the requested port
			-----------------------------
			omtp12PlusInterfaceNumber:
			1 - CLIENT-1
			-----------------------------
			Values:
			1 - Inhibit
			0 - Do Not Inhibit
			-----------------------------"
		::= { omtp12PlusConfigurationEntry 357 }

	omtp12PlusFcReceiveLineCodeViolationDefectAlarmInhibit OBJECT-TYPE
	      SYNTAX  INTEGER
	      MAX-ACCESS  read-write
	      STATUS  current
	      DESCRIPTION
			"Inhibits OMTP12-PLUS FC Receive Lcv Alarm
			for the requested port
			-----------------------------
			omtp12PlusInterfaceNumber:
			1 - CLIENT-1
			-----------------------------
			Values:
			1 - Inhibit
			0 - Do Not Inhibit
			-----------------------------"
		::= { omtp12PlusConfigurationEntry 358 }

	omtp12PlusGfpCsfSignalFailAlarmInhibit OBJECT-TYPE
	      SYNTAX  INTEGER
	      MAX-ACCESS  read-write
	      STATUS  current
	      DESCRIPTION
			"Inhibits OMTP12-PLUS GFP Csf Signal Failure Alarm
			for the requested port
			-----------------------------
			omtp12PlusInterfaceNumber:
			1 - CLIENT-1
			-----------------------------
			Values:
			1 - Inhibit
			0 - Do Not Inhibit
			-----------------------------"
		::= { omtp12PlusConfigurationEntry 371 }

	omtp12PlusGfpCsfLinkFailAlarmInhibit OBJECT-TYPE
	      SYNTAX  INTEGER
	      MAX-ACCESS  read-write
	      STATUS  current
	      DESCRIPTION
			"Inhibits OMTP12-PLUS GFP Csf Link Failure Alarm
			for the requested port
			-----------------------------
			omtp12PlusInterfaceNumber:
			1 - CLIENT-1
			-----------------------------
			Values:
			1 - Inhibit
			0 - Do Not Inhibit
			-----------------------------"
		::= { omtp12PlusConfigurationEntry 372 }

	omtp12PlusGfpCoreHeaderErrorAlarmInhibit OBJECT-TYPE
	      SYNTAX  INTEGER
	      MAX-ACCESS  read-write
	      STATUS  current
	      DESCRIPTION
			"Inhibits OMTP12-PLUS GFP Core Header Error Alarm
			for the requested port
			-----------------------------
			omtp12PlusInterfaceNumber:
			1 - CLIENT-1
			-----------------------------
			Values:
			1 - Inhibit
			0 - Do Not Inhibit
			-----------------------------"
		::= { omtp12PlusConfigurationEntry 373 }

	omtp12PlusGfpExtentionHeaderErrorAlarmInhibit OBJECT-TYPE
	      SYNTAX  INTEGER
	      MAX-ACCESS  read-write
	      STATUS  current
	      DESCRIPTION
			"Inhibits OMTP12-PLUS GFP Extention Header Error Alarm
			for the requested port
			-----------------------------
			omtp12PlusInterfaceNumber:
			1 - CLIENT-1
			-----------------------------
			Values:
			1 - Inhibit
			0 - Do Not Inhibit
			-----------------------------"
		::= { omtp12PlusConfigurationEntry 374 }

	omtp12PlusXfpInputPowerFailureAlarmSeverity OBJECT-TYPE
	      SYNTAX  DisplayString
	      MAX-ACCESS  read-write
	      STATUS  current
	      DESCRIPTION
			"Set or Get the alarm severity level of the
			OMTP12-PLUS XFP Input Power Failure Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 401 }

	omtp12PlusXfpOutputPowerFailureAlarmSeverity OBJECT-TYPE
	      SYNTAX  DisplayString
	      MAX-ACCESS  read-write
	      STATUS  current
	      DESCRIPTION
			"Set or Get the alarm severity level of the
			OMTP12-PLUS XFP Output Power Failure Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 402 }

	omtp12PlusXfpHighTemperatureAlarmSeverity OBJECT-TYPE
	      SYNTAX  DisplayString
	      MAX-ACCESS  read-write
	      STATUS  current
	      DESCRIPTION
			"Set or Get the alarm severity level of the
			OMTP12-PLUS XFP High Temperature Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 403 }

	omtp12PlusXfpLowTemperatureAlarmSeverity OBJECT-TYPE
	      SYNTAX  DisplayString
	      MAX-ACCESS  read-write
	      STATUS  current
	      DESCRIPTION
			"Set or Get the alarm severity level of the
			OMTP12-PLUS XFP Low Temperature Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 404 }

	omtp12PlusXfpHighTemperatureWarningSeverity OBJECT-TYPE
	      SYNTAX  DisplayString
	      MAX-ACCESS  read-write
	      STATUS  current
	      DESCRIPTION
			"Set or Get the alarm severity level of the
			OMTP12-PLUS XFP High Temperature Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 405 }

	omtp12PlusXfpLowTemperatureWarningSeverity OBJECT-TYPE
	      SYNTAX  DisplayString
	      MAX-ACCESS  read-write
	      STATUS  current
	      DESCRIPTION
			"Set or Get the alarm severity level of the
			OMTP12-PLUS XFP Low Temperature Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 406 }

	omtp12PlusXfpHighBiasCurrentAlarmSeverity OBJECT-TYPE
	      SYNTAX  DisplayString
	      MAX-ACCESS  read-write
	      STATUS  current
	      DESCRIPTION
			"Set or Get the alarm severity level of the
			OMTP12-PLUS XFP High Bias Current Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 407 }

	omtp12PlusXfpLowBiasCurrentAlarmSeverity OBJECT-TYPE
	      SYNTAX  DisplayString
	      MAX-ACCESS  read-write
	      STATUS  current
	      DESCRIPTION
			"Set or Get the alarm severity level of the
			OMTP12-PLUS XFP Low Bias Current Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 408 }

	omtp12PlusXfpHighBiasCurrentWarningSeverity OBJECT-TYPE
	      SYNTAX  DisplayString
	      MAX-ACCESS  read-write
	      STATUS  current
	      DESCRIPTION
			"Set or Get the alarm severity level of the
			OMTP12-PLUS XFP High Bias Current Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 409 }

	omtp12PlusXfpLowBiasCurrentWarningSeverity OBJECT-TYPE
	      SYNTAX  DisplayString
	      MAX-ACCESS  read-write
	      STATUS  current
	      DESCRIPTION
			"Set or Get the alarm severity level of the
			OMTP12-PLUS XFP Low Bias Current Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 410 }

	omtp12PlusXfpInputHighPowerAlarmSeverity OBJECT-TYPE
	      SYNTAX  DisplayString
	      MAX-ACCESS  read-write
	      STATUS  current
	      DESCRIPTION
			"Set or Get the alarm severity level of the
			OMTP12-PLUS XFP Input High Power Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 411 }

	omtp12PlusXfpInputLowPowerAlarmSeverity OBJECT-TYPE
	      SYNTAX  DisplayString
	      MAX-ACCESS  read-write
	      STATUS  current
	      DESCRIPTION
			"Set or Get the alarm severity level of the
			OMTP12-PLUS XFP Input Low Power Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 412 }

	omtp12PlusXfpInputHighPowerWarningSeverity OBJECT-TYPE
	      SYNTAX  DisplayString
	      MAX-ACCESS  read-write
	      STATUS  current
	      DESCRIPTION
			"Set or Get the alarm severity level of the
			OMTP12-PLUS XFP Input High Power Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 413 }

	omtp12PlusXfpInputLowPowerWarningSeverity OBJECT-TYPE
	      SYNTAX  DisplayString
	      MAX-ACCESS  read-write
	      STATUS  current
	      DESCRIPTION
			"Set or Get the alarm severity level of the
			OMTP12-PLUS XFP Input Low Power Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 414 }

	omtp12PlusXfpOutputHighPowerAlarmSeverity OBJECT-TYPE
	      SYNTAX  DisplayString
	      MAX-ACCESS  read-write
	      STATUS  current
	      DESCRIPTION
			"Set or Get the alarm severity level of the
			OMTP12-PLUS XFP Output High Power Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 415 }

	omtp12PlusXfpOutputLowPowerAlarmSeverity OBJECT-TYPE
	      SYNTAX  DisplayString
	      MAX-ACCESS  read-write
	      STATUS  current
	      DESCRIPTION
			"Set or Get the alarm severity level of the
			OMTP12-PLUS XFP Output Low Power Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 416 }

	omtp12PlusXfpOutputHighPowerWarningSeverity OBJECT-TYPE
	      SYNTAX  DisplayString
	      MAX-ACCESS  read-write
	      STATUS  current
	      DESCRIPTION
			"Set or Get the alarm severity level of the
			OMTP12-PLUS XFP Output High Power Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 417 }

	omtp12PlusXfpOutputLowPowerWarningSeverity OBJECT-TYPE
	      SYNTAX  DisplayString
	      MAX-ACCESS  read-write
	      STATUS  current
	      DESCRIPTION
			"Set or Get the alarm severity level of the
			OMTP12-PLUS XFP Output Low Power Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 418 }

	omtp12PlusXfpHighSupplyVoltageAlarmSeverity OBJECT-TYPE
	      SYNTAX  DisplayString
	      MAX-ACCESS  read-write
	      STATUS  current
	      DESCRIPTION
			"Set or Get the alarm severity level of the
			OMTP12-PLUS XFP High Supply Voltage Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 419 }

	omtp12PlusXfpLowSupplyVoltageAlarmSeverity OBJECT-TYPE
	      SYNTAX  DisplayString
	      MAX-ACCESS  read-write
	      STATUS  current
	      DESCRIPTION
			"Set or Get the alarm severity level of the
			OMTP12-PLUS XFP Low Supply Voltage Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 420 }

	omtp12PlusXfpHighSupplyVoltageWarningSeverity OBJECT-TYPE
	      SYNTAX  DisplayString
	      MAX-ACCESS  read-write
	      STATUS  current
	      DESCRIPTION
			"Set or Get the alarm severity level of the
			OMTP12-PLUS XFP High Supply Voltage Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 421 }

	omtp12PlusXfpLowSupplyVoltageWarningSeverity OBJECT-TYPE
	      SYNTAX  DisplayString
	      MAX-ACCESS  read-write
	      STATUS  current
	      DESCRIPTION
			"Set or Get the alarm severity level of the
			OMTP12-PLUS XFP Low Supply Voltage Warning   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 422 }

	omtp12PlusXfpPresenceAbsenceNotificationSeverity OBJECT-TYPE
	      SYNTAX  DisplayString
	      MAX-ACCESS  read-write
	      STATUS  current
	      DESCRIPTION
			"Set or Get the alarm severity level of the
			OMTP12-PLUS XFP Presence Absence Notification   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 423 }

	omtp12PlusOtuLossOfSignalAlarmSeverity OBJECT-TYPE
	      SYNTAX  DisplayString
	      MAX-ACCESS  read-write
	      STATUS  current
	      DESCRIPTION
			"Set or Get the alarm severity level of the
			OMTP12-PLUS OTU Loss Of Signal Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 431 }

	omtp12PlusOtuLossOfFrameAlarmSeverity OBJECT-TYPE
	      SYNTAX  DisplayString
	      MAX-ACCESS  read-write
	      STATUS  current
	      DESCRIPTION
			"Set or Get the alarm severity level of the
			OMTP12-PLUS OTU Loss Of Frame Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 432 }

	omtp12PlusOtuOutOfFrameAlarmSeverity OBJECT-TYPE
	      SYNTAX  DisplayString
	      MAX-ACCESS  read-write
	      STATUS  current
	      DESCRIPTION
			"Set or Get the alarm severity level of the
			OMTP12-PLUS OTU Out Of Frame Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 433 }

	omtp12PlusOtuLossOfMultiFrameAlarmSeverity OBJECT-TYPE
	      SYNTAX  DisplayString
	      MAX-ACCESS  read-write
	      STATUS  current
	      DESCRIPTION
			"Set or Get the alarm severity level of the
			OMTP12-PLUS OTU Loss Of Multi Frame Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 434 }

	omtp12PlusOtuOutOfMultiFrameAlarmSeverity OBJECT-TYPE
	      SYNTAX  DisplayString
	      MAX-ACCESS  read-write
	      STATUS  current
	      DESCRIPTION
			"Set or Get the alarm severity level of the
			OMTP12-PLUS OTU Out Of Multi Frame Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 435 }

	omtp12PlusOtuSignalFailAlarmSeverity OBJECT-TYPE
	      SYNTAX  DisplayString
	      MAX-ACCESS  read-write
	      STATUS  current
	      DESCRIPTION
			"Set or Get the alarm severity level of the
			OMTP12-PLUS OTU Signal Fail Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 436 }

	omtp12PlusOtuSignalDegradeAlarmSeverity OBJECT-TYPE
	      SYNTAX  DisplayString
	      MAX-ACCESS  read-write
	      STATUS  current
	      DESCRIPTION
			"Set or Get the alarm severity level of the
			OMTP12-PLUS OTU Signal Degrade Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 437 }

	omtp12PlusOtuAlarmIndicationSignalAlarmSeverity OBJECT-TYPE
	      SYNTAX  DisplayString
	      MAX-ACCESS  read-write
	      STATUS  current
	      DESCRIPTION
			"Set or Get the alarm severity level of the
			OMTP12-PLUS OTU Alarm Indication Signal Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 438 }

	omtp12PlusOtuIncomingAlignmentErrorAlarmSeverity OBJECT-TYPE
	      SYNTAX  DisplayString
	      MAX-ACCESS  read-write
	      STATUS  current
	      DESCRIPTION
			"Set or Get the alarm severity level of the
			OMTP12-PLUS OTU Incoming Alignment Error Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 439 }

	omtp12PlusOtuTraceIdentifierMismatchAlarmSeverity OBJECT-TYPE
	      SYNTAX  DisplayString
	      MAX-ACCESS  read-write
	      STATUS  current
	      DESCRIPTION
			"Set or Get the alarm severity level of the
			OMTP12-PLUS OTU Trace Identifier Mismatch Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 440 }

	omtp12PlusOtuBackwardIncomingAlignmentErrorAlarmSeverity OBJECT-TYPE
	      SYNTAX  DisplayString
	      MAX-ACCESS  read-write
	      STATUS  current
	      DESCRIPTION
			"Set or Get the alarm severity level of the
			OMTP12-PLUS OTU Backward Incoming Alignment Error Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 441 }

	omtp12PlusOtuBackwardDefectIndicationAlarmSeverity OBJECT-TYPE
	      SYNTAX  DisplayString
	      MAX-ACCESS  read-write
	      STATUS  current
	      DESCRIPTION
			"Set or Get the alarm severity level of the
			OMTP12-PLUS OTU Backward Defect Indication Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 442 }

	omtp12PlusOduSignalFailAlarmSeverity OBJECT-TYPE
	      SYNTAX  DisplayString
	      MAX-ACCESS  read-write
	      STATUS  current
	      DESCRIPTION
			"Set or Get the alarm severity level of the
			OMTP12-PLUS ODU Signal Fail Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 451 }

	omtp12PlusOduSignalDegradeAlarmSeverity OBJECT-TYPE
	      SYNTAX  DisplayString
	      MAX-ACCESS  read-write
	      STATUS  current
	      DESCRIPTION
			"Set or Get the alarm severity level of the
			OMTP12-PLUS ODU Signal Degrade Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 452 }

	omtp12PlusOduAlarmIndicationSignalAlarmSeverity OBJECT-TYPE
	      SYNTAX  DisplayString
	      MAX-ACCESS  read-write
	      STATUS  current
	      DESCRIPTION
			"Set or Get the alarm severity level of the
			OMTP12-PLUS ODU Alarm Indication Signal Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 453 }

	omtp12PlusOduTcm1IncomingAlignmentErrorAlarmSeverity OBJECT-TYPE
	      SYNTAX  DisplayString
	      MAX-ACCESS  read-write
	      STATUS  current
	      DESCRIPTION
			"Set or Get the alarm severity level of the
			OMTP12-PLUS ODU TCM1 Incoming Alignment Error Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 454 }

	omtp12PlusOduTcm2IncomingAlignmentErrorAlarmSeverity OBJECT-TYPE
	      SYNTAX  DisplayString
	      MAX-ACCESS  read-write
	      STATUS  current
	      DESCRIPTION
			"Set or Get the alarm severity level of the
			OMTP12-PLUS ODU TCM2 Incoming Alignment Error Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 455 }

	omtp12PlusOduTcm3IncomingAlignmentErrorAlarmSeverity OBJECT-TYPE
	      SYNTAX  DisplayString
	      MAX-ACCESS  read-write
	      STATUS  current
	      DESCRIPTION
			"Set or Get the alarm severity level of the
			OMTP12-PLUS ODU TCM3 Incoming Alignment Error Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 456 }

	omtp12PlusOduTcm4IncomingAlignmentErrorAlarmSeverity OBJECT-TYPE
	      SYNTAX  DisplayString
	      MAX-ACCESS  read-write
	      STATUS  current
	      DESCRIPTION
			"Set or Get the alarm severity level of the
			OMTP12-PLUS ODU TCM4 Incoming Alignment Error Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 457 }

	omtp12PlusOduTcm5IncomingAlignmentErrorAlarmSeverity OBJECT-TYPE
	      SYNTAX  DisplayString
	      MAX-ACCESS  read-write
	      STATUS  current
	      DESCRIPTION
			"Set or Get the alarm severity level of the
			OMTP12-PLUS ODU TCM5 Incoming Alignment Error Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 458 }

	omtp12PlusOduTcm6IncomingAlignmentErrorAlarmSeverity OBJECT-TYPE
	      SYNTAX  DisplayString
	      MAX-ACCESS  read-write
	      STATUS  current
	      DESCRIPTION
			"Set or Get the alarm severity level of the
			OMTP12-PLUS ODU TCM6 Incoming Alignment Error Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 459 }

	omtp12PlusOduTraceIdentifierMismatchAlarmSeverity OBJECT-TYPE
	      SYNTAX  DisplayString
	      MAX-ACCESS  read-write
	      STATUS  current
	      DESCRIPTION
			"Set or Get the alarm severity level of the
			OMTP12-PLUS ODU Trace Identifier Mismatch Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 460 }

	omtp12PlusOduLockedDefectAlarmSeverity OBJECT-TYPE
	      SYNTAX  DisplayString
	      MAX-ACCESS  read-write
	      STATUS  current
	      DESCRIPTION
			"Set or Get the alarm severity level of the
			OMTP12-PLUS ODU Locked Defect Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 461 }

	omtp12PlusOduOpenConnectionIndicationAlarmSeverity OBJECT-TYPE
	      SYNTAX  DisplayString
	      MAX-ACCESS  read-write
	      STATUS  current
	      DESCRIPTION
			"Set or Get the alarm severity level of the
			OMTP12-PLUS ODU Open Connection Indication Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 462 }

	omtp12PlusOduBackwardDefectIndicationAlarmSeverity OBJECT-TYPE
	      SYNTAX  DisplayString
	      MAX-ACCESS  read-write
	      STATUS  current
	      DESCRIPTION
			"Set or Get the alarm severity level of the
			OMTP12-PLUS ODU Backward Defect Indication Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 463 }

	omtp12PlusOduTcm1BackwardIncomingAlignmentErrorAlarmSeverity OBJECT-TYPE
	      SYNTAX  DisplayString
	      MAX-ACCESS  read-write
	      STATUS  current
	      DESCRIPTION
			"Set or Get the alarm severity level of the
			OMTP12-PLUS ODU TCM1 Backward Incoming Alignment Error
			Alarm for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 469 }

	omtp12PlusOduTcm2BackwardIncomingAlignmentErrorAlarmSeverity OBJECT-TYPE
	      SYNTAX  DisplayString
	      MAX-ACCESS  read-write
	      STATUS  current
	      DESCRIPTION
			"Set or Get the alarm severity level of the
			OMTP12-PLUS ODU TCM2 Backward Incoming Alignment Error
			Alarm for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 470 }

	omtp12PlusOduTcm3BackwardIncomingAlignmentErrorAlarmSeverity OBJECT-TYPE
	      SYNTAX  DisplayString
	      MAX-ACCESS  read-write
	      STATUS  current
	      DESCRIPTION
			"Set or Get the alarm severity level of the
			OMTP12-PLUS ODU TCM3 Backward Incoming Alignment Error
			Alarm for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 471 }

	omtp12PlusOduTcm4BackwardIncomingAlignmentErrorAlarmSeverity OBJECT-TYPE
	      SYNTAX  DisplayString
	      MAX-ACCESS  read-write
	      STATUS  current
	      DESCRIPTION
			"Set or Get the alarm severity level of the
			OMTP12-PLUS ODU TCM4 Backward Incoming Alignment Error
			Alarm for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 472 }

	omtp12PlusOduTcm5BackwardIncomingAlignmentErrorAlarmSeverity OBJECT-TYPE
	      SYNTAX  DisplayString
	      MAX-ACCESS  read-write
	      STATUS  current
	      DESCRIPTION
			"Set or Get the alarm severity level of the
			OMTP12-PLUS ODU TCM5 Backward Incoming Alignment Error
			Alarm for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 473 }

	omtp12PlusOduTcm6BackwardIncomingAlignmentErrorAlarmSeverity OBJECT-TYPE
	      SYNTAX  DisplayString
	      MAX-ACCESS  read-write
	      STATUS  current
	      DESCRIPTION
			"Set or Get the alarm severity level of the
			OMTP12-PLUS ODU TCM6 Backward Incoming Alignment Error
			Alarm for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 474 }

	omtp12PlusOpuPayloadMismatchAlarmSeverity OBJECT-TYPE
	      SYNTAX  DisplayString
	      MAX-ACCESS  read-write
	      STATUS  current
	      DESCRIPTION
			"Set or Get the alarm severity level of the
			OMTP12-PLUS Opu Payload Mismatch Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 475 }

	omtp12PlusOchLossOfPayloadAlarmSeverity OBJECT-TYPE
	      SYNTAX  DisplayString
	      MAX-ACCESS  read-write
	      STATUS  current
	      DESCRIPTION
			"Set or Get the alarm severity level of the
			OMTP12-PLUS Och Loss Of Payload Alarm   
			for requested port
 			-----------------------------
			omtp12PlusInterfaceNumber:
			1 - CLIENT-1
			2 - LINE-1
			3 - LINE-2
			-----------------------------
			Values:
			1 - Critical
			2 - Major
			3 - Minor
			4 - Deferred
			-----------------------------"
		::= { omtp12PlusConfigurationEntry 476 }

	omtp12PlusSdhLossOfSignalAlarmSeverity OBJECT-TYPE
	      SYNTAX  DisplayString
	      MAX-ACCESS  read-write
	      STATUS  current
	      DESCRIPTION
			"Set or Get the alarm severity level of the
			OMTP12-PLUS SDH Loss Of Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 481 }

	omtp12PlusSdhOutOfFrameAlarmSeverity OBJECT-TYPE
	      SYNTAX  DisplayString
	      MAX-ACCESS  read-write
	      STATUS  current
	      DESCRIPTION
			"Set or Get the alarm severity level of the
			OMTP12-PLUS SDH Out Of Frame Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 482 }

	omtp12PlusSdhLossOfFrameAlarmSeverity OBJECT-TYPE
	      SYNTAX  DisplayString
	      MAX-ACCESS  read-write
	      STATUS  current
	      DESCRIPTION
			"Set or Get the alarm severity level of the
			OMTP12-PLUS SDH Loss Of Frame Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 483 }

	omtp12PlusSdhRsAlarmIndicationSignalAlarmSeverity OBJECT-TYPE
	      SYNTAX  DisplayString
	      MAX-ACCESS  read-write
	      STATUS  current
	      DESCRIPTION
			"Set or Get the alarm severity level of the
			OMTP12-PLUS SDH RS Alarm Indication Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 484 }

	omtp12PlusSdhRsTraceIdentifierMismatchAlarmSeverity OBJECT-TYPE
	      SYNTAX  DisplayString
	      MAX-ACCESS  read-write
	      STATUS  current
	      DESCRIPTION
			"Set or Get the alarm severity level of the
			OMTP12-PLUS SDH RS Trace Identifier Mismatch Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 485 }

	omtp12PlusSdhAuAlarmIndicationSignalAlarmSeverity OBJECT-TYPE
	      SYNTAX  DisplayString
	      MAX-ACCESS  read-write
	      STATUS  current
	      DESCRIPTION
			"Set or Get the alarm severity level of the
			OMTP12-PLUS SDH AU Alarm Indication Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 486 }

	omtp12PlusSdhAuLossOfPointerAlarmSeverity OBJECT-TYPE
	      SYNTAX  DisplayString
	      MAX-ACCESS  read-write
	      STATUS  current
	      DESCRIPTION
			"Set or Get the alarm severity level of the
			OMTP12-PLUS SDH AU Loss Of Pointer Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 487 }

	omtp12PlusSdhMsAlarmIndicationSignalAlarmSeverity OBJECT-TYPE
	      SYNTAX  DisplayString
	      MAX-ACCESS  read-write
	      STATUS  current
	      DESCRIPTION
			"Set or Get the alarm severity level of the
			OMTP12-PLUS SDH MS Alarm Indication Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 488 }

	omtp12PlusSdhMsRemoteErrorIndicationAlarmSeverity OBJECT-TYPE
	      SYNTAX  DisplayString
	      MAX-ACCESS  read-write
	      STATUS  current
	      DESCRIPTION
			"Set or Get the alarm severity level of the
			OMTP12-PLUS SDH MS Remote Error Indication Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 489 }

	omtp12PlusSdhMsRemoteDefectIndicationAlarmSeverity OBJECT-TYPE
	      SYNTAX  DisplayString
	      MAX-ACCESS  read-write
	      STATUS  current
	      DESCRIPTION
			"Set or Get the alarm severity level of the
			OMTP12-PLUS SDH MS Remote Defect Indication Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 490 }

	omtp12PlusSdhMsRemoteFailureIndicationAlarmSeverity OBJECT-TYPE
	      SYNTAX  DisplayString
	      MAX-ACCESS  read-write
	      STATUS  current
	      DESCRIPTION
			"Set or Get the alarm severity level of the
			OMTP12-PLUS SDH MS Remote Failure Indication Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 491 }

	omtp12PlusSdhMsB2ExcessiveErrorAlarmSeverity OBJECT-TYPE
	      SYNTAX  DisplayString
	      MAX-ACCESS  read-write
	      STATUS  current
	      DESCRIPTION
			"Set or Get the alarm severity level of the
			OMTP12-PLUS SDH MS B2 Signal Fail Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 492 }

	omtp12PlusSdhMsB2SignalDegradeAlarmSeverity OBJECT-TYPE
	      SYNTAX  DisplayString
	      MAX-ACCESS  read-write
	      STATUS  current
	      DESCRIPTION
			"Set or Get the alarm severity level of the
			OMTP12-PLUS SDH MS B2 Signal Degrade Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 493 }

	omtp12PlusSdhLossOfSequenceSynchronisationAlarmSeverity OBJECT-TYPE
	      SYNTAX  DisplayString
	      MAX-ACCESS  read-write
	      STATUS  current
	      DESCRIPTION
			"Set or Get the alarm severity level of the
			OMTP12-PLUS SDH Loss Of Sequence Synchronisation Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 494 }

	omtp12PlusSdhHigherOrderPathPayloadLabelMismatchAlarmSeverity OBJECT-TYPE
	      SYNTAX  DisplayString
	      MAX-ACCESS  read-write
	      STATUS  current
	      DESCRIPTION
			"Set or Get the alarm severity level of the
			OMTP12-PLUS SDH Higher Order Path Payload Label Mismatch Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 495 }

	omtp12PlusSdhHigherOrderPathUnequippedAlarmSeverity OBJECT-TYPE
	      SYNTAX  DisplayString
	      MAX-ACCESS  read-write
	      STATUS  current
	      DESCRIPTION
			"Set or Get the alarm severity level of the
			OMTP12-PLUS SDH Higher Order Path Unequipped Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 496 }

	omtp12PlusWan10gLossOfSignalAlarmSeverity OBJECT-TYPE
	      SYNTAX  DisplayString
	      MAX-ACCESS  read-write
	      STATUS  current
	      DESCRIPTION
			"Set or Get the alarm severity level of the
			OMTP12-PLUS WAN10G Loss Of Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 501 }

	omtp12PlusWan10gOutOfFrameAlarmSeverity OBJECT-TYPE
	      SYNTAX  DisplayString
	      MAX-ACCESS  read-write
	      STATUS  current
	      DESCRIPTION
			"Set or Get the alarm severity level of the
			OMTP12-PLUS WAN10G Out Of Frame Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 502 }

	omtp12PlusWan10gLossOfFrameAlarmSeverity OBJECT-TYPE
	      SYNTAX  DisplayString
	      MAX-ACCESS  read-write
	      STATUS  current
	      DESCRIPTION
			"Set or Get the alarm severity level of the
			OMTP12-PLUS WAN10G Loss Of Frame Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 503 }

	omtp12PlusWan10gRsAlarmIndicationSignalAlarmSeverity OBJECT-TYPE
	      SYNTAX  DisplayString
	      MAX-ACCESS  read-write
	      STATUS  current
	      DESCRIPTION
			"Set or Get the alarm severity level of the
			OMTP12-PLUS WAN10G RS Alarm Indication Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 504 }

	omtp12PlusWan10gRsTraceIdentifierMismatchAlarmSeverity OBJECT-TYPE
	      SYNTAX  DisplayString
	      MAX-ACCESS  read-write
	      STATUS  current
	      DESCRIPTION
			"Set or Get the alarm severity level of the
			OMTP12-PLUS WAN10G RS Trace Identifier Mismatch Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 505 }

	omtp12PlusWan10gAuAlarmIndicationSignalAlarmSeverity OBJECT-TYPE
	      SYNTAX  DisplayString
	      MAX-ACCESS  read-write
	      STATUS  current
	      DESCRIPTION
			"Set or Get the alarm severity level of the
			OMTP12-PLUS WAN10G AU Alarm Indication Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 506 }

	omtp12PlusWan10gAuLossOfPointerAlarmSeverity OBJECT-TYPE
	      SYNTAX  DisplayString
	      MAX-ACCESS  read-write
	      STATUS  current
	      DESCRIPTION
			"Set or Get the alarm severity level of the
			OMTP12-PLUS WAN10G AU Loss Of Pointer Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 507 }

	omtp12PlusWan10gMsAlarmIndicationSignalAlarmSeverity OBJECT-TYPE
	      SYNTAX  DisplayString
	      MAX-ACCESS  read-write
	      STATUS  current
	      DESCRIPTION
			"Set or Get the alarm severity level of the
			OMTP12-PLUS WAN10G MS Alarm Indication Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 508 }

	omtp12PlusWan10gMsRemoteErrorIndicationAlarmSeverity OBJECT-TYPE
	      SYNTAX  DisplayString
	      MAX-ACCESS  read-write
	      STATUS  current
	      DESCRIPTION
			"Set or Get the alarm severity level of the
			OMTP12-PLUS WAN10G MS Remote Error Indication Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 509 }

	omtp12PlusWan10gMsRemoteDefectIndicationAlarmSeverity OBJECT-TYPE
	      SYNTAX  DisplayString
	      MAX-ACCESS  read-write
	      STATUS  current
	      DESCRIPTION
			"Set or Get the alarm severity level of the
			OMTP12-PLUS WAN10G MS Remote Defect Indication Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 510 }

	omtp12PlusWan10gMsRemoteFailureIndicationAlarmSeverity OBJECT-TYPE
	      SYNTAX  DisplayString
	      MAX-ACCESS  read-write
	      STATUS  current
	      DESCRIPTION
			"Set or Get the alarm severity level of the
			OMTP12-PLUS WAN10G MS Remote Failure Indication Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 511 }

	omtp12PlusWan10gMsB2ExcessiveErrorAlarmSeverity OBJECT-TYPE
	      SYNTAX  DisplayString
	      MAX-ACCESS  read-write
	      STATUS  current
	      DESCRIPTION
			"Set or Get the alarm severity level of the
			OMTP12-PLUS WAN10G MS B2 Signal Fail Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 512 }

	omtp12PlusWan10gMsB2SignalDegradeAlarmSeverity OBJECT-TYPE
	      SYNTAX  DisplayString
	      MAX-ACCESS  read-write
	      STATUS  current
	      DESCRIPTION
			"Set or Get the alarm severity level of the
			OMTP12-PLUS WAN10G MS B2 Signal Degrade Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 513 }

	omtp12PlusWan10gLossOfSequenceSynchronisationAlarmSeverity OBJECT-TYPE
	      SYNTAX  DisplayString
	      MAX-ACCESS  read-write
	      STATUS  current
	      DESCRIPTION
			"Set or Get the alarm severity level of the
			OMTP12-PLUS WAN10G Loss Of Sequence Synchronisation Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 514 }

	omtp12PlusWan10gHigherOrderPathPayloadLabelMismatchAlarmSeverity OBJECT-TYPE
	      SYNTAX  DisplayString
	      MAX-ACCESS  read-write
	      STATUS  current
	      DESCRIPTION
			"Set or Get the alarm severity level of the
			OMTP12-PLUS WAN10G Higher Order Path Payload Label 
			Mismatch Alarm for requested port
 			-----------------------------
			omtp12PlusInterfaceNumber:
			1 - CLIENT-1
			-----------------------------
			Values:
			1 - Critical
			2 - Major
			3 - Minor
			4 - Deferred
			-----------------------------"
		::= { omtp12PlusConfigurationEntry 515 }

	omtp12PlusWan10gHigherOrderPathUnequippedAlarmSeverity OBJECT-TYPE
	      SYNTAX  DisplayString
	      MAX-ACCESS  read-write
	      STATUS  current
	      DESCRIPTION
			"Set or Get the alarm severity level of the
			OMTP12-PLUS WAN10G Higher Order Path Unequipped Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 516 }

	omtp12PlusLan10gLossOfSignalAlarmSeverity OBJECT-TYPE
	      SYNTAX  DisplayString
	      MAX-ACCESS  read-write
	      STATUS  current
	      DESCRIPTION
			"Set or Get the alarm severity level of the
			OMTP12-PLUS LAN10G Loss Of Signal Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 531 }

	omtp12PlusLan10gLossOfSignalSyncAlarmSeverity OBJECT-TYPE
	      SYNTAX  DisplayString
	      MAX-ACCESS  read-write
	      STATUS  current
	      DESCRIPTION
			"Set or Get the alarm severity level of the
			OMTP12-PLUS LAN10G Loss Of Signal Sync Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 532 }

	omtp12PlusLan10gLinkFailureAlarmSeverity OBJECT-TYPE
	      SYNTAX  DisplayString
	      MAX-ACCESS  read-write
	      STATUS  current
	      DESCRIPTION
			"Set or Get the alarm severity level of the
			OMTP12-PLUS LAN10G Link Failure Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 533 }

	omtp12PlusLan10gFrameCheckSequenceAlarmSeverity OBJECT-TYPE
	      SYNTAX  DisplayString
	      MAX-ACCESS  read-write
	      STATUS  current
	      DESCRIPTION
			"Set or Get the alarm severity level of the
			OMTP12-PLUS LAN10G Frame Check Sequence Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 534 }

	omtp12PlusLan10gCarrierStatusAlarmSeverity OBJECT-TYPE
	      SYNTAX  DisplayString
	      MAX-ACCESS  read-write
	      STATUS  current
	      DESCRIPTION
			"Set or Get the alarm severity level of the
			OMTP12-PLUS LAN10G Carrier Status Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 535 }

	omtp12PlusLan10gHighBerAlarmSeverity OBJECT-TYPE
	      SYNTAX  DisplayString
	      MAX-ACCESS  read-write
	      STATUS  current
	      DESCRIPTION
			"Set or Get the alarm severity level of the
			OMTP12-PLUS LAN10G High Ber Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 536 }

	omtp12PlusLan10gLocalFaultAlarmSeverity OBJECT-TYPE
	      SYNTAX  DisplayString
	      MAX-ACCESS  read-write
	      STATUS  current
	      DESCRIPTION
			"Set or Get the alarm severity level of the
			OMTP12-PLUS LAN10G Local Fault Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 537 }

	omtp12PlusLan10gRemoteFaultAlarmSeverity OBJECT-TYPE
	      SYNTAX  DisplayString
	      MAX-ACCESS  read-write
	      STATUS  current
	      DESCRIPTION
			"Set or Get the alarm severity level of the
			OMTP12-PLUS LAN10G Remote Fault Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 538 }

	omtp12PlusFcTransmitDisparityInversionDefectAlarmSeverity OBJECT-TYPE
	      SYNTAX  DisplayString
	      MAX-ACCESS  read-write
	      STATUS  current
	      DESCRIPTION
			"Set or Get the alarm severity level of the
			OMTP12-PLUS FC Transmit Display Invert Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 551 }

	omtp12PlusFcTransmitDigitalLossOfLinkDefectAlarmSeverity OBJECT-TYPE
	      SYNTAX  DisplayString
	      MAX-ACCESS  read-write
	      STATUS  current
	      DESCRIPTION
			"Set or Get the alarm severity level of the
			OMTP12-PLUS FC Transmit Dlolb Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 552 }

	omtp12PlusFcTrasnmitLossofSynchronizationDefectAlarmSeverity OBJECT-TYPE
	      SYNTAX  DisplayString
	      MAX-ACCESS  read-write
	      STATUS  current
	      DESCRIPTION
			"Set or Get the alarm severity level of the
			OMTP12-PLUS FC Transmit Sync Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 553 }

	omtp12PlusFcReceiveDigitalLossofLinkDefectAlarmSeverity OBJECT-TYPE
	      SYNTAX  DisplayString
	      MAX-ACCESS  read-write
	      STATUS  current
	      DESCRIPTION
			"Set or Get the alarm severity level of the
			OMTP12-PLUS FC Receive Dlolb Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 554 }

	omtp12PlusFcReceiveLossofSynchronizationDefectAlarmSeverity OBJECT-TYPE
	      SYNTAX  DisplayString
	      MAX-ACCESS  read-write
	      STATUS  current
	      DESCRIPTION
			"Set or Get the alarm severity level of the
			OMTP12-PLUS FC Receive Sync Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 555 }

	omtp12PlusFcReceiveTransitionDetectDefectAlarmSeverity OBJECT-TYPE
	      SYNTAX  DisplayString
	      MAX-ACCESS  read-write
	      STATUS  current
	      DESCRIPTION
			"Set or Get the alarm severity level of the
			OMTP12-PLUS FC Receive Xdet Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 556 }

	omtp12PlusFcReceiveAnalogLossofSignalDefectAlarmSeverity OBJECT-TYPE
	      SYNTAX  DisplayString
	      MAX-ACCESS  read-write
	      STATUS  current
	      DESCRIPTION
			"Set or Get the alarm severity level of the
			OMTP12-PLUS FC Receive Asd Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 557 }

	omtp12PlusFcReceiveLineCodeViolationDefectAlarmSeverity OBJECT-TYPE
	      SYNTAX  DisplayString
	      MAX-ACCESS  read-write
	      STATUS  current
	      DESCRIPTION
			"Set or Get the alarm severity level of the
			OMTP12-PLUS FC Receive Lcv Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 558 }

	omtp12PlusGfpCsfSignalFailAlarmSeverity OBJECT-TYPE
	      SYNTAX  DisplayString
	      MAX-ACCESS  read-write
	      STATUS  current
	      DESCRIPTION
			"Set or Get the alarm severity level of the
			OMTP12-PLUS GFP Csf Signal Failure Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 571 }

	omtp12PlusGfpCsfLinkFailAlarmSeverity OBJECT-TYPE
	      SYNTAX  DisplayString
	      MAX-ACCESS  read-write
	      STATUS  current
	      DESCRIPTION
			"Set or Get the alarm severity level of the
			OMTP12-PLUS GFP Csf Link Failure Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 572 }

	omtp12PlusGfpCoreHeaderErrorAlarmSeverity OBJECT-TYPE
	      SYNTAX  DisplayString
	      MAX-ACCESS  read-write
	      STATUS  current
	      DESCRIPTION
			"Set or Get the alarm severity level of the
			OMTP12-PLUS GFP Core Header Error Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 573 }

	omtp12PlusGfpExtentionHeaderErrorAlarmSeverity OBJECT-TYPE
	      SYNTAX  DisplayString
	      MAX-ACCESS  read-write
	      STATUS  current
	      DESCRIPTION
			"Set or Get the alarm severity level of the
			OMTP12-PLUS GFP Extention Header Error Alarm   
			for requested port
 			-----------------------------
			omtp12PlusInterfaceNumber:
			1 - CLIENT-1
			-----------------------------
			Values:
			1 - Critical
			2 - Major
			3 - Minor
			4 - Deferred
			-----------------------------"
		::= { omtp12PlusConfigurationEntry 574 }

	omtp12PlusConfigurationTableRowStatus OBJECT-TYPE
              SYNTAX      RowStatus
              MAX-ACCESS  read-write
              STATUS      current
              DESCRIPTION
                      "	This is MIB realted property,
			NOT to be considered as a card property"
              ::= { omtp12PlusConfigurationEntry 575 }	

--*****************************************************************************
--				    ALARMS
--*****************************************************************************

	omtp12PlusAlarmQueryTable OBJECT-TYPE
		SYNTAX SEQUENCE OF Omtp12PlusAlarmQueryEntry
		MAX-ACCESS not-accessible
		STATUS current
		DESCRIPTION
			"Contains Alarm queries of the OMTP12-PLUS card"
	
		::= { omtp12PlusAlarmQuery 1 }

	omtp12PlusAlarmQueryEntry OBJECT-TYPE
		SYNTAX Omtp12PlusAlarmQueryEntry
		MAX-ACCESS not-accessible
		STATUS current
		DESCRIPTION 
			""
		
		INDEX   { node, rack , subRack , slot , omtp12PlusInterfaceNumber}
	
		::= { omtp12PlusAlarmQueryTable 1 }
		
	Omtp12PlusAlarmQueryEntry ::= 
		SEQUENCE {
				omtp12PlusXfpInputPowerFailureAlarm				DisplayString,
				omtp12PlusXfpOutputPowerFailureAlarm				DisplayString,
				omtp12PlusXfpHighTemperatureAlarm				DisplayString, 
				omtp12PlusXfpLowTemperatureAlarm				DisplayString, 
				omtp12PlusXfpHighTemperatureWarning				DisplayString, 
				omtp12PlusXfpLowTemperatureWarning				DisplayString, 
				omtp12PlusXfpHighBiasCurrentAlarm				DisplayString, 
				omtp12PlusXfpLowBiasCurrentAlarm				DisplayString, 
				omtp12PlusXfpHighBiasCurrentWarning				DisplayString, 
				omtp12PlusXfpLowBiasCurrentWarning				DisplayString, 
				omtp12PlusXfpInputHighPowerAlarm				DisplayString, 
				omtp12PlusXfpInputLowPowerAlarm					DisplayString, 
				omtp12PlusXfpInputHighPowerWarning				DisplayString, 
				omtp12PlusXfpInputLowPowerWarning				DisplayString, 
				omtp12PlusXfpOutputHighPowerAlarm				DisplayString, 
				omtp12PlusXfpOutputLowPowerAlarm				DisplayString, 
				omtp12PlusXfpOutputHighPowerWarning				DisplayString, 
				omtp12PlusXfpOutputLowPowerWarning				DisplayString, 
				omtp12PlusXfpHighSupplyVoltageAlarm				DisplayString, 
				omtp12PlusXfpLowSupplyVoltageAlarm				DisplayString, 
				omtp12PlusXfpHighSupplyVoltageWarning				DisplayString, 
				omtp12PlusXfpLowSupplyVoltageWarning				DisplayString, 
				omtp12PlusXfpPresenceAbsenceNotification			DisplayString, 
				omtp12PlusOtuLossOfSignalAlarm					DisplayString, 
				omtp12PlusOtuLossOfFrameAlarm					DisplayString, 
				omtp12PlusOtuOutOfFrameAlarm					DisplayString, 
				omtp12PlusOtuLossOfMultiFrameAlarm				DisplayString, 
				omtp12PlusOtuOutOfMultiFrameAlarm				DisplayString, 
				omtp12PlusOtuSignalFailAlarm					DisplayString, 
				omtp12PlusOtuSignalDegradeAlarm					DisplayString, 
				omtp12PlusOtuAlarmIndicationSignalAlarm				DisplayString, 
				omtp12PlusOtuIncomingAlignmentErrorAlarm			DisplayString, 
				omtp12PlusOtuTraceIdentifierMismatchAlarm			DisplayString, 
				omtp12PlusOtuBackwardIncomingAlignmentErrorAlarm		DisplayString, 
				omtp12PlusOtuBackwardDefectIndicationAlarm			DisplayString, 
				omtp12PlusOduSignalFailAlarm					DisplayString, 
				omtp12PlusOduSignalDegradeAlarm					DisplayString, 
				omtp12PlusOduAlarmIndicationSignalAlarm				DisplayString, 
				omtp12PlusOduTcm1IncomingAlignmentErrorAlarm			DisplayString,
				omtp12PlusOduTcm2IncomingAlignmentErrorAlarm			DisplayString, 
				omtp12PlusOduTcm3IncomingAlignmentErrorAlarm			DisplayString, 
				omtp12PlusOduTcm4IncomingAlignmentErrorAlarm			DisplayString, 
				omtp12PlusOduTcm5IncomingAlignmentErrorAlarm			DisplayString, 
				omtp12PlusOduTcm6IncomingAlignmentErrorAlarm			DisplayString, 
				omtp12PlusOduTraceIdentifierMismatchAlarm			DisplayString, 
				omtp12PlusOduLockedDefectAlarm					DisplayString, 
				omtp12PlusOduOpenConnectionIndicationAlarm			DisplayString, 
				omtp12PlusOduBackwardDefectIndicationAlarm			DisplayString, 
				omtp12PlusOduTcm1BackwardIncomingAlignmentErrorAlarm		DisplayString, 
				omtp12PlusOduTcm2BackwardIncomingAlignmentErrorAlarm		DisplayString, 
				omtp12PlusOduTcm3BackwardIncomingAlignmentErrorAlarm		DisplayString, 
				omtp12PlusOduTcm4BackwardIncomingAlignmentErrorAlarm		DisplayString,
				omtp12PlusOduTcm5BackwardIncomingAlignmentErrorAlarm		DisplayString, 
				omtp12PlusOduTcm6BackwardIncomingAlignmentErrorAlarm		DisplayString, 
				omtp12PlusOpuPayloadMismatchAlarm				DisplayString, 
				omtp12PlusOchLossOfPayloadAlarm					DisplayString, 
				omtp12PlusSdhLossOfSignalAlarm					DisplayString, 
				omtp12PlusSdhOutOfFrameAlarm					DisplayString, 
				omtp12PlusSdhLossOfFrameAlarm					DisplayString, 
				omtp12PlusSdhRsAlarmIndicationSignalAlarm			DisplayString, 
				omtp12PlusSdhRsTraceIdentifierMismatchAlarm			DisplayString, 
				omtp12PlusSdhAuAlarmIndicationSignalAlarm			DisplayString, 
				omtp12PlusSdhAuLossOfPointerAlarm				DisplayString, 
				omtp12PlusSdhMsAlarmIndicationSignalAlarm			DisplayString, 
				omtp12PlusSdhMsRemoteErrorIndicationAlarm			DisplayString, 
				omtp12PlusSdhMsRemoteDefectIndicationAlarm			DisplayString, 
				omtp12PlusSdhMsRemoteFailureIndicationAlarm			DisplayString, 
				omtp12PlusSdhMsB2ExcessiveErrorAlarm				DisplayString, 
				omtp12PlusSdhMsB2SignalDegradeAlarm				DisplayString, 
				omtp12PlusSdhLossOfSequenceSynchronisationAlarm			DisplayString,
				omtp12PlusSdhHigherOrderPathPayloadLabelMismatchAlarm		DisplayString,
				omtp12PlusSdhHigherOrderPathUnequippedAlarm			DisplayString,
				omtp12PlusWan10gLossOfSignalAlarm				DisplayString,
				omtp12PlusWan10gOutOfFrameAlarm					DisplayString,
				omtp12PlusWan10gLossOfFrameAlarm				DisplayString,
				omtp12PlusWan10gRsAlarmIndicationSignalAlarm			DisplayString,
				omtp12PlusWan10gRsTraceIdentifierMismatchAlarm			DisplayString,
				omtp12PlusWan10gAuAlarmIndicationSignalAlarm			DisplayString,
				omtp12PlusWan10gAuLossOfPointerAlarm				DisplayString,
				omtp12PlusWan10gMsAlarmIndicationSignalAlarm			DisplayString,
				omtp12PlusWan10gMsRemoteErrorIndicationAlarm			DisplayString,
				omtp12PlusWan10gMsRemoteDefectIndicationAlarm			DisplayString,
				omtp12PlusWan10gMsRemoteFailureIndicationAlarm			DisplayString,
				omtp12PlusWan10gMsB2ExcessiveErrorAlarm				DisplayString,
				omtp12PlusWan10gMsB2SignalDegradeAlarm				DisplayString,
				omtp12PlusWan10gLossOfSequenceSynchronisationAlarm		DisplayString,
				omtp12PlusWan10gHigherOrderPathPayloadLabelMismatchAlarm	DisplayString,
				omtp12PlusWan10gHigherOrderPathUnequippedAlarm			DisplayString,
				omtp12PlusLan10gLossOfSignalAlarm				DisplayString,
				omtp12PlusLan10gLossOfSignalSyncAlarm				DisplayString,
				omtp12PlusLan10gLinkFailureAlarm				DisplayString,
				omtp12PlusLan10gFrameCheckSequenceAlarm				DisplayString,
				omtp12PlusLan10gCarrierStatusAlarm				DisplayString,
				omtp12PlusLan10gHighBerAlarm					DisplayString,
				omtp12PlusLan10gLocalFaultAlarm					DisplayString,
				omtp12PlusLan10gRemoteFaultAlarm				DisplayString,
				omtp12PlusFcTransmitDisparityInversionDefectAlarm		DisplayString,
				omtp12PlusFcTransmitDigitalLossOfLinkDefectAlarm		DisplayString,
				omtp12PlusFcTrasnmitLossofSynchronizationDefectAlarm		DisplayString,
				omtp12PlusFcReceiveDigitalLossofLinkDefectAlarm			DisplayString,
				omtp12PlusFcReceiveLossofSynchronizationDefectAlarm		DisplayString,
				omtp12PlusFcReceiveTransitionDetectDefectAlarm			DisplayString,
				omtp12PlusFcReceiveAnalogLossofSignalDefectAlarm		DisplayString,
				omtp12PlusFcReceiveLineCodeViolationDefectAlarm			DisplayString,
				omtp12PlusGfpCsfSignalFailAlarm					DisplayString,
				omtp12PlusGfpCsfLinkFailAlarm					DisplayString,
				omtp12PlusGfpCoreHeaderErrorAlarm				DisplayString,
				omtp12PlusGfpExtentionHeaderErrorAlarm				DisplayString,
				omtp12PlusAlarmQueryTableRowStatus				RowStatus
		}


	omtp12PlusXfpInputPowerFailureAlarm OBJECT-TYPE
		SYNTAX  DisplayString
		MAX-ACCESS  read-only
		STATUS  current
		DESCRIPTION
			"If optical input power at requested interface is less than
			-20dbm, this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 1 }

        omtp12PlusXfpOutputPowerFailureAlarm OBJECT-TYPE
		SYNTAX  DisplayString
		MAX-ACCESS  read-only
		STATUS  current
		DESCRIPTION
			"If optical output power at requested interface is less than
			-10dbm, this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 2 }

        omtp12PlusXfpHighTemperatureAlarm OBJECT-TYPE
		SYNTAX  DisplayString
		MAX-ACCESS  read-only
		STATUS  current
		DESCRIPTION
			"If optical temperature at requested interface is greater 
			than the High Temperature Alarm Threshold, alarm will 
			be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 3 }

        omtp12PlusXfpLowTemperatureAlarm OBJECT-TYPE
		SYNTAX  DisplayString
		MAX-ACCESS  read-only
		STATUS  current
		DESCRIPTION
			"If optical temperature at requested interface is lower 
			than the Low Temperature Alarm Threshold, alarm will be 
			generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 4 }

        omtp12PlusXfpHighTemperatureWarning OBJECT-TYPE
		SYNTAX  DisplayString
		MAX-ACCESS  read-only
		STATUS  current
		DESCRIPTION
       			"If optical temperature at requested interface is greater
			than the High Temperature Warning Threshold, this alarm 
			will be generated.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 5 }

        omtp12PlusXfpLowTemperatureWarning OBJECT-TYPE
		SYNTAX  DisplayString
		MAX-ACCESS  read-only
		STATUS  current
		DESCRIPTION
       			"If optical temperature at requested interface is lesser
			than the Low Temperature Warning Threshold, this alarm 
			will be generated.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 6 }

        omtp12PlusXfpHighBiasCurrentAlarm OBJECT-TYPE
		SYNTAX  DisplayString
		MAX-ACCESS  read-only
		STATUS  current
		DESCRIPTION
       			"If optical transmit bias current at requested interface
			is greater than the High Bias Current Alarm Threshold, 
			this this alarm will be generated.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 7 }

        omtp12PlusXfpLowBiasCurrentAlarm OBJECT-TYPE
		SYNTAX  DisplayString
		MAX-ACCESS  read-only
		STATUS  current
		DESCRIPTION
			"If optical transmit bias current at requested interface
			is lesser than the Low Bias Current Alarm Threshold, 
			this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 8 }

        omtp12PlusXfpHighBiasCurrentWarning OBJECT-TYPE
		SYNTAX  DisplayString
		MAX-ACCESS  read-only
		STATUS  current
		DESCRIPTION
       			"If optical transmit bias current at requested interface
			is greater than the High Bias Current Warning Threshold,
			this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 9 }

        omtp12PlusXfpLowBiasCurrentWarning OBJECT-TYPE
		SYNTAX  DisplayString
		MAX-ACCESS  read-only
		STATUS  current
		DESCRIPTION
       			"If optical transmit bias current at requested interface
			is lesser than the Low Bias Current Warning Threshold, 
			this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 10 }

        omtp12PlusXfpInputHighPowerAlarm OBJECT-TYPE
		SYNTAX  DisplayString
		MAX-ACCESS  read-only
		STATUS  current
		DESCRIPTION
       			"If optical Input power at requested interface is 
			greater than the High Input Power Alarm Threshold, this 
			alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 11 }

        omtp12PlusXfpInputLowPowerAlarm OBJECT-TYPE
		SYNTAX  DisplayString
		MAX-ACCESS  read-only
		STATUS  current
		DESCRIPTION
       			"If optical Input power at requested interface is lesser
			than the Low Input Power Alarm Threshold, this alarm 
			will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 12 }

        omtp12PlusXfpInputHighPowerWarning OBJECT-TYPE
		SYNTAX  DisplayString
		MAX-ACCESS  read-only
		STATUS  current
		DESCRIPTION
       			"If optical Input power at requested interface is 
			greater than the High Input Power Warning Threshold, 
			this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 13 }

        omtp12PlusXfpInputLowPowerWarning OBJECT-TYPE
		SYNTAX  DisplayString
		MAX-ACCESS  read-only
		STATUS  current
		DESCRIPTION
       			"If optical Input power at requested interface is lesser
			than the Low Input Power Warning Threshold, this alarm 
			will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 14 }

        omtp12PlusXfpOutputHighPowerAlarm OBJECT-TYPE
		SYNTAX  DisplayString
		MAX-ACCESS  read-only
		STATUS  current
		DESCRIPTION
       			"If optical Output power at requested interface is 
			greater than the High Output Power Alarm Threshold, this
			alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 15 }

        omtp12PlusXfpOutputLowPowerAlarm OBJECT-TYPE
		SYNTAX  DisplayString
		MAX-ACCESS  read-only
		STATUS  current
		DESCRIPTION
       			"If optical Output power at requested interface is 
			lesser than the Low Output Power Alarm Threshold, this 
			alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 16 }

        omtp12PlusXfpOutputHighPowerWarning OBJECT-TYPE
		SYNTAX  DisplayString
		MAX-ACCESS  read-only
		STATUS  current
		DESCRIPTION
       			"If optical Output power at requested interface is 
			greater than the High Output Power Warning Threshold, 
			this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 17 }

        omtp12PlusXfpOutputLowPowerWarning OBJECT-TYPE
		SYNTAX  DisplayString
		MAX-ACCESS  read-only
		STATUS  current
		DESCRIPTION
       			"If optical Output power at requested interface is 
			lesser than the Low Output Power Warning Threshold, this
			alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 18 }

        omtp12PlusXfpHighSupplyVoltageAlarm OBJECT-TYPE
		SYNTAX  DisplayString
		MAX-ACCESS  read-only
		STATUS  current
		DESCRIPTION
       			"If optical Supply Voltage at requested interface is 
			greater than the High Supply Voltage Alarm Threshold, 
			this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 19 }

        omtp12PlusXfpLowSupplyVoltageAlarm OBJECT-TYPE
		SYNTAX  DisplayString
		MAX-ACCESS  read-only
		STATUS  current
		DESCRIPTION
       			"If optical Supply Voltage at requested interface is 
			lesser than the Low Supply Voltage Alarm Threshold, this
			alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 20 }

        omtp12PlusXfpHighSupplyVoltageWarning OBJECT-TYPE
		SYNTAX  DisplayString
		MAX-ACCESS  read-only
		STATUS  current
		DESCRIPTION
       			"If optical Supply Voltage at requested interface is 
			greater than the High Supply Voltage Warning Threshold, 
			this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 21 }

        omtp12PlusXfpLowSupplyVoltageWarning OBJECT-TYPE
		SYNTAX  DisplayString
		MAX-ACCESS  read-only
		STATUS  current
		DESCRIPTION
       			"If optical Supply Voltage at requested interface is 
			lesser than the Low Supply Voltage Warning Threshold, 
			this alarm will be generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 22 }

        omtp12PlusXfpPresenceAbsenceNotification OBJECT-TYPE
		SYNTAX  DisplayString
		MAX-ACCESS  read-only
		STATUS  current
		DESCRIPTION
			"Whenever the XFP is jacked in or jacked out, this 
			notification is generated.
			-----------------------------
			omtp12PlusInterfaceNumber:
			1 - CLIENT-1
			2 - LINE-1
			3 - LINE-2
			-----------------------------
			Values :
			If Alarm is Present(module absent) - Date and Time Stamp
				    eg:2017-5-18,9:47:20.0,+5:30
			If Alarm is Absent(module present) - 0
			-----------------------------"
               ::= { omtp12PlusAlarmQueryEntry 23 }

        omtp12PlusOtuLossOfSignalAlarm OBJECT-TYPE
		SYNTAX  DisplayString
		MAX-ACCESS  read-only
		STATUS  current
		DESCRIPTION
			"For port configured with OTU2 traffic,
			if there is no signal received then OTU-LOS Alarm
			is generated.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 31 }

        omtp12PlusOtuLossOfFrameAlarm OBJECT-TYPE
		SYNTAX  DisplayString
		MAX-ACCESS  read-only
		STATUS  current
		DESCRIPTION
			"For port configured with OTU2 traffic, if
			OTU2 frame received are in out-of-frame (OOF)
			state for 3 ms, then OTU-LOF Alarm is generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 32 }

        omtp12PlusOtuOutOfFrameAlarm OBJECT-TYPE
		SYNTAX  DisplayString
		MAX-ACCESS  read-only
		STATUS  current
		DESCRIPTION
			"For port configured with OTU2 traffic, if 5
			consecutive OTU2 frames are received with
			invalid framing patterns then OTU OOF Alarm is
			generated
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 33 }

        omtp12PlusOtuLossOfMultiFrameAlarm OBJECT-TYPE
		SYNTAX  DisplayString
		MAX-ACCESS  read-only
		STATUS  current
		DESCRIPTION
		        "For port configured with OTU2 traffic, if 
			OTU2 frame received are in Out-of-multiframe
			(OOM) state for 3 ms then LOM Alarm is generated.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 34 }

        omtp12PlusOtuOutOfMultiFrameAlarm OBJECT-TYPE
		SYNTAX  DisplayString
		MAX-ACCESS  read-only
		STATUS  current
		DESCRIPTION
		        "For port configured with OTU2 traffic, if the
			received MFAS does not match with the expected multi
			frame number for five consecutive frames then
			OTU OOM Alarm is generated.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 35 }

        omtp12PlusOtuSignalFailAlarm OBJECT-TYPE
		SYNTAX  DisplayString
		MAX-ACCESS  read-only
		STATUS  current
		DESCRIPTION
		       "For port configured with OTU2 traffic, 
			OTU SF alarm is generated when BIP errors evaluated by 
			SM field of OTU2 frame exceeds the 
			'omtp12PlusOtuSignalFailThreshold' threshold
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 36 }

        omtp12PlusOtuSignalDegradeAlarm OBJECT-TYPE
		SYNTAX  DisplayString
		MAX-ACCESS  read-only
		STATUS  current
		DESCRIPTION
		        "For port configured with OTU2 traffic, 
		        OTU SD alarm is generated when BIP errors evaluated by 
			SM field of OTU2 frame exceeds the 
			'omtp12PlusOtuSignalDegradeThreshold' threshold.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 37 }

        omtp12PlusOtuAlarmIndicationSignalAlarm OBJECT-TYPE
		SYNTAX  DisplayString
		MAX-ACCESS  read-only
		STATUS  current
		DESCRIPTION
		         "For port configured with OTU2 traffic, 
			OTU-AIS is generated and transmitted in forward 
			direction, when LOS has been detected at far-end port.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 38 }

        omtp12PlusOtuIncomingAlignmentErrorAlarm OBJECT-TYPE
		SYNTAX  DisplayString
		MAX-ACCESS  read-only
		STATUS  current
		DESCRIPTION
		        "For port configured with OTU2 traffic, 
			OTU-IAE alarm is generated to indicate a 
			frame alignment error 
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 39 }

        omtp12PlusOtuTraceIdentifierMismatchAlarm OBJECT-TYPE
		SYNTAX  DisplayString
		MAX-ACCESS  read-only
		STATUS  current
		DESCRIPTION
		        "For port configured with OTU2 traffic, 
			when there is a trace identifier mismatch in the data 
			stream at SM section, OTU-TIM alarm is generated 
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 40 }

        omtp12PlusOtuBackwardIncomingAlignmentErrorAlarm OBJECT-TYPE
		SYNTAX  DisplayString
		MAX-ACCESS  read-only
		STATUS  current
		DESCRIPTION
		        "For port configured with OTU2 traffic, 
			This alarm conveys that 
			incoming alignment error (IAE) condition that is 
			detected in the far end card
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 41 }

        omtp12PlusOtuBackwardDefectIndicationAlarm OBJECT-TYPE
		SYNTAX  DisplayString
		MAX-ACCESS  read-only
		STATUS  current
		DESCRIPTION
		        "For port configured with OTU2 traffic, 
			OTU-BDI is sent in backward direction, to indicate that
			a defect like LOS, LOF, OTU-TIM has been detected in the
			receive direction.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 42 }

        omtp12PlusOduSignalFailAlarm OBJECT-TYPE
		SYNTAX  DisplayString
		MAX-ACCESS  read-only
		STATUS  current
		DESCRIPTION
		        "For port configured with OTU2 traffic, 
			ODU SF alarm is generated when BIP errors evaluated by 
			PM field of OTU2 frame exceeds the 
			'omtp12PlusOduSignalFailThreshold' threshold.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 51 }

        omtp12PlusOduSignalDegradeAlarm OBJECT-TYPE
		SYNTAX  DisplayString
		MAX-ACCESS  read-only
		STATUS  current
		DESCRIPTION
			"For port configured with OTU2 traffic, 
			ODU SD alarm is generated when BIP errors evaluated by 
			PM field of OTU2 frame exceeds the 	
			'omtp12PlusOduSignalDegradeThreshold' threshold.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 52 }

        omtp12PlusOduAlarmIndicationSignalAlarm OBJECT-TYPE
		SYNTAX  DisplayString
		MAX-ACCESS  read-only
		STATUS  current
		DESCRIPTION
		        "For port configured with OTU2 traffic, 
			ODU-AIS is generated when LOS/TIM/PT mismatch has been 
			detected at far-end port.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 53 }

        omtp12PlusOduTcm1IncomingAlignmentErrorAlarm OBJECT-TYPE
		SYNTAX  DisplayString
		MAX-ACCESS  read-only
		STATUS  current
		DESCRIPTION
			"For port configured with OTU2 traffic, TCM1 IAE
			shall be declared if the accepted STAT information is
			0b010
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 54 }

        omtp12PlusOduTcm2IncomingAlignmentErrorAlarm OBJECT-TYPE
		SYNTAX  DisplayString
		MAX-ACCESS  read-only
		STATUS  current
		DESCRIPTION
			"For port configured with OTU2 traffic, TCM2 IAE
			shall be declared if the accepted STAT information is
			0b010
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 55 }

        omtp12PlusOduTcm3IncomingAlignmentErrorAlarm OBJECT-TYPE
		SYNTAX  DisplayString
		MAX-ACCESS  read-only
		STATUS  current
		DESCRIPTION
			"For port configured with OTU2 traffic, TCM3 IAE
			shall be declared if the accepted STAT information is
			0b010
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 56 }

        omtp12PlusOduTcm4IncomingAlignmentErrorAlarm OBJECT-TYPE
		SYNTAX  DisplayString
		MAX-ACCESS  read-only
		STATUS  current
		DESCRIPTION
			"For port configured with OTU2 traffic, TCM4 IAE
			shall be declared if the accepted STAT information is
			0b010
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 57 }

        omtp12PlusOduTcm5IncomingAlignmentErrorAlarm OBJECT-TYPE
		SYNTAX  DisplayString
		MAX-ACCESS  read-only
		STATUS  current
		DESCRIPTION
			"For port configured with OTU2 traffic, TCM5 IAE
			shall be declared if the accepted STAT information is
			0b010
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 58 }

        omtp12PlusOduTcm6IncomingAlignmentErrorAlarm OBJECT-TYPE
		SYNTAX  DisplayString
		MAX-ACCESS  read-only
		STATUS  current
		DESCRIPTION
			"For port configured with OTU2 traffic, TCM6 IAE
			shall be declared if the accepted STAT information is
			0b010
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 59 }

        omtp12PlusOduTraceIdentifierMismatchAlarm OBJECT-TYPE
		SYNTAX  DisplayString
		MAX-ACCESS  read-only
		STATUS  current
		DESCRIPTION
			"For port configured with OTU2 traffic, 
			when there is a trace identifier mismatch in the data 
			stream at PM section ODU-TIM alarm is generated.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 60 }

        omtp12PlusOduLockedDefectAlarm OBJECT-TYPE
		SYNTAX  DisplayString
		MAX-ACCESS  read-only
		STATUS  current
		DESCRIPTION
			"For port configured with OTU2 traffic, 
			The locked maintenance signal is generated on operator
			request in order to lock the signal from user access. It
			consists of a repeating 0b01010101 pattern in the entire
			ODUk signal, which excludes the Frame Alignment
			overhead and the OTUk overhead.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 61 }

        omtp12PlusOduOpenConnectionIndicationAlarm OBJECT-TYPE
		SYNTAX  DisplayString
		MAX-ACCESS  read-only
		STATUS  current
		DESCRIPTION
			"For port configured with OTU2 traffic, 
			An open connection indication is sent downstream when
			no signal is detected from upstream. It consists of a
			repeating 0b01100110 pattern in the entire ODUk signal,
			which excludes the Frame Alignment overhead and the
			OTUk overhead.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 62 }

        omtp12PlusOduBackwardDefectIndicationAlarm OBJECT-TYPE
		SYNTAX  DisplayString
		MAX-ACCESS  read-only
		STATUS  current
		DESCRIPTION
		        "For port configured with OTU2 traffic, 
			ODU-BDI is sent in backward direction, to indicate that
			a defect like LOS, LOF, ODU-TIM has been detected in the
			receive direction.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 63 }

        omtp12PlusOduTcm1BackwardIncomingAlignmentErrorAlarm OBJECT-TYPE
		SYNTAX  DisplayString
		MAX-ACCESS  read-only
		STATUS  current
		DESCRIPTION
			"For port configured with OTU2 traffic, 
			the presence of this alarm conveys that
			TCM1 incoming alignment error (IAE) condition is 
			detected in the far-end card.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 64 }

        omtp12PlusOduTcm2BackwardIncomingAlignmentErrorAlarm OBJECT-TYPE
		SYNTAX  DisplayString
		MAX-ACCESS  read-only
		STATUS  current
		DESCRIPTION
			"For port configured with OTU2 traffic, 
			the presence of this alarm conveys that
			TCM2 incoming alignment error (IAE) condition is 
			detected in the far-end card.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 65 }

        omtp12PlusOduTcm3BackwardIncomingAlignmentErrorAlarm OBJECT-TYPE
		SYNTAX  DisplayString
		MAX-ACCESS  read-only
		STATUS  current
		DESCRIPTION
			"For port configured with OTU2 traffic, 
			the presence of this alarm conveys that
			TCM3 incoming alignment error (IAE) condition is 
			detected in the far-end card.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 66 }

        omtp12PlusOduTcm4BackwardIncomingAlignmentErrorAlarm OBJECT-TYPE
		SYNTAX  DisplayString
		MAX-ACCESS  read-only
		STATUS  current
		DESCRIPTION
			"For port configured with OTU2 traffic, 
			the presence of this alarm conveys that
			TCM4 incoming alignment error (IAE) condition is 
			detected in the far-end card.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 67 }

        omtp12PlusOduTcm5BackwardIncomingAlignmentErrorAlarm OBJECT-TYPE
		SYNTAX  DisplayString
		MAX-ACCESS  read-only
		STATUS  current
		DESCRIPTION
			"For port configured with OTU2 traffic, 
			the presence of this alarm conveys that
			TCM5 incoming alignment error (IAE) condition is 
			detected in the far-end card.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 68 }

        omtp12PlusOduTcm6BackwardIncomingAlignmentErrorAlarm OBJECT-TYPE
		SYNTAX  DisplayString
		MAX-ACCESS  read-only
		STATUS  current
		DESCRIPTION
			"For port configured with OTU2 traffic, 
			the presence of this alarm conveys that
			TCM6 incoming alignment error (IAE) condition is 
			detected in the far-end card.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 69 }

        omtp12PlusOpuPayloadMismatchAlarm OBJECT-TYPE
		SYNTAX  DisplayString
		MAX-ACCESS  read-only
		STATUS  current
		DESCRIPTION
		        "For port configured with OTU2 traffic, 
			OPU-PLM Alarm is declared if the accepted payload type
			is not equal to the expected payload type.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 70 }

        omtp12PlusOchLossOfPayloadAlarm OBJECT-TYPE
		SYNTAX  DisplayString
		MAX-ACCESS  read-only
		STATUS  current
		DESCRIPTION
		        "If input power level at the XFP is less than 
			-21dbm this this alarm will be generated.
			-----------------------------
			omtp12PlusInterfaceNumber:
			1 - CLIENT-1
			2 - LINE-1
			3 - LINE-2
			-----------------------------
			Values :
			If Alarm is Present - Date and Time Stamp
				    eg:2017-5-18,9:47:20.0,+5:30
			If Alarm is Absent  - 0
			-----------------------------"
               ::= { omtp12PlusAlarmQueryEntry 71 }

        omtp12PlusSdhLossOfSignalAlarm OBJECT-TYPE
		SYNTAX  DisplayString
		MAX-ACCESS  read-only
		STATUS  current
		DESCRIPTION
			"For port configured with SDH traffic, 
			If there is No signal received at the requested Port 
			configured with STM64 traffic, then LOS Alarm is 
			generated.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 81 }

        omtp12PlusSdhOutOfFrameAlarm OBJECT-TYPE
		SYNTAX  DisplayString
		MAX-ACCESS  read-only
		STATUS  current
		DESCRIPTION
			"For port configured with SDH traffic, 
			If SDH frame received are out-of-frame (OOF) state for 
			3 ms at the Port configured with STM64 traffic, LOF 
			Alarm is generated.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 82 }

        omtp12PlusSdhLossOfFrameAlarm OBJECT-TYPE
		SYNTAX  DisplayString
		MAX-ACCESS  read-only
		STATUS  current
		DESCRIPTION
		        "For port configured with SDH traffic, 
			If SDH frame received are out-of-frame (OOF) state for 
			3 ms at the Port configured with STM64 traffic, LOF 
			Alarm is generated.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 83 }

        omtp12PlusSdhRsAlarmIndicationSignalAlarm OBJECT-TYPE
		SYNTAX  DisplayString
		MAX-ACCESS  read-only
		STATUS  current
		DESCRIPTION
		        "For port configured with SDH traffic, 
			RS-AIS alarm is indicated when there is no signal 
			received in far end port.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 84 }

        omtp12PlusSdhRsTraceIdentifierMismatchAlarm OBJECT-TYPE
		SYNTAX  DisplayString
		MAX-ACCESS  read-only
		STATUS  current
		DESCRIPTION
		        "For port configured with SDH traffic, 
			RS-TIM alarm is indicated when there is mimatch in the 
			expected traces at the requested port configured with 
			STM64 traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 85 }

        omtp12PlusSdhAuAlarmIndicationSignalAlarm OBJECT-TYPE
		SYNTAX  DisplayString
		MAX-ACCESS  read-only
		STATUS  current
		DESCRIPTION
		        "For port configured with SDH traffic, 
			AU-AIS is an alarm indication signal (AIS) is a signal 
			sent downstream as an indication that an upstream
			defect has been detected.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 86 }

        omtp12PlusSdhAuLossOfPointerAlarm OBJECT-TYPE
		SYNTAX  DisplayString
		MAX-ACCESS  read-only
		STATUS  current
		DESCRIPTION
		        "For port configured with SDH traffic, 
			LOP state occurs when N consecutive invalid pointers
			are received or N consecutive New Data Flags (NDF)
			are received where N = 8, 9, or 10. LOP state is 
			cleared when three equal valid pointers or three
			consecutive AIS indications are received.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 87 }

        omtp12PlusSdhMsAlarmIndicationSignalAlarm OBJECT-TYPE
		SYNTAX  DisplayString
		MAX-ACCESS  read-only
		STATUS  current
		DESCRIPTION
		        "For port configured with SDH traffic, 
			MS-AIS is an alarm indication signal (AIS) is a signal 
			sent downstream as an indication that an upstream
			defect has been detected.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 88 }

        omtp12PlusSdhMsRemoteErrorIndicationAlarm OBJECT-TYPE
		SYNTAX  DisplayString
		MAX-ACCESS  read-only
		STATUS  current
		DESCRIPTION
		        "For port configured with SDH traffic, 
			This alarm is an indication returned to a transmitting
			node (source) that an errored block has been detected at
			the receiving node (sink).
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 89 }

        omtp12PlusSdhMsRemoteDefectIndicationAlarm OBJECT-TYPE
		SYNTAX  DisplayString
		MAX-ACCESS  read-only
		STATUS  current
		DESCRIPTION
		        "For port configured with SDH traffic, 
			MS-RDI is a signal returned to the transmitting equipment 
			upon detecting a LOS, LOF, or MS-AIS defect
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 90 }

        omtp12PlusSdhMsRemoteFailureIndicationAlarm OBJECT-TYPE
		SYNTAX  DisplayString
		MAX-ACCESS  read-only
		STATUS  current
		DESCRIPTION
		        "For port configured with SDH traffic, 
			A failure is a defect that persists beyond the maximum
			time allocated to the transmission system protection
			mechanisms. When this situation occurs, an RFI is sent
			to the far end and will initiate a path protection
			switch if this function has been provisioned.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 91 }

        omtp12PlusSdhMsB2ExcessiveErrorAlarm OBJECT-TYPE
		SYNTAX  DisplayString
		MAX-ACCESS  read-only
		STATUS  current
		DESCRIPTION
		        "For port configured with SDH traffic, 
			B2 SF alarm is generated when Parity errors evaluated 
			by byte B2 of SDH frame exceeds the 
			'omtp12PlusSdhMsB2ExcessiveErrorThreshold' threshold.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 92 }

        omtp12PlusSdhMsB2SignalDegradeAlarm OBJECT-TYPE
		SYNTAX  DisplayString
		MAX-ACCESS  read-only
		STATUS  current
		DESCRIPTION
		        "For port configured with SDH traffic, 
			B2 SD alarm is generated when Parity errors evaluated 
			by byte B2 of SDH frame exceeds the 
			'omtp12PlusSdhMsB2SignalDegradeThreshold' threshold.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 93 }

        omtp12PlusSdhLossOfSequenceSynchronisationAlarm OBJECT-TYPE
		SYNTAX  DisplayString
		MAX-ACCESS  read-only
		STATUS  current
		DESCRIPTION
		        "For port configured with SDH traffic, 
			Sequence synchronisation shall be considered to be lost
			and re-synchronisation shall be started if:
			The bit error ratio is ≥ 0.20 during an integration
			interval of 1 second; or
			It can be unambiguously identified that the test
			sequence and the reference sequence are out of phase.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 94 }
               
        omtp12PlusSdhHigherOrderPathPayloadLabelMismatchAlarm OBJECT-TYPE
		SYNTAX  DisplayString
		MAX-ACCESS  read-only
		STATUS  current
		DESCRIPTION
		        "Reserved for future study
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 95 }
               
        omtp12PlusSdhHigherOrderPathUnequippedAlarm OBJECT-TYPE
		SYNTAX  DisplayString
		MAX-ACCESS  read-only
		STATUS  current
		DESCRIPTION
		        "For port configured with SDH traffic, 
			These signals indicate to downstream transport
			processing functions (refer to ITU-T Rec. G.803) that
			the virtual container is unoccupied,
			not connected to a path termination source function.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 96 }

        omtp12PlusWan10gLossOfSignalAlarm OBJECT-TYPE
		SYNTAX  DisplayString
		MAX-ACCESS  read-only
		STATUS  current
		DESCRIPTION
		        "For port configured with 10G WAN traffic, 
			If there is No signal received at the requested port 
			configured with WAN10G traffic then LOS Alarm is 
			generated.			
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 101 }

        omtp12PlusWan10gOutOfFrameAlarm OBJECT-TYPE
		SYNTAX  DisplayString
		MAX-ACCESS  read-only
		STATUS  current
		DESCRIPTION
		        "For port configured with 10G WAN traffic, 
			If WAN frame received are out-of-frame (OOF) state for 
			3 ms at the requested port configured with WAN10G 
			traffic, LOF Alarm is generated.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 102 }

        omtp12PlusWan10gLossOfFrameAlarm OBJECT-TYPE
                      SYNTAX  DisplayString
		MAX-ACCESS  read-only
		STATUS  current
                       DESCRIPTION
		        "For port configured with 10G WAN traffic, 
			If WAN10G frame received are out-of-frame (OOF) state 
			for 3 ms at the requested port configured with WAN10G 
			traffic, LOF Alarm is generated.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 103 }

        omtp12PlusWan10gRsAlarmIndicationSignalAlarm OBJECT-TYPE
		SYNTAX  DisplayString
		MAX-ACCESS  read-only
		STATUS  current
		DESCRIPTION
		        "For port configured with 10G WAN traffic, 
			RS-AIS alarm is indicated when there is no signal 
			received in far end port.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 104 }

        omtp12PlusWan10gRsTraceIdentifierMismatchAlarm OBJECT-TYPE
		SYNTAX  DisplayString
		MAX-ACCESS  read-only
		STATUS  current
		DESCRIPTION
		        "For port configured with 10G WAN traffic, 
			RS-TIM alarm is indicated when there is mimatch in the 
			expected traces.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 105 }

        omtp12PlusWan10gAuAlarmIndicationSignalAlarm OBJECT-TYPE
		SYNTAX  DisplayString
		MAX-ACCESS  read-only
		STATUS  current
		DESCRIPTION
		        "For port configured with 10G WAN traffic, 
			AU-AIS is an alarm indication signal (AIS) is a signal 
			sent downstream as an indication that an upstream
			defect has been detected.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 106 }

        omtp12PlusWan10gAuLossOfPointerAlarm OBJECT-TYPE
		SYNTAX  DisplayString
		MAX-ACCESS  read-only
		STATUS  current
		DESCRIPTION
		        "For port configured with 10G WAN traffic, 
			LOP state occurs when N consecutive invalid pointers
			are received or N consecutive New Data Flags (NDF)
			are received where N = 8, 9, or 10. LOP state is 
			cleared when three equal valid pointers or three
			consecutive AIS indications are received.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 107 }

        omtp12PlusWan10gMsAlarmIndicationSignalAlarm OBJECT-TYPE
		SYNTAX  DisplayString
		MAX-ACCESS  read-only
		STATUS  current
		DESCRIPTION
		        "For port configured with 10G WAN traffic, 
			MS-AIS is an alarm indication signal (AIS) is a signal 
			sent downstream as an indication that an upstream
			defect has been detected.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 108 }

        omtp12PlusWan10gMsRemoteErrorIndicationAlarm OBJECT-TYPE
		SYNTAX  DisplayString
		MAX-ACCESS  read-only
		STATUS  current
		DESCRIPTION
		        "For port configured with 10G WAN traffic, 
			This alarm is an indication returned to a transmitting
			node (source) that an errored block has been detected at
			the receiving node (sink).
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 109 }

        omtp12PlusWan10gMsRemoteDefectIndicationAlarm OBJECT-TYPE
		SYNTAX  DisplayString
		MAX-ACCESS  read-only
		STATUS  current
		DESCRIPTION
		        "For port configured with 10G WAN traffic, 
			MS-RDI is a signal returned to the transmitting 
			equipment upon detecting a LOS, LOF, or MS-AIS defect.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 110 }

        omtp12PlusWan10gMsRemoteFailureIndicationAlarm OBJECT-TYPE
		SYNTAX  DisplayString
		MAX-ACCESS  read-only
		STATUS  current
		DESCRIPTION
		        "For port configured with 10G WAN traffic, 
			A failure is a defect that persists beyond the maximum
			time allocated to the transmission system protection
			mechanisms. When this situation occurs, an RFI is sent
			to the far end and will initiate a path protection
			switch if this function has been provisioned.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 111 }

        omtp12PlusWan10gMsB2ExcessiveErrorAlarm OBJECT-TYPE
		SYNTAX  DisplayString
		MAX-ACCESS  read-only
		STATUS  current
		DESCRIPTION
		        "For port configured with 10G WAN traffic, 
			B2 SF alarm is generated when Parity errors evaluated 
			by byte B2 of Wan10g frame exceeds the 
			'omtp12PlusWan10gMsB2ExcessiveErrorThreshold' threshold
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 112 }

        omtp12PlusWan10gMsB2SignalDegradeAlarm OBJECT-TYPE
		SYNTAX  DisplayString
		MAX-ACCESS  read-only
		STATUS  current
		DESCRIPTION
		        "For port configured with 10G WAN traffic, 
			B2 SD alarm is generated when Parity errors evaluated
			by byte B2 of Wan10g frame exceeds the
			'omtp12PlusWan10gMsB2SignalDegradeThreshold' threshold
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 113 }

        omtp12PlusWan10gLossOfSequenceSynchronisationAlarm OBJECT-TYPE
		SYNTAX  DisplayString
		MAX-ACCESS  read-only
		STATUS  current
		DESCRIPTION
		        "For port configured with 10G WAN traffic, 
			Sequence synchronisation shall be considered to be lost
			and re-synchronisation shall be started if:
			The bit error ratio is ≥ 0.20 during an integration
			interval of 1 second; or
			It can be unambiguously identified that the test
			sequence and the reference sequence are out of phase.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 114 }
               
        omtp12PlusWan10gHigherOrderPathPayloadLabelMismatchAlarm OBJECT-TYPE
		SYNTAX  DisplayString
		MAX-ACCESS  read-only
		STATUS  current
		DESCRIPTION
		        "Reserved for future study
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 115 }               
               
        omtp12PlusWan10gHigherOrderPathUnequippedAlarm OBJECT-TYPE
		SYNTAX  DisplayString
		MAX-ACCESS  read-only
		STATUS  current
		DESCRIPTION
		        "For port configured with 10G WAN traffic, 
			These signals indicate to downstream transport
			processing functions (refer to ITU-T Rec. G.803) that
			the virtual container is unoccupied, not connected to a 
			path termination source function.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 116 }
               
	omtp12PlusLan10gLossOfSignalAlarm OBJECT-TYPE
		SYNTAX  DisplayString
		MAX-ACCESS  read-only
		STATUS  current
		DESCRIPTION
		        "For port configured with 10G LAN traffic, 
			If there is No signal received at the Port configured 
			with LAN10G traffic, it leads to LOS Alarm.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 121 }

        omtp12PlusLan10gLossOfSignalSyncAlarm OBJECT-TYPE
		SYNTAX  DisplayString
		MAX-ACCESS  read-only
		STATUS  current
		DESCRIPTION
		        "For port configured with 10G LAN traffic, 
			When the receive interface does not achieve PCS
		         sync it is called Loss of Sync.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 122 }

        omtp12PlusLan10gLinkFailureAlarm OBJECT-TYPE
		SYNTAX  DisplayString
		MAX-ACCESS  read-only
		STATUS  current
		DESCRIPTION
		       "For port configured with 10G LAN traffic, 
			In the case of remote fault alarm, the link failure 
			alarm is generated.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 123 }

        omtp12PlusLan10gFrameCheckSequenceAlarm OBJECT-TYPE
		SYNTAX  DisplayString
		MAX-ACCESS  read-only
		STATUS  current
		DESCRIPTION
		       "For port configured with 10G LAN traffic, 
			In the incoming ethernet frame, if the FCS value in the
			FCS byte and the FCS value calculated for the payload
			of the frame doesnt match, then number of FCS errors
			is incremented. If in one second 50 such FCS errors
			are got, then FCS this alarm will be generated. 
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 124 }

        omtp12PlusLan10gCarrierStatusAlarm OBJECT-TYPE
		SYNTAX  DisplayString
		MAX-ACCESS  read-only
		STATUS  current
		DESCRIPTION
		       "For port configured with 10G LAN traffic, 
			Whenever there is an absence of the carrier signal
			i.e. carrier sense loss occurs this alarm is generated.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 125 }

        omtp12PlusLan10gHighBerAlarm OBJECT-TYPE
		SYNTAX  DisplayString
		MAX-ACCESS  read-only
		STATUS  current
		DESCRIPTION
		       "For port configured with 10G LAN traffic, 
			High Bit Errors Alarm is indicated when signal BER is greater than 1e−4
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 126 }

        omtp12PlusLan10gLocalFaultAlarm OBJECT-TYPE
		SYNTAX  DisplayString
		MAX-ACCESS  read-only
		STATUS  current
		DESCRIPTION
			"For port configured with 10G LAN traffic, 
			If Fault is detected on the receive data path then Local
			Fault Alarm is generated
			port should be configured with LAN10G traffic.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 127 }

        omtp12PlusLan10gRemoteFaultAlarm OBJECT-TYPE
		SYNTAX  DisplayString
		MAX-ACCESS  read-only
		STATUS  current
		DESCRIPTION
		       "For port configured with 10G LAN traffic, 
			If Fault is detected on the transmit data path then 
			Remote Fault Alarm is generated
			port should be configured with LAN10G traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 128 }

        omtp12PlusFcTransmitDisparityInversionDefectAlarm OBJECT-TYPE
		SYNTAX  DisplayString
		MAX-ACCESS  read-only
		STATUS  current
		DESCRIPTION
		        "For port configured with FC 800/1200 traffic, 
			Get FC Transmit Display Invert status
			for requested port configured with FC traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 141 }

        omtp12PlusFcTransmitDigitalLossOfLinkDefectAlarm OBJECT-TYPE
		SYNTAX  DisplayString
		MAX-ACCESS  read-only
		STATUS  current
		DESCRIPTION
		        "For port configured with FC 800/1200 traffic, 
			Get FC Transmit DLOLB status 
			for requested port configured with FC traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 142 }

        omtp12PlusFcTrasnmitLossofSynchronizationDefectAlarm OBJECT-TYPE
		SYNTAX  DisplayString
		MAX-ACCESS  read-only
		STATUS  current
		DESCRIPTION
		        "For port configured with FC 800/1200 traffic, 
			Get FC Transmit Sync status 
			for requested port configured with FC traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 143 }

        omtp12PlusFcReceiveDigitalLossofLinkDefectAlarm OBJECT-TYPE
		SYNTAX  DisplayString
		MAX-ACCESS  read-only
		STATUS  current
		DESCRIPTION
		        "For port configured with FC 800/1200 traffic, 
			Get FC Receive DLOLB status 
			for requested port configured with FC traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 144 }

        omtp12PlusFcReceiveLossofSynchronizationDefectAlarm OBJECT-TYPE
		SYNTAX  DisplayString
		MAX-ACCESS  read-only
		STATUS  current
		DESCRIPTION
		        "For port configured with FC 800/1200 traffic, 
			Get FC Receive Sync alarm status 
			for requested port configured with FC traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 145 }

        omtp12PlusFcReceiveTransitionDetectDefectAlarm OBJECT-TYPE
		SYNTAX  DisplayString
		MAX-ACCESS  read-only
		STATUS  current
		DESCRIPTION
		        "For port configured with FC 800/1200 traffic, 
			Get FC Receive Xdet alarm status 
			for requested port configured with FC traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 146 }

        omtp12PlusFcReceiveAnalogLossofSignalDefectAlarm OBJECT-TYPE
		SYNTAX  DisplayString
		MAX-ACCESS  read-only
		STATUS  current
		DESCRIPTION
		        "For port configured with FC 800/1200 traffic, 
			Get FC Receive Asd alarm status 
			for requested port configured with FC traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 147 }

        omtp12PlusFcReceiveLineCodeViolationDefectAlarm OBJECT-TYPE
		SYNTAX  DisplayString
		MAX-ACCESS  read-only
		STATUS  current
		DESCRIPTION
		        "For port configured with FC 800/1200 traffic, 
			Get FC Receive Lcv alarm status 
			for requested port configured with FC traffic
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 148 }

        omtp12PlusGfpCsfSignalFailAlarm OBJECT-TYPE
		SYNTAX  DisplayString
		MAX-ACCESS  read-only
		STATUS  current
		DESCRIPTION
		        "If signal loss at the far-end occurs, then
			this alarm is detected at the near-end card.
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 161 }

        omtp12PlusGfpCsfLinkFailAlarm OBJECT-TYPE
		SYNTAX  DisplayString
		MAX-ACCESS  read-only
		STATUS  current
		DESCRIPTION
			"If there is a link failure occured at the far-end
			card, then this alarm is detected at the near-end card 
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 162 }

        omtp12PlusGfpCoreHeaderErrorAlarm OBJECT-TYPE
		SYNTAX  DisplayString
		MAX-ACCESS  read-only
		STATUS  current
		DESCRIPTION
			"This alarm is generated if the core header error
			count is found to be greater than 50 for a particular
			instance. i.e. for a particular second 
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 163 }

        omtp12PlusGfpExtentionHeaderErrorAlarm OBJECT-TYPE
		SYNTAX  DisplayString
		MAX-ACCESS  read-only
		STATUS  current
		DESCRIPTION
			"This alarm is generated if the extention header error
			count is found to be greater than 50 for a particular
			instance. i.e. for a particular second 
			-----------------------------
			omtp12PlusInterfaceNumber:
			1 - CLIENT-1
			-----------------------------
			Values :
			If Alarm is Present - Date and Time Stamp
				    eg:2017-5-18,9:47:20.0,+5:30
			If Alarm is Absent  - 0
			-----------------------------"
               ::= { omtp12PlusAlarmQueryEntry 164 }

	omtp12PlusAlarmQueryTableRowStatus OBJECT-TYPE
              SYNTAX      RowStatus
              MAX-ACCESS  read-write
              STATUS      current
              DESCRIPTION
                      "	This is MIB realted property,
			NOT to be considered as a card property"
              ::= { omtp12PlusAlarmQueryEntry 165 }	


--*****************************************************************************
--				    PERFORMANCE
--***************************************************************************** 	
	omtp12PlusPerformanceTable OBJECT-TYPE
		SYNTAX SEQUENCE OF Omtp12PlusPerformanceEntry
		MAX-ACCESS not-accessible
		STATUS current
		DESCRIPTION
			"we can get performance details of the OMTP12-PLUS Card"
	
		::= { omtp12PlusPerformance 1 }

	omtp12PlusPerformanceEntry OBJECT-TYPE
		SYNTAX Omtp12PlusPerformanceEntry
		MAX-ACCESS not-accessible
		STATUS current
		DESCRIPTION 
			""
	
		INDEX   { node, rack , subRack , slot , omtp12PlusInterfaceNumber}
	
		::= { omtp12PlusPerformanceTable 1 }

		Omtp12PlusPerformanceEntry ::= 
			SEQUENCE {
					omtp12PlusXfpInputPower                                     		DisplayString,
				        omtp12PlusXfpOutputPower                                    		DisplayString,
				        omtp12PlusXfpBiasCurrent                                    		DisplayString,
				        omtp12PlusXfpSupplyVoltage                                  		DisplayString,
				        omtp12PlusXfpTemperature                                    		DisplayString,
				        omtp12PlusOtnFecUncorrectedWords                            		DisplayString,
				        omtp12PlusOtnFecCorrectedBits                              		DisplayString,       
				        omtp12PlusOtnFecZerosCorrectedBits                          		DisplayString,
				        omtp12PlusOtnFecOnesCorrectedBits                           		DisplayString,
				        omtp12PlusOtuBitInterleavedParityErrors                     		DisplayString,
				        omtp12PlusOtuIncomingAlignmentErrorSeconds                  		DisplayString,
				        omtp12PlusOtuBackwardErrorIndicationErrorCount                  	DisplayString,
				        omtp12PlusOtuBackwardIncomingAlignmentErrorSeconds          		DisplayString,
				        omtp12PlusOtuErrorFreeSeconds						DisplayString,
				        omtp12PlusOtuErrorSeconds						DisplayString,
				        omtp12PlusOtuBackgroundBlockErrors					DisplayString,
				        omtp12PlusOtuSevereErrorSeconds						DisplayString,
				        omtp12PlusOtuUnavailableSeconds						DisplayString,
				        omtp12PlusOtuBackgroundBlockErrorRatio					DisplayString,
				        omtp12PlusOtuSevereErrorSecondsErrorRatio				DisplayString,
				        omtp12PlusOtuFarEndErrorFreeSeconds					DisplayString,
				        omtp12PlusOtuFarEndErrorSeconds						DisplayString,
				        omtp12PlusOtuFarEndBackgroundBlockErrors				DisplayString,
				        omtp12PlusOtuFarEndSevereErrorSeconds					DisplayString,
				        omtp12PlusOtuFarEndUnavailableSeconds					DisplayString,
				        omtp12PlusOtuFarEndBackgroundBlockErrorRatio				DisplayString,
				        omtp12PlusOtuFarEndSevereErrorSecondsErrorRatio				DisplayString,
					omtp12PlusOtuErrorRatio							DisplayString,
					omtp12PlusOtuBitErrorRate						DisplayString,
					omtp12PlusOtuFramesReceived						DisplayString,
				        omtp12PlusOduBitInterleavedParityErrors					DisplayString,
				        omtp12PlusOduTcm1BitInterleavedParityErrors				DisplayString,
				        omtp12PlusOduTcm2BitInterleavedParityErrors				DisplayString,
				        omtp12PlusOduTcm3BitInterleavedParityErrors				DisplayString,
				        omtp12PlusOduTcm4BitInterleavedParityErrors				DisplayString,
				        omtp12PlusOduTcm5BitInterleavedParityErrors				DisplayString,
				        omtp12PlusOduTcm6BitInterleavedParityErrors				DisplayString,
				        omtp12PlusOduTcm1IncomingAlignmentErrorSeconds				DisplayString,
				        omtp12PlusOduBackwardErrorIndicationErrorCount				DisplayString,
				        omtp12PlusOduTcm1BackwardErrorIndicationErrorCount			DisplayString,
				        omtp12PlusOduTcm2BackwardErrorIndicationErrorCount			DisplayString,
				        omtp12PlusOduTcm3BackwardErrorIndicationErrorCount			DisplayString,
				        omtp12PlusOduTcm4BackwardErrorIndicationErrorCount			DisplayString,
				        omtp12PlusOduTcm5BackwardErrorIndicationErrorCount			DisplayString,
				        omtp12PlusOduTcm6BackwardErrorIndicationErrorCount			DisplayString,
				        omtp12PlusOduTcm1BackwardIncomingAlignmentErrorSeconds			DisplayString,
				        omtp12PlusOduDelayMeasurement						DisplayString,
				        omtp12PlusOduErrorFreeSeconds						DisplayString,
				        omtp12PlusOduErrorSeconds						DisplayString,
				        omtp12PlusOduBackgroundBlockErrors					DisplayString,
				        omtp12PlusOduSevereErrorSeconds						DisplayString,
				        omtp12PlusOduUnavailableSeconds						DisplayString,
				        omtp12PlusOduBackgroundBlockErrorRatio					DisplayString,
				        omtp12PlusOduSevereErrorSecondsErrorRatio				DisplayString,
				        omtp12PlusOduFarEndErrorFreeSeconds					DisplayString,
				        omtp12PlusOduFarEndErrorSeconds						DisplayString,
				        omtp12PlusOduFarEndBackgroundBlockErrors				DisplayString,
				        omtp12PlusOduFarEndSevereErrorSeconds					DisplayString,
				        omtp12PlusOduFarEndUnavailableSeconds					DisplayString,
				        omtp12PlusOduFarEndBackgroundBlockErrorRatio				DisplayString,
				        omtp12PlusOduFarEndSevereErrorSecondsErrorRatio				DisplayString,
				        omtp12PlusSdhRsB1BitInterleavedParityErrors				DisplayString,
				        omtp12PlusSdhMsB2BitInterleavedParityErrors				DisplayString,
				        omtp12PlusSdhMsB3BitInterleavedParityErrors				DisplayString,
				        omtp12PlusSdhMsRemoteErrorIndicationErrorCount				DisplayString,
				        omtp12PlusSdhMsRemoteDefectIndicationErrorCount				DisplayString,
				        omtp12PlusSdhErrorFreeSeconds						DisplayString,
				        omtp12PlusSdhErrorSeconds						DisplayString,
				        omtp12PlusSdhBackgroundBlockErrors					DisplayString,
				        omtp12PlusSdhSevereErrorSeconds						DisplayString,
				        omtp12PlusSdhUnavailableSeconds						DisplayString,
				        omtp12PlusSdhErrorSecondsErrorRatio					DisplayString,
				        omtp12PlusSdhBackgroundBlockErrorRatio					DisplayString,
				        omtp12PlusSdhSevereErrorSecondsErrorRatio				DisplayString,
				        omtp12PlusWan10gRsB1BitInterleavedParityErrors				DisplayString,
				        omtp12PlusWan10gMsB2BitInterleavedParityErrors				DisplayString,
				        omtp12PlusWan10gMsB3BitInterleavedParityErrors				DisplayString,
				        omtp12PlusWan10gMsRemoteErrorIndicationErrorCount			DisplayString,
				        omtp12PlusWan10gMsRemoteDefectIndicationErrorCount			DisplayString,
				        omtp12PlusWan10gErrorFreeSeconds					DisplayString,
				        omtp12PlusWan10gErrorSeconds						DisplayString,
				        omtp12PlusWan10gBackgroundBlockErrors					DisplayString,
				        omtp12PlusWan10gSevereErrorSeconds					DisplayString,
				        omtp12PlusWan10gUnavailableSeconds					DisplayString,
				        omtp12PlusWan10gErrorSecondsErrorRatio					DisplayString,
				        omtp12PlusWan10gBackgroundBlockErrorRatio				DisplayString,
				        omtp12PlusWan10gSevereErrorSecondsErrorRatio				DisplayString,
				        omtp12PlusLan10gMacTerminatedFramesTransmitted				DisplayString,
				        omtp12PlusLan10gMacTerminatedFramesReceived				DisplayString,
				        omtp12PlusLan10gMacTerminatedPauseFramesTransmitted			DisplayString,
				        omtp12PlusLan10gMacTerminatedPauseFramesReceived			DisplayString,
				        omtp12PlusLan10gMacTerminatedUnicastFramesTransmitted			DisplayString,
				        omtp12PlusLan10gMacTerminatedUnicastFramesReceived			DisplayString,
				        omtp12PlusLan10gMacTerminatedMulticastFramesTransmitted			DisplayString,
				        omtp12PlusLan10gMacTerminatedMulticastFramesReceived			DisplayString,
				        omtp12PlusLan10gMacTerminatedBroadcastFramesTransmitted			DisplayString,
				        omtp12PlusLan10gMacTerminatedBroadcastFramesReceived			DisplayString,
				        omtp12PlusLan10gMacTerminatedUnderSizeFramesTransmitted			DisplayString,
				        omtp12PlusLan10gMacTerminatedUnderSizeFramesReceived			DisplayString,
				        omtp12PlusLan10gMacTerminatedOverSizeFramesTransmitted			DisplayString,
				        omtp12PlusLan10gMacTerminatedOverSizeFramesReceived			DisplayString,
				        omtp12PlusLan10gMacTerminatedVlanTaggedFramesTransmitted		DisplayString,
				        omtp12PlusLan10gMacTerminatedVlanTaggedFramesReceived			DisplayString,
				        omtp12PlusLan10gMacTerminatedFrameSymbolErrorsReceived			DisplayString,
				        omtp12PlusLan10gMacTerminatedFragmentFramesReceived			DisplayString,
				        omtp12PlusLan10gMacTerminatedFrameCheckSequenceErrorsReceived		DisplayString,
					omtp12PlusLan10gMacTerminatedFramesReceivedWithNoDefect			DisplayString,
					omtp12PlusLan10gMacTerminatedBytesTransmitted				DisplayString,
					omtp12PlusLan10gMacTerminatedBytesReceived				DisplayString,	
					omtp12PlusLan10gMacTerminatedControlFramesTransmitted			DisplayString,
					omtp12PlusLan10gMacTerminatedControlFramesReceived			DisplayString,
				        omtp12PlusLan10gTransparentTransmitLcvCount				DisplayString,
				        omtp12PlusLan10gTransparentTransmitPropagationErrorDeletionCount	DisplayString,
				        omtp12PlusLan10gTransparentTransmitIdleDeletionCount			DisplayString,
				        omtp12PlusLan10gTransparentTransmitConfDeletionCount			DisplayString,
				        omtp12PlusLan10gTransparentTransmitPropagationInsertionCount		DisplayString,
				        omtp12PlusLan10gTransparentTransmitIdleInsertionCount			DisplayString,
				        omtp12PlusLan10gTransparentTransmitConfInsertionCount			DisplayString,
				        omtp12PlusLan10gTransparentReceiveLcvCount				DisplayString,
				        omtp12PlusLan10gTransparentReceivePropagationErrorDeletionCount		DisplayString,
				        omtp12PlusLan10gTransparentReceiveIdleDeletionCount			DisplayString,
				        omtp12PlusLan10gTransparentReceiveConfDeletionCount			DisplayString,
				        omtp12PlusLan10gTransparentReceivePacketDeletionCount			DisplayString,
				        omtp12PlusGfpCoreHeaderErrorCount					DisplayString,
				        omtp12PlusGfpExtentionHeaderErrorCount					DisplayString,
				        omtp12PlusGfpFrameCountWithSingleBitError				DisplayString,
					omtp12PlusGfpTypeHeaderErrorCount					DisplayString,
					omtp12PlusGfpReceiveDropFrameCount					DisplayString,
					omtp12PlusGfpReceiveExtensionHeaderIdentifierFilterDropCount		DisplayString,
				        omtp12PlusFcTransmitWordCount						DisplayString,
				        omtp12PlusFcTransmitBadCrc						DisplayString,
				        omtp12PlusFcTransmitTotalPackets					DisplayString,
				        omtp12PlusFcTransmitLcvCount						DisplayString,
				        omtp12PlusFcReceiveWordCount						DisplayString,
				        omtp12PlusFcReceiveBadCrc						DisplayString,
				        omtp12PlusFcReceiveTotalPackets						DisplayString,
				        omtp12PlusFcReceiveLcvCount						DisplayString,
				        omtp12PlusFcTransmitFillWordInsertionCount				DisplayString,
				        omtp12PlusFcTransmitPrimitiveSequenceInsertionCount			DisplayString,
				        omtp12PlusFcTransmitFillWordDeletionCount				DisplayString,
				        omtp12PlusFcTransmitPrimitiveSequenceDeletionCount			DisplayString,
					omtp12PlusPerformanceTableRowStatus					RowStatus
			}
              
        omtp12PlusXfpInputPower OBJECT-TYPE
		SYNTAX  DisplayString
		MAX-ACCESS  read-only
		STATUS  current
		DESCRIPTION
			"Gives the current Input power(dbm) received at the port
			-----------------------------
			omtp12PlusInterfaceNumber:
			1 - CLIENT-1
			2 - LINE-1
			3 - LINE-2
			-----------------------------
			Values:
			eg: -9.0
			-----------------------------"
        ::= { omtp12PlusPerformanceEntry 1 }

        omtp12PlusXfpOutputPower OBJECT-TYPE
		SYNTAX  DisplayString
		MAX-ACCESS  read-only
		STATUS  current
		DESCRIPTION
			"Gives the current Output power(dbm) transmitted by the port
			-----------------------------
			omtp12PlusInterfaceNumber:
			1 - CLIENT-1
			2 - LINE-1
			3 - LINE-2
			-----------------------------
			Values:
			eg: -0.6
			-----------------------------"
        ::= { omtp12PlusPerformanceEntry 2 }


	omtp12PlusXfpBiasCurrent OBJECT-TYPE
		SYNTAX  DisplayString
		MAX-ACCESS  read-only
		STATUS  current
		DESCRIPTION
			"Gives the bias current(mA) thats transmitted at the port
			-----------------------------
			omtp12PlusInterfaceNumber:
			1 - CLIENT-1
			2 - LINE-1
			3 - LINE-2
			-----------------------------
			Values:
			eg: 55
			-----------------------------"
        ::= { omtp12PlusPerformanceEntry 3 }

	omtp12PlusXfpSupplyVoltage OBJECT-TYPE
		SYNTAX  DisplayString
		MAX-ACCESS  read-only
		STATUS  current
		DESCRIPTION
			"Gives the Supply Voltage of the port
			-----------------------------
			omtp12PlusInterfaceNumber:
			1 - CLIENT-1
			2 - LINE-1
			3 - LINE-2
			-----------------------------
			Values:
			eg: 3.3
			-----------------------------"
	::= { omtp12PlusPerformanceEntry 4 }

	omtp12PlusXfpTemperature OBJECT-TYPE
		SYNTAX  DisplayString
		MAX-ACCESS  read-only
		STATUS  current
		DESCRIPTION
			"Gives the temperature(degree celcius) of the transmitter at  the port
			-----------------------------
			omtp12PlusInterfaceNumber:
			1 - CLIENT-1
			2 - LINE-1
			3 - LINE-2
			-----------------------------
			Values:
			eg: 33.35
			-----------------------------"
        ::= { omtp12PlusPerformanceEntry 5 }

        omtp12PlusOtnFecUncorrectedWords OBJECT-TYPE
		SYNTAX  DisplayString
		MAX-ACCESS  read-only
		STATUS  current
		DESCRIPTION
			"For port configured with OTU2 traffic, 
			OTU Uncorrected Word Error Counter counts the number of
			FEC errored code words that could not be corrected.
			-----------------------------
			omtp12PlusInterfaceNumber:
			1 - CLIENT-1
			2 - LINE-1
			3 - LINE-2
			-----------------------------
			Values:
			eg: 1234
			-----------------------------"
        ::= { omtp12PlusPerformanceEntry 11 }

	omtp12PlusOtnFecCorrectedBits OBJECT-TYPE
		SYNTAX  DisplayString
		MAX-ACCESS  read-only
		STATUS  current
		DESCRIPTION
			"For port configured with OTU2 traffic, 
			OTU Corrected Bit Error Counter counts the number of
			FEC error bits that could be corrected(sum of ones
			corrected and zeros corrected bits).
			-----------------------------
			omtp12PlusInterfaceNumber:
			1 - CLIENT-1
			2 - LINE-1
			3 - LINE-2
			-----------------------------
			Values:
			eg: 1234
			-----------------------------"
        ::= { omtp12PlusPerformanceEntry 12 }

        omtp12PlusOtnFecZerosCorrectedBits OBJECT-TYPE
		SYNTAX  DisplayString
		MAX-ACCESS  read-only
		STATUS  current
		DESCRIPTION
			"For port configured with OTU2 traffic, 
			OTU Zero Corrected Bits Error Counter counts the number
			of FEC error bits that could be corrected from
			one to zero value(Expected 0 but received as 1).
			-----------------------------
			omtp12PlusInterfaceNumber:
			1 - CLIENT-1
			2 - LINE-1
			3 - LINE-2
			-----------------------------
			Values:
			eg: 1234
			-----------------------------"
	::= { omtp12PlusPerformanceEntry 13 }

        omtp12PlusOtnFecOnesCorrectedBits OBJECT-TYPE
		SYNTAX  DisplayString
		MAX-ACCESS  read-only
		STATUS  current
		DESCRIPTION
			"For port configured with OTU2 traffic, 
			OTU Ones Corrected Byte Error Counter counts the number
			of FEC error bytes that could be corrected from
			zero to one value(Expected 1 but received as 0).
			-----------------------------
			omtp12PlusInterfaceNumber:
			1 - CLIENT-1
			2 - LINE-1
			3 - LINE-2
			-----------------------------
			Values:
			eg: 1234
			-----------------------------"
		::= { omtp12PlusPerformanceEntry 14 }

        omtp12PlusOtuBitInterleavedParityErrors OBJECT-TYPE
		SYNTAX  DisplayString
		MAX-ACCESS  read-only
		STATUS  current
		DESCRIPTION
			"For port configured with OTU2 traffic, 
			OTU-BIP Counter counts the Parity errors evaluated by
			SM field of an OTU2 frame.
			-----------------------------
			omtp12PlusInterfaceNumber:
			1 - CLIENT-1
			2 - LINE-1
			3 - LINE-2
			-----------------------------
			Values:
			eg: 1234
			-----------------------------"
	::= { omtp12PlusPerformanceEntry 15 }

        omtp12PlusOtuIncomingAlignmentErrorSeconds OBJECT-TYPE
		SYNTAX  DisplayString
		MAX-ACCESS  read-only
		STATUS  current
		DESCRIPTION
			"For port configured with OTU2 traffic, 
			OTU Incoming Alignment Error Count increases,
			when OTU IAE Alarm is detected in that particular second
			of the incoming OTU signal
			-----------------------------
			omtp12PlusInterfaceNumber:
			1 - CLIENT-1
			2 - LINE-1
			3 - LINE-2
			-----------------------------
			Values:
			eg: 1234
			-----------------------------"
	::= { omtp12PlusPerformanceEntry 16 }

        omtp12PlusOtuBackwardErrorIndicationErrorCount OBJECT-TYPE
		SYNTAX  DisplayString
		MAX-ACCESS  read-only
		STATUS  current
		DESCRIPTION
			"For port configured with OTU2 traffic, 
			OTU-BEI Counter increases when SM-BEI Alarm is 
			detected in that particular second
			of the incoming OTU signal
			-----------------------------
			omtp12PlusInterfaceNumber:
			1 - CLIENT-1
			2 - LINE-1
			3 - LINE-2
			-----------------------------
			Values:
			eg: 1234
			-----------------------------"
	::= { omtp12PlusPerformanceEntry 17 }

        omtp12PlusOtuBackwardIncomingAlignmentErrorSeconds OBJECT-TYPE
		SYNTAX  DisplayString
		MAX-ACCESS  read-only
		STATUS  current
		DESCRIPTION
			"For port configured with OTU2 traffic, 
			OTU-BIAE Counter increases when SM-BIAE Alarm is 
			detected in that particular second
			of the incoming OTU signal
			-----------------------------
			omtp12PlusInterfaceNumber:
			1 - CLIENT-1
			2 - LINE-1
			3 - LINE-2
			-----------------------------
			Values:
			eg: 1234
			-----------------------------"
	::= { omtp12PlusPerformanceEntry 18 }

        omtp12PlusOtuErrorFreeSeconds OBJECT-TYPE
		SYNTAX  DisplayString
		MAX-ACCESS  read-only
		STATUS  current
		DESCRIPTION
			"For port configured with OTU2 traffic, 
			OTU Error Free Seconds increases when no BIP errors
			or defects are detected
			-----------------------------
			omtp12PlusInterfaceNumber:
			1 - CLIENT-1
			2 - LINE-1
			3 - LINE-2
			-----------------------------
			Values:
			eg: 1234
			-----------------------------"
	::= { omtp12PlusPerformanceEntry 19 }

        omtp12PlusOtuErrorSeconds OBJECT-TYPE
		SYNTAX  DisplayString
		MAX-ACCESS  read-only
		STATUS  current
		DESCRIPTION
			"For port configured with OTU2 traffic, 
			OTU Error Seconds increases when any defects like 
			OTU-AIS, SM-TIM etc are detected at the
			section monitoring level
			-----------------------------
			omtp12PlusInterfaceNumber:
			1 - CLIENT-1
			2 - LINE-1
			3 - LINE-2
			-----------------------------
			Values:
			eg: 1234
			-----------------------------"
	::= { omtp12PlusPerformanceEntry 20 }

        omtp12PlusOtuBackgroundBlockErrors OBJECT-TYPE
		SYNTAX  DisplayString
		MAX-ACCESS  read-only
		STATUS  current
		DESCRIPTION
			"For port configured with OTU2 traffic, 
			OTU Background Block Errors increases on defects 
			detected and when BIP errors are less than 15% errored
			blocks received 
			-----------------------------
			omtp12PlusInterfaceNumber:
			1 - CLIENT-1
			2 - LINE-1
			3 - LINE-2
			-----------------------------
			Values:
			eg: 1234
			-----------------------------"
	::= { omtp12PlusPerformanceEntry 21 }

        omtp12PlusOtuSevereErrorSeconds OBJECT-TYPE
		SYNTAX  DisplayString
		MAX-ACCESS  read-only
		STATUS  current
		DESCRIPTION
			"For port configured with OTU2 traffic, 
			OTU Severe Error Seconds increases on defects
			detected and when BIP errors are greater than or
			equal to 15% errored blocks received 
			-----------------------------
			omtp12PlusInterfaceNumber:
			1 - CLIENT-1
			2 - LINE-1
			3 - LINE-2
			-----------------------------
			Values:
			eg: 1234
			-----------------------------"
	::= { omtp12PlusPerformanceEntry 22 }

        omtp12PlusOtuUnavailableSeconds OBJECT-TYPE
		SYNTAX  DisplayString
		MAX-ACCESS  read-only
		STATUS  current
		DESCRIPTION
			"For port configured with OTU2 traffic, 
			OTU Unavailable Seconds increases,
			when 10 consecutive
			Severe OTU Error seconds are detected
			-----------------------------
			omtp12PlusInterfaceNumber:
			1 - CLIENT-1
			2 - LINE-1
			3 - LINE-2
			-----------------------------
			Values:
			eg: 1234
			-----------------------------"
	::= { omtp12PlusPerformanceEntry 23 }

        omtp12PlusOtuBackgroundBlockErrorRatio OBJECT-TYPE
		SYNTAX  DisplayString
		MAX-ACCESS  read-only
		STATUS  current
		DESCRIPTION
			"For port configured with OTU2 traffic, 
			Gives OTU Background Block Error Seconds Error Ratio.
			The ratio of BBE in available time to total seconds
			in available time during a fixed measurement interval.
			-----------------------------
			omtp12PlusInterfaceNumber:
			1 - CLIENT-1
			2 - LINE-1
			3 - LINE-2
			-----------------------------
			Values:
			eg: 1e-3
			-----------------------------"
	::= { omtp12PlusPerformanceEntry 25 }

        omtp12PlusOtuSevereErrorSecondsErrorRatio OBJECT-TYPE
		SYNTAX  DisplayString
		MAX-ACCESS  read-only
		STATUS  current
		DESCRIPTION
			"For port configured with OTU2 traffic, 
			Gives OTU Severe Error Seconds Error Ratio.
			The ratio of SES in available time to total seconds
			in available time during a fixed measurement interval.
			-----------------------------
			omtp12PlusInterfaceNumber:
			1 - CLIENT-1
			2 - LINE-1
			3 - LINE-2
			-----------------------------
			Values:
			eg: 1e-3
			-----------------------------"
	::= { omtp12PlusPerformanceEntry 26 }

        omtp12PlusOtuFarEndErrorFreeSeconds OBJECT-TYPE
		SYNTAX  DisplayString
		MAX-ACCESS  read-only
		STATUS  current
		DESCRIPTION
			"For port configured with OTU2 traffic, 
			OTU Far end Error Free Seconds, increases when no
			 backward errors or defects like BDI or BEI
			are detected in the incoming OTU signal.
			-----------------------------
			omtp12PlusInterfaceNumber:
			1 - CLIENT-1
			2 - LINE-1
			3 - LINE-2
			-----------------------------
			Values:
			eg: 1234
			-----------------------------"
	::= { omtp12PlusPerformanceEntry 27 }

        omtp12PlusOtuFarEndErrorSeconds OBJECT-TYPE
		SYNTAX  DisplayString
		MAX-ACCESS  read-only
		STATUS  current
		DESCRIPTION
			"For port configured with OTU2 traffic, 
			OTU Far End Error Seconds increases on
			detection of defects like BDI in incoming
			OTU signal.
			-----------------------------
			omtp12PlusInterfaceNumber:
			1 - CLIENT-1
			2 - LINE-1
			3 - LINE-2
			-----------------------------
			Values:
			eg: 1234
			-----------------------------"
	::= { omtp12PlusPerformanceEntry 28 }

        omtp12PlusOtuFarEndBackgroundBlockErrors OBJECT-TYPE
		SYNTAX  DisplayString
		MAX-ACCESS  read-only
		STATUS  current
		DESCRIPTION
			"For port configured with OTU2 traffic, 
			OTU Far End Background Block Errors increases when BEI
			errors are less than 15% Errored Blocks in incoming
			OTU signal.
			-----------------------------
			omtp12PlusInterfaceNumber:
			1 - CLIENT-1
			2 - LINE-1
			3 - LINE-2
			-----------------------------
			Values:
			eg: 1234
			-----------------------------"
	::= { omtp12PlusPerformanceEntry 29 }

        omtp12PlusOtuFarEndSevereErrorSeconds OBJECT-TYPE
		SYNTAX  DisplayString
		MAX-ACCESS  read-only
		STATUS  current
		DESCRIPTION
			"For port configured with OTU2 traffic, 
			OTU Far End Severe Error Seconds increases on defects
			like BDI are detected and when BEI errors are greater
			than or equal to 15% Errored Blocks in incoming OTU 
			signal.
			-----------------------------
			omtp12PlusInterfaceNumber:
			1 - CLIENT-1
			2 - LINE-1
			3 - LINE-2
			-----------------------------
			Values:
			eg: 1234
			-----------------------------"
	::= { omtp12PlusPerformanceEntry 30 }

        omtp12PlusOtuFarEndUnavailableSeconds OBJECT-TYPE
		SYNTAX  DisplayString
		MAX-ACCESS  read-only
		STATUS  current
		DESCRIPTION
			"For port configured with OTU2 traffic, 
			OTU Unavailable Seconds increases, after 9 consecutive
			OTU Far End Severe Error seconds are detected
			-----------------------------
			omtp12PlusInterfaceNumber:
			1 - CLIENT-1
			2 - LINE-1
			3 - LINE-2
			-----------------------------
			Values:
			eg: 1234
			-----------------------------"
	::= { omtp12PlusPerformanceEntry 31 }

        omtp12PlusOtuFarEndBackgroundBlockErrorRatio OBJECT-TYPE
		SYNTAX  DisplayString
		MAX-ACCESS  read-only
		STATUS  current
		DESCRIPTION
			"For port configured with OTU2 traffic, 
			Gives Otu Far End Background Block Error Ratio.
			The ratio of BBE in available time to total seconds
			in available time during a fixed measurement interval.
			-----------------------------
			omtp12PlusInterfaceNumber:
			1 - CLIENT-1
			2 - LINE-1
			3 - LINE-2
			-----------------------------
			Values:
			eg: 1e-3
			-----------------------------"
	::= { omtp12PlusPerformanceEntry 33 }

        omtp12PlusOtuFarEndSevereErrorSecondsErrorRatio OBJECT-TYPE
		SYNTAX  DisplayString
		MAX-ACCESS  read-only
		STATUS  current
		DESCRIPTION
			"For port configured with OTU2 traffic, 
			Gives Otu Far End Severe Error Seconds Error Ratio.
			The ratio of SES in available time to total seconds
			in available time during a fixed measurement interval.
			-----------------------------
			omtp12PlusInterfaceNumber:
			1 - CLIENT-1
			2 - LINE-1
			3 - LINE-2
			-----------------------------
			Values:
			eg: 1e-3
			-----------------------------"
	::= { omtp12PlusPerformanceEntry 34 }

	omtp12PlusOtuErrorRatio   OBJECT-TYPE
              SYNTAX  DisplayString
              MAX-ACCESS  read-only
              STATUS  current
              DESCRIPTION
			"For port configured with OTU2 traffic, 
			OTU Error Ratio for requested port. The ratio of 
			number of error bits to the number of bits received in
			a particular second
			-----------------------------
			omtp12PlusInterfaceNumber:
			1 - CLIENT-1
			2 - LINE-1
			3 - LINE-2
			-----------------------------	
			Value:
			eg: 4.0
			-----------------------------"
	::= { omtp12PlusPerformanceEntry 35 } 

	omtp12PlusOtuBitErrorRate  OBJECT-TYPE
              SYNTAX  DisplayString
              MAX-ACCESS  read-only
              STATUS  current
              DESCRIPTION
			"For port configured with OTU2 traffic, 
			Bit error rate is the Error ratio multiplied by the
			OTU2 standard signal data-rate( 10.709225316 Gbps )
			-----------------------------
			omtp12PlusInterfaceNumber:
			1 - CLIENT-1
			2 - LINE-1
			3 - LINE-2
			-----------------------------	
			Value:
			eg: 4.0
			-----------------------------"
	::= { omtp12PlusPerformanceEntry 36 }

	omtp12PlusOtuFramesReceived  OBJECT-TYPE
              SYNTAX  DisplayString
              MAX-ACCESS  read-only
              STATUS  current
              DESCRIPTION
			"For port configured with OTU2 traffic, gives the 
			gives the number of OTU frames transmitted.
			-----------------------------
			omtp12PlusInterfaceNumber:
			1 - CLIENT-1
			2 - LINE-1
			3 - LINE-2
			-----------------------------		
			Value:
			eg: 4.0
			-----------------------------"
	::= { omtp12PlusPerformanceEntry 37 }

        omtp12PlusOduBitInterleavedParityErrors OBJECT-TYPE
		SYNTAX  DisplayString
		MAX-ACCESS  read-only
		STATUS  current
		DESCRIPTION
			"For port configured with OTU2 traffic, 
			ODU-BIP Counter counts the Parity errors evaluated by
			PM field of an OTU2 frame
			-----------------------------
			omtp12PlusInterfaceNumber:
			1 - CLIENT-1
			2 - LINE-1
			3 - LINE-2
			-----------------------------
			Values:
			eg: 1234
			-----------------------------"
	::= { omtp12PlusPerformanceEntry 41 }

        omtp12PlusOduTcm1BitInterleavedParityErrors OBJECT-TYPE
		SYNTAX  DisplayString
		MAX-ACCESS  read-only
		STATUS  current
		DESCRIPTION
			"For port configured with OTU2 traffic, 
			TCM1-BIP Counter counts the Parity errors evaluated by
			TCM1 field in ODU2 frame
			-----------------------------
			omtp12PlusInterfaceNumber:
			1 - CLIENT-1
			2 - LINE-1
			3 - LINE-2
			-----------------------------
			Values:
			eg: 1234
			-----------------------------"
	::= { omtp12PlusPerformanceEntry 42 }

        omtp12PlusOduTcm2BitInterleavedParityErrors OBJECT-TYPE
		SYNTAX  DisplayString
		MAX-ACCESS  read-only
		STATUS  current
		DESCRIPTION
			"For port configured with OTU2 traffic, 
			TCM2-BIP Counter counts the Parity errors evaluated by
			TCM2 field in ODU2 frame
			-----------------------------
			omtp12PlusInterfaceNumber:
			1 - CLIENT-1
			2 - LINE-1
			3 - LINE-2
			-----------------------------
			Values:
			eg: 1234
			-----------------------------"
	::= { omtp12PlusPerformanceEntry 43 }

        omtp12PlusOduTcm3BitInterleavedParityErrors OBJECT-TYPE
		SYNTAX  DisplayString
		MAX-ACCESS  read-only
		STATUS  current
		DESCRIPTION
			"For port configured with OTU2 traffic, 
			TCM3-BIP Counter counts the Parity errors evaluated by
			TCM3 field in ODU2 frame
			-----------------------------
			omtp12PlusInterfaceNumber:
			1 - CLIENT-1
			2 - LINE-1
			3 - LINE-2
			-----------------------------
			Values:
			eg: 1234
			-----------------------------"
	::= { omtp12PlusPerformanceEntry 44 }

        omtp12PlusOduTcm4BitInterleavedParityErrors OBJECT-TYPE
		SYNTAX  DisplayString
		MAX-ACCESS  read-only
		STATUS  current
		DESCRIPTION
			"For port configured with OTU2 traffic, 
			TCM4-BIP Counter counts the Parity errors evaluated by
			TCM4 field in ODU2 frame
			-----------------------------
			omtp12PlusInterfaceNumber:
			1 - CLIENT-1
			2 - LINE-1
			3 - LINE-2
			-----------------------------
			Values:
			eg: 1234
			-----------------------------"
	::= { omtp12PlusPerformanceEntry 45 }

        omtp12PlusOduTcm5BitInterleavedParityErrors OBJECT-TYPE
		SYNTAX  DisplayString
		MAX-ACCESS  read-only
		STATUS  current
		DESCRIPTION
			"For port configured with OTU2 traffic, 
			TCM5-BIP Counter counts the Parity errors evaluated by
			TCM5 field in ODU2 frame
			-----------------------------
			omtp12PlusInterfaceNumber:
			1 - CLIENT-1
			2 - LINE-1
			3 - LINE-2
			-----------------------------
			Values:
			eg: 1234
			-----------------------------"
	::= { omtp12PlusPerformanceEntry 46 }

        omtp12PlusOduTcm6BitInterleavedParityErrors OBJECT-TYPE
		SYNTAX  DisplayString
		MAX-ACCESS  read-only
		STATUS  current
		DESCRIPTION
			"For port configured with OTU2 traffic, 
			TCM6-BIP Counter counts the Parity errors evaluated by
			TCM6 field in ODU2 frame
			-----------------------------
			omtp12PlusInterfaceNumber:
			1 - CLIENT-1
			2 - LINE-1
			3 - LINE-2
			-----------------------------
			Values:
			eg: 1234
			-----------------------------"
	::= { omtp12PlusPerformanceEntry 47 }

        omtp12PlusOduTcm1IncomingAlignmentErrorSeconds OBJECT-TYPE
		SYNTAX  DisplayString
		MAX-ACCESS  read-only
		STATUS  current
		DESCRIPTION
			"For port configured with OTU2 traffic,
			ODU Incoming Alignment Error Count increases,
			when ODU-TCM1-IAE is detected in that particular second
			of the incoming OTU signal
			-----------------------------
			omtp12PlusInterfaceNumber:
			1 - CLIENT-1
			2 - LINE-1
			3 - LINE-2
			-----------------------------
			Values:
			eg: 1234
			-----------------------------"
	::= { omtp12PlusPerformanceEntry 48 }

        omtp12PlusOduBackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code.
			-----------------------------
			omtp12PlusInterfaceNumber:
			1 - CLIENT-1
			2 - LINE-1
			3 - LINE-2
			-----------------------------
			Values:
			eg: 1234
			-----------------------------"
	::= { omtp12PlusPerformanceEntry 49 }

        omtp12PlusOduTcm1BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-1 level.
			-----------------------------
			omtp12PlusInterfaceNumber:
			1 - CLIENT-1
			2 - LINE-1
			3 - LINE-2
			-----------------------------
			Values:
			eg: 1234
			-----------------------------"
	::= { omtp12PlusPerformanceEntry 50 }

        omtp12PlusOduTcm2BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-2 level.
			-----------------------------
			omtp12PlusInterfaceNumber:
			1 - CLIENT-1
			2 - LINE-1
			3 - LINE-2
			-----------------------------
			Values:
			eg: 1234
			-----------------------------"
	::= { omtp12PlusPerformanceEntry 51 }

        omtp12PlusOduTcm3BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-3 level.
			-----------------------------
			omtp12PlusInterfaceNumber:
			1 - CLIENT-1
			2 - LINE-1
			3 - LINE-2
			-----------------------------
			Values:
			eg: 1234
			-----------------------------"
	::= { omtp12PlusPerformanceEntry 52 }

        omtp12PlusOduTcm4BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-4 level.
			-----------------------------
			omtp12PlusInterfaceNumber:
			1 - CLIENT-1
			2 - LINE-1
			3 - LINE-2
			-----------------------------
			Values:
			eg: 1234
			-----------------------------"
	::= { omtp12PlusPerformanceEntry 53 }

        omtp12PlusOduTcm5BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-5 level.
			-----------------------------
			omtp12PlusInterfaceNumber:
			1 - CLIENT-1
			2 - LINE-1
			3 - LINE-2
			-----------------------------
			Values:
			eg: 1234
			-----------------------------"
	::= { omtp12PlusPerformanceEntry 54 }

        omtp12PlusOduTcm6BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-6 level.
			-----------------------------
			omtp12PlusInterfaceNumber:
			1 - CLIENT-1
			2 - LINE-1
			3 - LINE-2
			-----------------------------
			Values:
			eg: 1234
			-----------------------------"
	::= { omtp12PlusPerformanceEntry 55 }

        omtp12PlusOduTcm1BackwardIncomingAlignmentErrorSeconds OBJECT-TYPE
		SYNTAX  DisplayString
		MAX-ACCESS  read-only
		STATUS  current
		DESCRIPTION
			"For port configured with OTU2 traffic,
			ODU Backward Incoming Alignment Error Count increases,
			when ODU-TCM1-BIAE is detected in that particular second
			of the incoming OTU signal
			-----------------------------
			omtp12PlusInterfaceNumber:
			1 - CLIENT-1
			2 - LINE-1
			3 - LINE-2
			-----------------------------
			Values:
			eg: 1234
			-----------------------------"
	::= { omtp12PlusPerformanceEntry 56 }

        omtp12PlusOduDelayMeasurement OBJECT-TYPE
		SYNTAX  DisplayString
		MAX-ACCESS  read-only
		STATUS  current
		DESCRIPTION
			"For port configured with OTU2 traffic, 
			Gives Delay measurement of OTU frame
			-----------------------------
			omtp12PlusInterfaceNumber:
			1 - CLIENT-1
			2 - LINE-1
			3 - LINE-2
			-----------------------------
			Values:
			eg: Reserved
			-----------------------------"
	::= { omtp12PlusPerformanceEntry 57 }

        omtp12PlusOduErrorFreeSeconds OBJECT-TYPE
		SYNTAX  DisplayString
		MAX-ACCESS  read-only
		STATUS  current
		DESCRIPTION
			"For port configured with OTU2 traffic, 
			ODU Error Free Seconds increases,
			when no BIP errors or defects are detected at the
			path monitoring level
			-----------------------------
			omtp12PlusInterfaceNumber:
			1 - CLIENT-1
			2 - LINE-1
			3 - LINE-2
			-----------------------------
			Values:
			eg: 1234
			-----------------------------"
	::= { omtp12PlusPerformanceEntry 58 }

        omtp12PlusOduErrorSeconds OBJECT-TYPE
		SYNTAX  DisplayString
		MAX-ACCESS  read-only
		STATUS  current
		DESCRIPTION
			"For port configured with OTU2 traffic, 
			ODU Error Seconds increases on defects detected at the
			path monitoring level
			-----------------------------
			omtp12PlusInterfaceNumber:
			1 - CLIENT-1
			2 - LINE-1
			3 - LINE-2
			-----------------------------
			Values:
			eg: 1234
			-----------------------------"
	::= { omtp12PlusPerformanceEntry 59 }

        omtp12PlusOduBackgroundBlockErrors OBJECT-TYPE
		SYNTAX  DisplayString
		MAX-ACCESS  read-only
		STATUS  current
		DESCRIPTION
			"For port configured with OTU2 traffic, 
			ODU Background Block Errors increases on defects 
			detected and when BIP errors are less than 15% 
			Errored Blocks in incoming OTU signal.
			-----------------------------
			omtp12PlusInterfaceNumber:
			1 - CLIENT-1
			2 - LINE-1
			3 - LINE-2
			-----------------------------
			Values:
			eg: 1234
			-----------------------------"
	::= { omtp12PlusPerformanceEntry 60 }

        omtp12PlusOduSevereErrorSeconds OBJECT-TYPE
		SYNTAX  DisplayString
		MAX-ACCESS  read-only
		STATUS  current
		DESCRIPTION
			"For port configured with OTU2 traffic, 
			ODU Severe Error Seconds increases on defects detected
			and when BIP errors are more than 15% Errored Blocks
			in incoming OTU signal.
			-----------------------------
			omtp12PlusInterfaceNumber:
			1 - CLIENT-1
			2 - LINE-1
			3 - LINE-2
			-----------------------------
			Values:
			eg: 1234
			-----------------------------"
	::= { omtp12PlusPerformanceEntry 61 }

        omtp12PlusOduUnavailableSeconds OBJECT-TYPE
		SYNTAX  DisplayString
		MAX-ACCESS  read-only
		STATUS  current
		DESCRIPTION
			"For port configured with OTU2 traffic, 
			ODU Unavailable Seconds increases, when 10 consecutive
			Severe
			ODU Error seconds are detected
			-----------------------------
			omtp12PlusInterfaceNumber:
			1 - CLIENT-1
			2 - LINE-1
			3 - LINE-2
			-----------------------------
			Values:
			eg: 1234
			-----------------------------"
	::= { omtp12PlusPerformanceEntry 62 }

        omtp12PlusOduBackgroundBlockErrorRatio OBJECT-TYPE
		SYNTAX  DisplayString
		MAX-ACCESS  read-only
		STATUS  current
		DESCRIPTION
			"For port configured with OTU2 traffic, 
			Gives ODU Background Block Error Ratio
			The ratio of BBE in available time to total seconds
			in available time during a fixed measurement interval.
			-----------------------------
			omtp12PlusInterfaceNumber:
			1 - CLIENT-1
			2 - LINE-1
			3 - LINE-2
			-----------------------------
			Values:
			eg: 1e-3
			-----------------------------"
	::= { omtp12PlusPerformanceEntry 64 }

        omtp12PlusOduSevereErrorSecondsErrorRatio OBJECT-TYPE
		SYNTAX  DisplayString
		MAX-ACCESS  read-only
		STATUS  current
		DESCRIPTION
			"For port configured with OTU2 traffic, 
			Gives ODU Severe Error Seconds Error Ratio
			The ratio of SES in available time to total seconds
			in available time during a fixed measurement interval.
			-----------------------------
			omtp12PlusInterfaceNumber:
			1 - CLIENT-1
			2 - LINE-1
			3 - LINE-2
			-----------------------------
			Values:
			eg: 1e-3
			-----------------------------"
	::= { omtp12PlusPerformanceEntry 65 }

        omtp12PlusOduFarEndErrorFreeSeconds OBJECT-TYPE
		SYNTAX  DisplayString
		MAX-ACCESS  read-only
		STATUS  current
		DESCRIPTION
			"For port configured with OTU2 traffic, 
			ODU Far end Error Free Seconds, increases when no
			errors or defects are detected
			-----------------------------
			omtp12PlusInterfaceNumber:
			1 - CLIENT-1
			2 - LINE-1
			3 - LINE-2
			-----------------------------
			Values:
			eg: 1234
			-----------------------------"
	::= { omtp12PlusPerformanceEntry 66 }

        omtp12PlusOduFarEndErrorSeconds OBJECT-TYPE
		SYNTAX  DisplayString
		MAX-ACCESS  read-only
		STATUS  current
		DESCRIPTION
			"For port configured with OTU2 traffic, 
			ODU Far End Error Seconds increases on detection of
			defects like BDI and BEI at path monitoring level
			-----------------------------
			omtp12PlusInterfaceNumber:
			1 - CLIENT-1
			2 - LINE-1
			3 - LINE-2
			-----------------------------
			Values:
			eg: 1234
			-----------------------------"
	::= { omtp12PlusPerformanceEntry 67 }

        omtp12PlusOduFarEndBackgroundBlockErrors OBJECT-TYPE
		SYNTAX  DisplayString
		MAX-ACCESS  read-only
		STATUS  current
		DESCRIPTION
			"For port configured with OTU2 traffic, 
			ODU Far End Background Block Errors increases when
			BEI errors are less than 15% Errored Blocks in
			incoming OTU signal.
			-----------------------------
			omtp12PlusInterfaceNumber:
			1 - CLIENT-1
			2 - LINE-1
			3 - LINE-2
			-----------------------------
			Values:
			eg: 1234
			-----------------------------"
	::= { omtp12PlusPerformanceEntry 68 }

        omtp12PlusOduFarEndSevereErrorSeconds OBJECT-TYPE
		SYNTAX  DisplayString
		MAX-ACCESS  read-only
		STATUS  current
		DESCRIPTION
			"For port configured with OTU2 traffic, 
			ODU Far End Severe Error Seconds increases on defects
			like BDI are detected and when BEI errors are more than
			15% Errored Blocks in incoming OTU signal.
			-----------------------------
			omtp12PlusInterfaceNumber:
			1 - CLIENT-1
			2 - LINE-1
			3 - LINE-2
			-----------------------------
			Values:
			eg: 1234
			-----------------------------"
	::= { omtp12PlusPerformanceEntry 69 }

        omtp12PlusOduFarEndUnavailableSeconds OBJECT-TYPE
		SYNTAX  DisplayString
		MAX-ACCESS  read-only
		STATUS  current
		DESCRIPTION
			"For port configured with OTU2 traffic, 
			ODU Far End Unavailable Seconds increases, when 10
		        consecutive OTU Far End Error seconds are detected
		       -----------------------------
			omtp12PlusInterfaceNumber:
			1 - CLIENT-1
			2 - LINE-1
			3 - LINE-2
			-----------------------------
			Values:
			eg: 1234
			-----------------------------"
	::= { omtp12PlusPerformanceEntry 70 }

        omtp12PlusOduFarEndBackgroundBlockErrorRatio OBJECT-TYPE
		SYNTAX  DisplayString
		MAX-ACCESS  read-only
		STATUS  current
		DESCRIPTION
			"For port configured with OTU2 traffic, 
			Gives ODU Far End Background Block Error Ratio
			The ratio of BBE in available time to total seconds
			in available time during a fixed measurement interval.
			-----------------------------
			omtp12PlusInterfaceNumber:
			1 - CLIENT-1
			2 - LINE-1
			3 - LINE-2
			-----------------------------
			Values:
			eg: 1e-3
			-----------------------------"
	::= { omtp12PlusPerformanceEntry 72 }

        omtp12PlusOduFarEndSevereErrorSecondsErrorRatio OBJECT-TYPE
		SYNTAX  DisplayString
		MAX-ACCESS  read-only
		STATUS  current
		DESCRIPTION
			"For port configured with OTU2 traffic, 
			Gives ODU Far End Severe Error Seconds Error Ratio
			The ratio of SES in available time to total seconds
			in available time during a fixed measurement interval.
			-----------------------------
			omtp12PlusInterfaceNumber:
			1 - CLIENT-1
			2 - LINE-1
			3 - LINE-2
			-----------------------------
			Values:
			eg: 1e-3
			-----------------------------"
	::= { omtp12PlusPerformanceEntry 73 }

        omtp12PlusSdhRsB1BitInterleavedParityErrors OBJECT-TYPE
		SYNTAX  DisplayString
		MAX-ACCESS  read-only
		STATUS  current
		DESCRIPTION
			"For port configured with SDH traffic, 
			SDH B1 BIP counter counts the Parity errors evaluated
			from byte B1 of the STM frame
			-----------------------------
			omtp12PlusInterfaceNumber:
			1 - CLIENT-1
			-----------------------------
			Values:
			eg: 1234
			-----------------------------"
	::= { omtp12PlusPerformanceEntry 81 }

        omtp12PlusSdhMsB2BitInterleavedParityErrors OBJECT-TYPE
		SYNTAX  DisplayString
		MAX-ACCESS  read-only
		STATUS  current
		DESCRIPTION
			"For port configured with SDH traffic, 
			SDH B2 BIP counter counts the Parity errors evaluated 
			from byte B2 of the STM frame
			-----------------------------
			omtp12PlusInterfaceNumber:
			1 - CLIENT-1
			-----------------------------
			Values:
			eg: 1234
			-----------------------------"
	::= { omtp12PlusPerformanceEntry 82 }

        omtp12PlusSdhMsB3BitInterleavedParityErrors OBJECT-TYPE
		SYNTAX  DisplayString
		MAX-ACCESS  read-only
		STATUS  current
		DESCRIPTION
			"For port configured with SDH traffic, 
			SDH B3 BIP counter counts the Parity errors evaluated 
			from byte B3 of the STM frame
			-----------------------------
			omtp12PlusInterfaceNumber:
			1 - CLIENT-1
			-----------------------------
			Values:
			eg: 1234
			-----------------------------"
	::= { omtp12PlusPerformanceEntry 83 }

        omtp12PlusSdhMsRemoteErrorIndicationErrorCount OBJECT-TYPE
		SYNTAX  DisplayString
		MAX-ACCESS  read-only
		STATUS  current
		DESCRIPTION
			"For port configured with SDH traffic, 
			SDH MS-REI error count increases when
			MS-REI is detected for that particular second
			in incoming SDH signal.
			-----------------------------
			omtp12PlusInterfaceNumber:
			1 - CLIENT-1
			-----------------------------
			Values:
			eg: 1234
			-----------------------------"
	::= { omtp12PlusPerformanceEntry 84 }

        omtp12PlusSdhMsRemoteDefectIndicationErrorCount OBJECT-TYPE
		SYNTAX  DisplayString
		MAX-ACCESS  read-only
		STATUS  current
		DESCRIPTION
			"For port configured with SDH traffic, 
			SDH MS-RDI error count increases when
			MS-RDI is detected for that particular second
			in incoming SDH signal.
			-----------------------------
			omtp12PlusInterfaceNumber:
			1 - CLIENT-1
			-----------------------------
			Values:
			eg: 1234
			-----------------------------"
	::= { omtp12PlusPerformanceEntry 85 }

        omtp12PlusSdhErrorFreeSeconds OBJECT-TYPE
		SYNTAX  DisplayString
		MAX-ACCESS  read-only
		STATUS  current
		DESCRIPTION
			"For port configured with SDH traffic, 
			SDH Error Free Seconds increases when no BIP
			errors or no defects are detected in incoming
			SDH signal.
			-----------------------------
			omtp12PlusInterfaceNumber:
			1 - CLIENT-1
			-----------------------------
			Values:
			eg: 1234
			-----------------------------"
	::= { omtp12PlusPerformanceEntry 86 }

        omtp12PlusSdhErrorSeconds OBJECT-TYPE
		SYNTAX  DisplayString
		MAX-ACCESS  read-only
		STATUS  current
		DESCRIPTION
			"For port configured with SDH traffic, 
			SDH Error Seconds increases on detection of BIP errors
			and defects like LOS, LOF, AIS etc in incoming SDH
			signal.
			-----------------------------
			omtp12PlusInterfaceNumber:
			1 - CLIENT-1
			-----------------------------
			Values:
			eg: 1234
			-----------------------------"
	::= { omtp12PlusPerformanceEntry 87 }

        omtp12PlusSdhBackgroundBlockErrors OBJECT-TYPE
		SYNTAX  DisplayString
		MAX-ACCESS  read-only
		STATUS  current
		DESCRIPTION
			"For port configured with SDH traffic, 
			SDH Background Block Errors increases on defects 
			detected and when BIP errors are less than 30%
			errored blocks in the incoming SDH signal.
			-----------------------------
			omtp12PlusInterfaceNumber:
			1 - CLIENT-1
			-----------------------------
			Values:
			eg: 1234
			-----------------------------"
	::= { omtp12PlusPerformanceEntry 88 }

        omtp12PlusSdhSevereErrorSeconds OBJECT-TYPE
		SYNTAX  DisplayString
		MAX-ACCESS  read-only
		STATUS  current
		DESCRIPTION
			"For port configured with SDH traffic, 
			SDH Severe Error Secodns increases on defects 
			detected and when BIP errors are greater than or equal
			to 30% errored blocks in the incoming SDH signal.
			-----------------------------
			omtp12PlusInterfaceNumber:
			1 - CLIENT-1
			-----------------------------
			Values:
			eg: 1234
			-----------------------------"
	::= { omtp12PlusPerformanceEntry 89 }

        omtp12PlusSdhUnavailableSeconds OBJECT-TYPE
		SYNTAX  DisplayString
		MAX-ACCESS  read-only
		STATUS  current
		DESCRIPTION
			"For port configured with SDH traffic, 
			SDH Unavailable Seconds increases, when 10 consecutive
			Severe Error seconds are detected
			-----------------------------
			omtp12PlusInterfaceNumber:
			1 - CLIENT-1
			-----------------------------
			Values:
			eg: 1234
			-----------------------------"
	::= { omtp12PlusPerformanceEntry 90 }

        omtp12PlusSdhErrorSecondsErrorRatio OBJECT-TYPE
		SYNTAX  DisplayString
		MAX-ACCESS  read-only
		STATUS  current
		DESCRIPTION
			"For port configured with SDH traffic, 
			Gives SDH Error Seconds Error Ratio.
			The ratio of ES in available time to total seconds
			in available time during a fixed measurement interval.
			-----------------------------
			omtp12PlusInterfaceNumber:
			1 - CLIENT-1
			-----------------------------
			Values:
			eg: 1234
			-----------------------------"
	::= { omtp12PlusPerformanceEntry 91 }

        omtp12PlusSdhBackgroundBlockErrorRatio OBJECT-TYPE
		SYNTAX  DisplayString
		MAX-ACCESS  read-only
		STATUS  current
		DESCRIPTION
			"For port configured with SDH traffic, 
			Gives SDH Background Block Error Ratio.
			The ratio of BBE in available time to total seconds
			in available time during a fixed measurement interval.
			-----------------------------
			omtp12PlusInterfaceNumber:
			1 - CLIENT-1
			-----------------------------
			Values:
			eg: 1234
			-----------------------------"
	::= { omtp12PlusPerformanceEntry 92 }

        omtp12PlusSdhSevereErrorSecondsErrorRatio OBJECT-TYPE
		SYNTAX  DisplayString
		MAX-ACCESS  read-only
		STATUS  current
		DESCRIPTION
			"For port configured with SDH traffic, 
			Gives SDH Severe Error Seconds Error Ratio.
			The ratio of SES in available time to total seconds
			in available time during a fixed measurement interval.
			-----------------------------
			omtp12PlusInterfaceNumber:
			1 - CLIENT-1
			-----------------------------
			Values:
			eg: 1234
			-----------------------------"
	::= { omtp12PlusPerformanceEntry 93 }

        omtp12PlusWan10gRsB1BitInterleavedParityErrors OBJECT-TYPE
		SYNTAX  DisplayString
		MAX-ACCESS  read-only
		STATUS  current
		DESCRIPTION
			"For port configured with 10G WAN traffic, 
			Wan10g B1 BIP counter counts the Parity errors evaluated
			from byte B1 of the STM frame
			-----------------------------
			omtp12PlusInterfaceNumber:
			1 - CLIENT-1
			-----------------------------
			Values:
			eg: 1234
			-----------------------------"
	::= { omtp12PlusPerformanceEntry 101 }

        omtp12PlusWan10gMsB2BitInterleavedParityErrors OBJECT-TYPE
		SYNTAX  DisplayString
		MAX-ACCESS  read-only
		STATUS  current
		DESCRIPTION
			"For port configured with 10G WAN traffic, 
			Wan10g B2 BIP counter counts the Parity errors evaluated 
			from byte B2 of the STM frame
			-----------------------------
			omtp12PlusInterfaceNumber:
			1 - CLIENT-1
			-----------------------------
			Values:
			eg: 1234
			-----------------------------"
	::= { omtp12PlusPerformanceEntry 102 }

        omtp12PlusWan10gMsB3BitInterleavedParityErrors OBJECT-TYPE
		SYNTAX  DisplayString
		MAX-ACCESS  read-only
		STATUS  current
		DESCRIPTION
			"For port configured with 10G WAN traffic, 
			Wan10g B3 BIP counter counts the Parity errors evaluated 
			from byte B3 of the STM frame
			-----------------------------
			omtp12PlusInterfaceNumber:
			1 - CLIENT-1
			-----------------------------
			Values:
			eg: 1234
			-----------------------------"
	::= { omtp12PlusPerformanceEntry 103 }

        omtp12PlusWan10gMsRemoteErrorIndicationErrorCount OBJECT-TYPE
		SYNTAX  DisplayString
		MAX-ACCESS  read-only
		STATUS  current
		DESCRIPTION
			"For port configured with 10G WAN traffic, 
			Wan10g MS-REI error count increases when
			MS-REI is detected for that particular second
			in incoming Wan10g signal.
			-----------------------------
			omtp12PlusInterfaceNumber:
			1 - CLIENT-1
			-----------------------------
			Values:
			eg: 1234
			-----------------------------"
	::= { omtp12PlusPerformanceEntry 104 }

        omtp12PlusWan10gMsRemoteDefectIndicationErrorCount OBJECT-TYPE
		SYNTAX  DisplayString
		MAX-ACCESS  read-only
		STATUS  current
		DESCRIPTION
			"For port configured with 10G WAN traffic, 
			Wan10g MS-RDI error count increases when
			MS-RDI is detected for that particular second
			in incoming Wan10g signal.
			-----------------------------
			omtp12PlusInterfaceNumber:
			1 - CLIENT-1
			-----------------------------
			Values:
			eg: 1234
			-----------------------------"
	::= { omtp12PlusPerformanceEntry 105 }

        omtp12PlusWan10gErrorFreeSeconds OBJECT-TYPE
		SYNTAX  DisplayString
		MAX-ACCESS  read-only
		STATUS  current
		DESCRIPTION
			"For port configured with 10G WAN traffic, 
			Wan10g Error Free Seconds increases when no BIP
			errors or no defects are detected in incoming
			Wan10g signal.
			-----------------------------
			omtp12PlusInterfaceNumber:
			1 - CLIENT-1
			-----------------------------
			Values:
			eg: 1234
			-----------------------------"
	::= { omtp12PlusPerformanceEntry 106 }

        omtp12PlusWan10gErrorSeconds OBJECT-TYPE
		SYNTAX  DisplayString
		MAX-ACCESS  read-only
		STATUS  current
		DESCRIPTION
			"For port configured with 10G WAN traffic, 
			Wan10g Error Seconds increases on detection of BIP errors
			and defects like LOS, LOF, AIS etc in incoming Wan10g
			signal.
			-----------------------------
			omtp12PlusInterfaceNumber:
			1 - CLIENT-1
			-----------------------------
			Values:
			eg: 1234
			-----------------------------"
	::= { omtp12PlusPerformanceEntry 107 }

        omtp12PlusWan10gBackgroundBlockErrors OBJECT-TYPE
		SYNTAX  DisplayString
		MAX-ACCESS  read-only
		STATUS  current
		DESCRIPTION
			"Wan10g Background Block Errors increases on defects 
			detected and when BIP errors are less than 30%
			errored blocks in the incoming Wan10g signal.
			-----------------------------
			omtp12PlusInterfaceNumber:
			1 - CLIENT-1
			-----------------------------
			Values:
			eg: 1234
			-----------------------------"
	::= { omtp12PlusPerformanceEntry 108 }

        omtp12PlusWan10gSevereErrorSeconds OBJECT-TYPE
		SYNTAX  DisplayString
		MAX-ACCESS  read-only
		STATUS  current
		DESCRIPTION
			"For port configured with 10G WAN traffic, 
			Wan10g Severe Error Secodns increases on defects 
			detected and when BIP errors are greater than or equal
			to 30% errored blocks in the incoming Wan10g signal.
			-----------------------------
			omtp12PlusInterfaceNumber:
			1 - CLIENT-1
			-----------------------------
			Values:
			eg: 1234
			-----------------------------"
	::= { omtp12PlusPerformanceEntry 109 }

        omtp12PlusWan10gUnavailableSeconds OBJECT-TYPE
		SYNTAX  DisplayString
		MAX-ACCESS  read-only
		STATUS  current
		DESCRIPTION
			"For port configured with 10G WAN traffic, 
			Wan10g Unavailable Seconds increases, when 10 consecutive
			Severe Error seconds are detected
			-----------------------------
			omtp12PlusInterfaceNumber:
			1 - CLIENT-1
			-----------------------------
			Values:
			eg: 1234
			-----------------------------"
	::= { omtp12PlusPerformanceEntry 110 }

        omtp12PlusWan10gErrorSecondsErrorRatio OBJECT-TYPE
		SYNTAX  DisplayString
		MAX-ACCESS  read-only
		STATUS  current
		DESCRIPTION
			"For port configured with 10G WAN traffic, 
			Gives Wan10g Error Seconds Error Ratio.
			The ratio of ES in available time to total seconds
			in available time during a fixed measurement interval.
			-----------------------------
			omtp12PlusInterfaceNumber:
			1 - CLIENT-1
			-----------------------------
			Values:
			eg: 1e-3
			-----------------------------"
	::= { omtp12PlusPerformanceEntry 111 }

        omtp12PlusWan10gBackgroundBlockErrorRatio OBJECT-TYPE
		SYNTAX  DisplayString
		MAX-ACCESS  read-only
		STATUS  current
		DESCRIPTION
			"For port configured with 10G WAN traffic, 
			Gives Wan10g Background Block Error Ratio.
			The ratio of BBE in available time to total seconds
			in available time during a fixed measurement interval.
			-----------------------------
			omtp12PlusInterfaceNumber:
			1 - CLIENT-1
			-----------------------------
			Values:
			eg: 1e-3
			-----------------------------"
	::= { omtp12PlusPerformanceEntry 112 }

        omtp12PlusWan10gSevereErrorSecondsErrorRatio OBJECT-TYPE
		SYNTAX  DisplayString
		MAX-ACCESS  read-only
		STATUS  current
		DESCRIPTION
			"For port configured with 10G WAN traffic, 
			Gives Wan10g Severe Error Seconds Error Ratio.
			The ratio of SES in available time to total seconds
			in available time during a fixed measurement interval.
			-----------------------------
			omtp12PlusInterfaceNumber:
			1 - CLIENT-1
			-----------------------------
			Values:
			eg: 1e-3
			-----------------------------"
	::= { omtp12PlusPerformanceEntry 113 }

        omtp12PlusLan10gMacTerminatedFramesTransmitted OBJECT-TYPE
		SYNTAX  DisplayString
		MAX-ACCESS  read-only
		STATUS  current
		DESCRIPTION
			"For port configured with 10G LAN traffic, 
			LAN 10G Frames transmitted counter counts the number of 
			Ethernet frame transmitted from the Client port 
			which is configured with 10G LAN traffic.
			-----------------------------
			omtp12PlusInterfaceNumber:
			1 - CLIENT-1
			-----------------------------
			Values:
			eg: 1234
			-----------------------------"
	::= { omtp12PlusPerformanceEntry 121 }

        omtp12PlusLan10gMacTerminatedFramesReceived OBJECT-TYPE
		SYNTAX  DisplayString
		MAX-ACCESS  read-only
		STATUS  current
		DESCRIPTION
			"For port configured with 10G LAN traffic, 
			LAN 10G Frames Received counter counts the number of 
			Ethernet frame received at the Client port 
			which is configured with 10G LAN traffic 
			-----------------------------
			omtp12PlusInterfaceNumber:
			1 - CLIENT-1
			-----------------------------
			Values:
			eg: 1234
			-----------------------------"
	::= { omtp12PlusPerformanceEntry 122 }

        omtp12PlusLan10gMacTerminatedPauseFramesTransmitted OBJECT-TYPE
		SYNTAX  DisplayString
		MAX-ACCESS  read-only
		STATUS  current
		DESCRIPTION
			"For port configured with 10G LAN traffic, 
			LAN 10G Pause Frames transmitted counter counts the
			number of Pause frame transmitted from port 
			which is configured with 10G LAN traffic 
			-----------------------------
			omtp12PlusInterfaceNumber:
			1 - CLIENT-1
			-----------------------------
			Values:
			eg: 1234
			-----------------------------"
	::= { omtp12PlusPerformanceEntry 123 }

        omtp12PlusLan10gMacTerminatedPauseFramesReceived OBJECT-TYPE
		SYNTAX  DisplayString
		MAX-ACCESS  read-only
		STATUS  current
		DESCRIPTION
			"For port configured with 10G LAN traffic, 
			LAN 10G Pause Frames received counter counts the
			number of Pause frame received at port 
			which is configured with 10G LAN traffic 
			-----------------------------
			omtp12PlusInterfaceNumber:
			1 - CLIENT-1
			-----------------------------
			Values:
			eg: 1234
			-----------------------------"
	::= { omtp12PlusPerformanceEntry 124 }

        omtp12PlusLan10gMacTerminatedUnicastFramesTransmitted OBJECT-TYPE
		SYNTAX  DisplayString
		MAX-ACCESS  read-only
		STATUS  current
		DESCRIPTION
			"For port configured with 10G LAN traffic, 
			Counts the number of unicast frames transmitted from port 
			which is configured with 10G LAN traffic 
			-----------------------------
			omtp12PlusInterfaceNumber:
			1 - CLIENT-1
			-----------------------------
			Values:
			eg: 1234
			-----------------------------"
	::= { omtp12PlusPerformanceEntry 125 }

        omtp12PlusLan10gMacTerminatedUnicastFramesReceived OBJECT-TYPE
		SYNTAX  DisplayString
		MAX-ACCESS  read-only
		STATUS  current
		DESCRIPTION
			"For port configured with 10G LAN traffic, 
			Counts the number of unicast frames received at port 
			which is configured with 10G LAN traffic
			-----------------------------
			omtp12PlusInterfaceNumber:
			1 - CLIENT-1
			-----------------------------
			Values:
			eg: 1234
			-----------------------------"
	::= { omtp12PlusPerformanceEntry 126 }

        omtp12PlusLan10gMacTerminatedMulticastFramesTransmitted OBJECT-TYPE
		SYNTAX  DisplayString
		MAX-ACCESS  read-only
		STATUS  current
		DESCRIPTION
			"For port configured with 10G LAN traffic, 
			Counts the number of multicast frames transmitted from port 
			which is configured with 10G LAN traffic
			-----------------------------
			omtp12PlusInterfaceNumber:
			1 - CLIENT-1
			-----------------------------
			Values:
			eg: 1234
			-----------------------------"
	::= { omtp12PlusPerformanceEntry 127 }

        omtp12PlusLan10gMacTerminatedMulticastFramesReceived OBJECT-TYPE
		SYNTAX  DisplayString
		MAX-ACCESS  read-only
		STATUS  current
		DESCRIPTION
			"For port configured with 10G LAN traffic, 
			Counts the number of multicast frames received at port 
			which is configured with 10G LAN traffic
			-----------------------------
			omtp12PlusInterfaceNumber:
			1 - CLIENT-1
			-----------------------------
			Values:
			eg: 1234
			-----------------------------"
        ::= { omtp12PlusPerformanceEntry 128 }

        omtp12PlusLan10gMacTerminatedBroadcastFramesTransmitted OBJECT-TYPE
		SYNTAX  DisplayString
		MAX-ACCESS  read-only
		STATUS  current
		DESCRIPTION
			"For port configured with 10G LAN traffic, 
			Counts the number of broadcast frames transmitted from
			port which is configured with 10G LAN traffic
			-----------------------------
			omtp12PlusInterfaceNumber:
			1 - CLIENT-1
			-----------------------------
			Values:
			eg: 1234
			-----------------------------"
	::= { omtp12PlusPerformanceEntry 129 }

        omtp12PlusLan10gMacTerminatedBroadcastFramesReceived OBJECT-TYPE
		SYNTAX  DisplayString
		MAX-ACCESS  read-only
		STATUS  current
		DESCRIPTION
			"For port configured with 10G LAN traffic, 
			Counts the number of broadcast frames received at port 
			which is configured with 10G LAN traffic
			-----------------------------
			omtp12PlusInterfaceNumber:
			1 - CLIENT-1
			-----------------------------
			Values:
			eg: 1234
			-----------------------------"
	::= { omtp12PlusPerformanceEntry 130 }

        omtp12PlusLan10gMacTerminatedUnderSizeFramesTransmitted OBJECT-TYPE
		SYNTAX  DisplayString
		MAX-ACCESS  read-only
		STATUS  current
		DESCRIPTION
			"For port configured with 10G LAN traffic, 
			LAN 10G Undersize Frames Transmitted counter counts the
			transmitted Ethernet framesize which is less than
			64 bytes from port which is configured with 10G LAN traffic
			-----------------------------
			omtp12PlusInterfaceNumber:
			1 - CLIENT-1
			-----------------------------
			Values:
			eg: 1234
			-----------------------------"
	::= { omtp12PlusPerformanceEntry 131 }

        omtp12PlusLan10gMacTerminatedUnderSizeFramesReceived OBJECT-TYPE
		SYNTAX  DisplayString
		MAX-ACCESS  read-only
		STATUS  current
		DESCRIPTION
			"For port configured with 10G LAN traffic, 
			LAN 10G Undersize Frames Received counter counts the
			Received Ethernet framesize which is less than
			64 bytes at port which is configured with 10G LAN traffic
			-----------------------------
			omtp12PlusInterfaceNumber:
			1 - CLIENT-1
			-----------------------------
			Values:
			eg: 1234
			-----------------------------"
	::= { omtp12PlusPerformanceEntry 132 }

        omtp12PlusLan10gMacTerminatedOverSizeFramesTransmitted OBJECT-TYPE
		SYNTAX  DisplayString
		MAX-ACCESS  read-only
		STATUS  current
		DESCRIPTION
			"For port configured with 10G LAN traffic, 
			LAN 10G Oversize Frames Transmitted counter counts the
			Transmitted  Ethernet framesize which is greater than 
			1518 bytes from port which is configured with 10G LAN
			traffic
			-----------------------------
			omtp12PlusInterfaceNumber:
			1 - CLIENT-1
			-----------------------------
			Values:
			eg: 1234
			-----------------------------"
        ::= { omtp12PlusPerformanceEntry 133 }

        omtp12PlusLan10gMacTerminatedOverSizeFramesReceived OBJECT-TYPE
		SYNTAX  DisplayString
		MAX-ACCESS  read-only
		STATUS  current
		DESCRIPTION
			"For port configured with 10G LAN traffic, 
			LAN 10G Oversize Frames Received counter counts the
			Received Ethernet framesize which is greater than 
			1518 bytes at port which is configured with 10G LAN 
			traffic
			-----------------------------
			omtp12PlusInterfaceNumber:
			1 - CLIENT-1
			-----------------------------
			Values:
			eg: 1234
			-----------------------------"
        ::= { omtp12PlusPerformanceEntry 134 }

        omtp12PlusLan10gMacTerminatedVlanTaggedFramesTransmitted OBJECT-TYPE
		SYNTAX  DisplayString
		MAX-ACCESS  read-only
		STATUS  current
		DESCRIPTION
			"For port configured with 10G LAN traffic, 
			Counts the Transmitted VLAN Tagged Frames
			at port which is configured with 10G LAN 
			traffic
			-----------------------------
			omtp12PlusInterfaceNumber:
			1 - CLIENT-1
			-----------------------------
			Values:
			eg: 1234
			-----------------------------"
	::= { omtp12PlusPerformanceEntry 135 }

        omtp12PlusLan10gMacTerminatedVlanTaggedFramesReceived OBJECT-TYPE
		SYNTAX  DisplayString
		MAX-ACCESS  read-only
		STATUS  current
		DESCRIPTION
			"For port configured with 10G LAN traffic, 
			Counts the Received VLAN Tagged Frames
			at port which is configured with 10G LAN 
			traffic
			-----------------------------
			omtp12PlusInterfaceNumber:
			1 - CLIENT-1
			-----------------------------
			Values:
			eg: 1234
			-----------------------------"
	::= { omtp12PlusPerformanceEntry 136 }

        omtp12PlusLan10gMacTerminatedFrameSymbolErrorsReceived OBJECT-TYPE
		SYNTAX  DisplayString
		MAX-ACCESS  read-only
		STATUS  current
		DESCRIPTION
			"For port configured with 10G LAN traffic, 
			Counts the Frame Symbol Error Received
			at port which is configured with 10G LAN 
			traffic
			-----------------------------
			omtp12PlusInterfaceNumber:
			1 - CLIENT-1
			-----------------------------
			Values:
			eg: 1234
			-----------------------------"
	::= { omtp12PlusPerformanceEntry 137 }

        omtp12PlusLan10gMacTerminatedFragmentFramesReceived OBJECT-TYPE
		SYNTAX  DisplayString
		MAX-ACCESS  read-only
		STATUS  current
		DESCRIPTION
			"Counts the Fragment Frames Received
			at port which is configured with 10G LAN 
			traffic
			-----------------------------
			omtp12PlusInterfaceNumber:
			1 - CLIENT-1
			-----------------------------
			Values:
			eg: 1234
			-----------------------------"
	::= { omtp12PlusPerformanceEntry 138 }

        omtp12PlusLan10gMacTerminatedFrameCheckSequenceErrorsReceived OBJECT-TYPE
		SYNTAX  DisplayString
		MAX-ACCESS  read-only
		STATUS  current
		DESCRIPTION
			"For port configured with 10G LAN traffic, 
			Gives Mac Terminated Frame Check Sequence Errors Received
			at port which is configured with 10G LAN 
			traffic
			-----------------------------
			omtp12PlusInterfaceNumber:
			1 - CLIENT-1
			-----------------------------
			Values:
			eg: 1234
			-----------------------------"
	::= { omtp12PlusPerformanceEntry 139 }

	omtp12PlusLan10gMacTerminatedFramesReceivedWithNoDefect OBJECT-TYPE
		SYNTAX  DisplayString
		MAX-ACCESS  read-only
		STATUS  current
		DESCRIPTION
			"For port configured with 10G LAN traffic, 
			Gives count of number of Mac Terminated frames
			received with no defects such as undersized frames, FCS
			errors etc, for port confgiured with 10G LAN traffic 
			-----------------------------
			omtp12PlusInterfaceNumber:
			1 - CLIENT-1
			-----------------------------
			Values:
			eg: 1234
			-----------------------------"
	::= { omtp12PlusPerformanceEntry 140 }
	
	omtp12PlusLan10gMacTerminatedBytesTransmitted OBJECT-TYPE
		SYNTAX  DisplayString
		MAX-ACCESS  read-only
		STATUS  current
		DESCRIPTION
			"For port configured with 10G LAN traffic, 
			10G Bytes transmitted counter counts the number of 
			Ethernet bytes transmitted from the Client port 
			which is configured with 10G LAN traffic
			-----------------------------
			omtp12PlusInterfaceNumber:
			1 - CLIENT-1
			-----------------------------
			Values:
			eg: 1234
			-----------------------------"
	::= { omtp12PlusPerformanceEntry 141 }

	omtp12PlusLan10gMacTerminatedBytesReceived OBJECT-TYPE
		SYNTAX  DisplayString
		MAX-ACCESS  read-only
		STATUS  current
		DESCRIPTION
			"For port configured with 10G LAN traffic, 
			10G Bytes Received counter counts the number of 
			Ethernet bytes received at the Client port 
			which is configured with 10G LAN traffic
			-----------------------------
			omtp12PlusInterfaceNumber:
			1 - CLIENT-1
			-----------------------------
			Values:
			eg: 1234
			-----------------------------"
	::= { omtp12PlusPerformanceEntry 142 }

	omtp12PlusLan10gMacTerminatedControlFramesTransmitted OBJECT-TYPE
		SYNTAX  DisplayString
		MAX-ACCESS  read-only
		STATUS  current
		DESCRIPTION
			"For port configured with GE-GFP-F/FE-GFP-F traffic,
			gives the count of the Ethernet control frames
			transmitted.
			-----------------------------
			omtp12PlusInterfaceNumber:
			1 - CLIENT-1
			-----------------------------
			Values:
			eg: 1234
			-----------------------------"
	::= { omtp12PlusPerformanceEntry 143 }

	omtp12PlusLan10gMacTerminatedControlFramesReceived OBJECT-TYPE
		SYNTAX  DisplayString
		MAX-ACCESS  read-only
		STATUS  current
		DESCRIPTION
			"For port configured with GE-GFP-F/FE-GFP-F traffic,
			gives the count of the Ethernet control frames
			received.
			-----------------------------
			omtp12PlusInterfaceNumber:
			1 - CLIENT-1
			-----------------------------
			Values:
			eg: 1234
			-----------------------------"
	::= { omtp12PlusPerformanceEntry 144 }

        omtp12PlusLan10gTransparentTransmitLcvCount OBJECT-TYPE
		SYNTAX  DisplayString
		MAX-ACCESS  read-only
		STATUS  current
		DESCRIPTION
			"For port configured with 10G LAN traffic, 
			Gives Lan10g Transparent Transmit Lcv Count
			at port which is configured with 10G LAN 
			traffic
			-----------------------------
			omtp12PlusInterfaceNumber:
			1 - CLIENT-1
			-----------------------------
			Values:
			eg: 1234
			-----------------------------"
	::= { omtp12PlusPerformanceEntry 151 }

        omtp12PlusLan10gTransparentTransmitPropagationErrorDeletionCount OBJECT-TYPE
		SYNTAX  DisplayString
		MAX-ACCESS  read-only
		STATUS  current
		DESCRIPTION
			"For port configured with 10G LAN traffic, 
			Gives Lan10g Transparent Transmit Propagation Error Deletion Count
			at port which is configured with 10G LAN 
			traffic
			-----------------------------
			omtp12PlusInterfaceNumber:
			1 - CLIENT-1
			-----------------------------
			Values:
			eg: 1234
			-----------------------------"
        ::= { omtp12PlusPerformanceEntry 152 }

        omtp12PlusLan10gTransparentTransmitIdleDeletionCount OBJECT-TYPE
		SYNTAX  DisplayString
		MAX-ACCESS  read-only
		STATUS  current
		DESCRIPTION
			"For port configured with 10G LAN traffic, 
			Gives Lan10g Transparent Transmit Idle Deletion Count
			at port which is configured with 10G LAN 
			traffic
			-----------------------------
			omtp12PlusInterfaceNumber:
			1 - CLIENT-1
			-----------------------------
			Values:
			eg: 1234
			-----------------------------"
	::= { omtp12PlusPerformanceEntry 153 }

        omtp12PlusLan10gTransparentTransmitConfDeletionCount OBJECT-TYPE
		SYNTAX  DisplayString
		MAX-ACCESS  read-only
		STATUS  current
		DESCRIPTION
			"For port configured with 10G LAN traffic, 
			Gives Lan10g Transparent Transmit Conf Deletion Count
			at port which is configured with 10G LAN 
			traffic
			-----------------------------
			omtp12PlusInterfaceNumber:
			1 - CLIENT-1
			-----------------------------
			Values:
			eg: 1234
			-----------------------------"
        ::= { omtp12PlusPerformanceEntry 154 }

        omtp12PlusLan10gTransparentTransmitPropagationInsertionCount OBJECT-TYPE
		SYNTAX  DisplayString
		MAX-ACCESS  read-only
		STATUS  current
		DESCRIPTION
			"For port configured with 10G LAN traffic, 
			Gives Lan10g Transparent Transmit Propagation Insertion Count
			at port which is configured with 10G LAN 
			traffic
			-----------------------------
			omtp12PlusInterfaceNumber:
			1 - CLIENT-1
			-----------------------------
			Values:
			eg: 1234
			-----------------------------"
	::= { omtp12PlusPerformanceEntry 155 }

        omtp12PlusLan10gTransparentTransmitIdleInsertionCount OBJECT-TYPE
		SYNTAX  DisplayString
		MAX-ACCESS  read-only
		STATUS  current
		DESCRIPTION
			"For port configured with 10G LAN traffic, 
			Gives Lan10g Transparent Transmit Idle Insertion Count
			at port which is configured with 10G LAN 
			traffic
			-----------------------------
			omtp12PlusInterfaceNumber:
			1 - CLIENT-1
			-----------------------------
			Values:
			eg: 1234
			-----------------------------"
	::= { omtp12PlusPerformanceEntry 156 }

        omtp12PlusLan10gTransparentTransmitConfInsertionCount OBJECT-TYPE
		SYNTAX  DisplayString
		MAX-ACCESS  read-only
		STATUS  current
		DESCRIPTION
			"For port configured with 10G LAN traffic, 
			Gives Lan10g Transparent Transmit Conf Insertion Count
			at port which is configured with 10G LAN 
			traffic
			-----------------------------
			omtp12PlusInterfaceNumber:
			1 - CLIENT-1
			-----------------------------
			Values:
			eg: 1234
			-----------------------------"
	::= { omtp12PlusPerformanceEntry 157 }

        omtp12PlusLan10gTransparentReceiveLcvCount OBJECT-TYPE
		SYNTAX  DisplayString
		MAX-ACCESS  read-only
		STATUS  current
		DESCRIPTION
			"For port configured with 10G LAN traffic, 
			Gives Lan10g Transparent Receive Lcv Count
			at port which is configured with 10G LAN 
			traffic
			-----------------------------
			omtp12PlusInterfaceNumber:
			1 - CLIENT-1
			-----------------------------
			Values:
			eg: 1234
			-----------------------------"
	::= { omtp12PlusPerformanceEntry 158 }

        omtp12PlusLan10gTransparentReceivePropagationErrorDeletionCount OBJECT-TYPE
		SYNTAX  DisplayString
		MAX-ACCESS  read-only
		STATUS  current
		DESCRIPTION
			"For port configured with 10G LAN traffic, 
			Gives Lan10g Transparent Receive Propagation Error
			Deletion Count at port which is configured with 10G LAN 
			traffic
			-----------------------------
			omtp12PlusInterfaceNumber:
			1 - CLIENT-1
			-----------------------------
			Values:
			eg: 1234
			-----------------------------"
	::= { omtp12PlusPerformanceEntry 159 }

        omtp12PlusLan10gTransparentReceiveIdleDeletionCount OBJECT-TYPE
		SYNTAX  DisplayString
		MAX-ACCESS  read-only
		STATUS  current
		DESCRIPTION
			"For port configured with 10G LAN traffic, 
			Gives Lan10g Transparent Receive Idle Deletion Count
			at port which is configured with 10G LAN 
			traffic
			-----------------------------
			omtp12PlusInterfaceNumber:
			1 - CLIENT-1
			-----------------------------
			Values:
			eg: 1234
			-----------------------------"
	::= { omtp12PlusPerformanceEntry 160 }

        omtp12PlusLan10gTransparentReceiveConfDeletionCount OBJECT-TYPE
		SYNTAX  DisplayString
		MAX-ACCESS  read-only
		STATUS  current
		DESCRIPTION
			"For port configured with 10G LAN traffic, 
			Gives Lan10g Transparent Receive Conf Deletion Count
			at port which is configured with 10G LAN 
			traffic
			-----------------------------
			omtp12PlusInterfaceNumber:
			1 - CLIENT-1
			-----------------------------
			Values:
			eg: 1234
			-----------------------------" 
	::= { omtp12PlusPerformanceEntry 161 }

        omtp12PlusLan10gTransparentReceivePacketDeletionCount OBJECT-TYPE
		SYNTAX  DisplayString
		MAX-ACCESS  read-only
		STATUS  current
		DESCRIPTION
			"For port configured with 10G LAN traffic, 
			Gives Lan10g Transparent Receive Packet Deletion Count
			at port which is configured with 10G LAN 
			traffic
			-----------------------------
			omtp12PlusInterfaceNumber:
			1 - CLIENT-1
			-----------------------------
			Values:
			eg: 1234
			-----------------------------"
	::= { omtp12PlusPerformanceEntry 162 }

        omtp12PlusGfpCoreHeaderErrorCount OBJECT-TYPE
		SYNTAX  DisplayString
		MAX-ACCESS  read-only
		STATUS  current
		DESCRIPTION
			"Get GFP Core Header Error Count at port which is
			configured with 10G LAN traffic
			-----------------------------
			omtp12PlusInterfaceNumber:
			1 - CLIENT-1
			-----------------------------
			Values:
			eg: 1234
			-----------------------------"
	::= { omtp12PlusPerformanceEntry 171 }

        omtp12PlusGfpExtentionHeaderErrorCount OBJECT-TYPE
		SYNTAX  DisplayString
		MAX-ACCESS  read-only
		STATUS  current
		DESCRIPTION
			"Get GFP Extention Header Error Count at port which is
			configured with 10G LAN traffic
			-----------------------------
			omtp12PlusInterfaceNumber:
			1 - CLIENT-1
			-----------------------------
			Values:
			eg: 1234
			-----------------------------"
	::= { omtp12PlusPerformanceEntry 172 }

	omtp12PlusGfpFrameCountWithSingleBitError OBJECT-TYPE
		SYNTAX  DisplayString
		MAX-ACCESS  read-only
		STATUS  current
		DESCRIPTION
			"For port configured with
			GE-GFP-F/FE-GFP-F/GE-GFP-T/FE-GFP-T traffic,
			gives the count of GFP Frames that are received 
			with single bit error.
			-----------------------------
			omtp12PlusInterfaceNumber:
			1 - CLIENT-1
			-----------------------------
			Values:
			eg: 1234
			-----------------------------"
	::= { omtp12PlusPerformanceEntry 173 }

	omtp12PlusGfpTypeHeaderErrorCount OBJECT-TYPE
		SYNTAX  DisplayString
		MAX-ACCESS  read-only
		STATUS  current
		DESCRIPTION
			"For port configured with
			GE-GFP-F/FE-GFP-F/GE-GFP-T/FE-GFP-T traffic,
			gives the count of received GFP frames which have error
			in the type header.
			-----------------------------
			omtp12PlusInterfaceNumber:
			1 - CLIENT-1
			-----------------------------
			Values:
			eg: 1234
			-----------------------------"
	::= { omtp12PlusPerformanceEntry 174 }

	omtp12PlusGfpReceiveDropFrameCount OBJECT-TYPE
		SYNTAX  DisplayString
		MAX-ACCESS  read-only
		STATUS  current
		DESCRIPTION
			"For port configured with
			GE-GFP-F/FE-GFP-F/GE-GFP-T/FE-GFP-T traffic,
			gives the Drop Frame count of received GFP frames.
			-----------------------------
			omtp12PlusInterfaceNumber:
			1 - CLIENT-1
			-----------------------------
			Values:
			eg: 1234
			-----------------------------"
	::= { omtp12PlusPerformanceEntry 175 }

	omtp12PlusGfpReceiveExtensionHeaderIdentifierFilterDropCount OBJECT-TYPE
		SYNTAX  DisplayString
		MAX-ACCESS  read-only
		STATUS  current
		DESCRIPTION
			"For port configured with
			GE-GFP-F/FE-GFP-F/GE-GFP-T/FE-GFP-T traffic,
			gives the Extension Header Identifier Filter
			Drop count of received GFP frames.
			-----------------------------
			omtp12PlusInterfaceNumber:
			1 - CLIENT-1
			-----------------------------
			Values:
			eg: 1234
			-----------------------------"
	::= { omtp12PlusPerformanceEntry 176 }

        omtp12PlusFcTransmitWordCount OBJECT-TYPE
		SYNTAX  DisplayString
		MAX-ACCESS  read-only
		STATUS  current
		DESCRIPTION
			"For port configured with FC 800/1200 traffic, 
			Get the FC Transmit Word Count at port which
			is configured with FC traffic
			-----------------------------
			omtp12PlusInterfaceNumber:
			1 - CLIENT-1
			-----------------------------
			Values:
			eg: 1234
			-----------------------------"
        ::= { omtp12PlusPerformanceEntry 181 }

        omtp12PlusFcTransmitBadCrc OBJECT-TYPE
		SYNTAX  DisplayString
		MAX-ACCESS  read-only
		STATUS  current
		DESCRIPTION
			"For port configured with FC 800/1200 traffic, 
			Get the FC Transmit Bad Crc count at port which
			is configured with FC traffic
			-----------------------------
			omtp12PlusInterfaceNumber:
			1 - CLIENT-1
			-----------------------------
			Values:
			eg: 1234
			-----------------------------"
        ::= { omtp12PlusPerformanceEntry 182 }

        omtp12PlusFcTransmitTotalPackets OBJECT-TYPE
		SYNTAX  DisplayString
		MAX-ACCESS  read-only
		STATUS  current
		DESCRIPTION
			"For port configured with FC 800/1200 traffic, 
			Get the FC Transmit Total packet Count at port which
			is configured with FC traffic
			-----------------------------
			omtp12PlusInterfaceNumber:
			1 - CLIENT-1
			-----------------------------
			Values:
			eg: 1234
			-----------------------------"
	::= { omtp12PlusPerformanceEntry 183 }

        omtp12PlusFcTransmitLcvCount OBJECT-TYPE
		SYNTAX  DisplayString
		MAX-ACCESS  read-only
		STATUS  current
		DESCRIPTION
			"For port configured with FC 800/1200 traffic, 
			Get the FC Transmit Lcv Count at port which
			is configured with FC traffic
			-----------------------------
			omtp12PlusInterfaceNumber:
			1 - CLIENT-1
			-----------------------------
			Values:
			eg: 1234
			-----------------------------"
	::= { omtp12PlusPerformanceEntry 184 }

        omtp12PlusFcReceiveWordCount OBJECT-TYPE
		SYNTAX  DisplayString
		MAX-ACCESS  read-only
		STATUS  current
		DESCRIPTION
			"For port configured with FC 800/1200 traffic, 
			Get the FC Receive Word Count at port which
			is configured with FC traffic
			-----------------------------
			omtp12PlusInterfaceNumber:
			1 - CLIENT-1
			-----------------------------
			Values:
			eg: 1234
			-----------------------------"
	::= { omtp12PlusPerformanceEntry 185 }

        omtp12PlusFcReceiveBadCrc OBJECT-TYPE
		SYNTAX  DisplayString
		MAX-ACCESS  read-only
		STATUS  current
		DESCRIPTION
			"For port configured with FC 800/1200 traffic, 
			Get the FC Receive Bad CRC at port which
			is configured with FC traffic
			-----------------------------
			omtp12PlusInterfaceNumber:
			1 - CLIENT-1
			-----------------------------
			Values:
			eg: 1234
			-----------------------------"
        ::= { omtp12PlusPerformanceEntry 186 }

        omtp12PlusFcReceiveTotalPackets OBJECT-TYPE
		SYNTAX  DisplayString
		MAX-ACCESS  read-only
		STATUS  current
		DESCRIPTION
			"For port configured with FC 800/1200 traffic, 
			Get the FC Receive total packet Count at port which
			is configured with FC traffic
			-----------------------------
			omtp12PlusInterfaceNumber:
			1 - CLIENT-1
			-----------------------------
			Values:
			eg: 1234
			-----------------------------"
	::= { omtp12PlusPerformanceEntry 187 }

        omtp12PlusFcReceiveLcvCount OBJECT-TYPE
		SYNTAX  DisplayString
		MAX-ACCESS  read-only
		STATUS  current
		DESCRIPTION
			"For port configured with FC 800/1200 traffic, 
			Get the FC Receive Lcv Count at port which
			is configured with FC traffic
			-----------------------------
			omtp12PlusInterfaceNumber:
			1 - CLIENT-1
			-----------------------------
			Values:
			eg: 1234
			-----------------------------"
	::= { omtp12PlusPerformanceEntry 188 }

        omtp12PlusFcTransmitFillWordInsertionCount OBJECT-TYPE
		SYNTAX  DisplayString
		MAX-ACCESS  read-only
		STATUS  current
		DESCRIPTION
			"For port configured with FC 800/1200 traffic, 
			Get the FC FW Insertion Count at port which
			is configured with FC traffic
			-----------------------------
			omtp12PlusInterfaceNumber:
			1 - CLIENT-1
			-----------------------------
			Values:
			eg: 1234
			-----------------------------"
	::= { omtp12PlusPerformanceEntry 189 }

        omtp12PlusFcTransmitPrimitiveSequenceInsertionCount OBJECT-TYPE
		SYNTAX  DisplayString
		MAX-ACCESS  read-only
		STATUS  current
		DESCRIPTION
			"For port configured with FC 800/1200 traffic, 
			Get the FC Primitive Sequence Insertion Count at port
			which is configured with FC traffic
			-----------------------------
			omtp12PlusInterfaceNumber:
			1 - CLIENT-1
			-----------------------------
			Values:
			eg: 1234
			-----------------------------"
	::= { omtp12PlusPerformanceEntry 190 }

        omtp12PlusFcTransmitFillWordDeletionCount OBJECT-TYPE
		SYNTAX  DisplayString
		MAX-ACCESS  read-only
		STATUS  current
		DESCRIPTION
			"For port configured with FC 800/1200 traffic, 
			Get the FC FW Deletion Count at port which
			is configured with FC traffic
			-----------------------------
			omtp12PlusInterfaceNumber:
			1 - CLIENT-1
			-----------------------------
			Values:
			eg: 1234
			-----------------------------"
	::= { omtp12PlusPerformanceEntry 191 }

        omtp12PlusFcTransmitPrimitiveSequenceDeletionCount OBJECT-TYPE
		SYNTAX  DisplayString
		MAX-ACCESS  read-only
		STATUS  current
		DESCRIPTION
			"For port configured with FC 800/1200 traffic, 
			Get the FC Primitive Sequence Deletion Count at port
			which is configured with FC traffic
			-----------------------------
			omtp12PlusInterfaceNumber:
			1 - CLIENT-1
			-----------------------------
			Values:
			eg: 1234
			-----------------------------"
	::= { omtp12PlusPerformanceEntry 192 }

	omtp12PlusPerformanceTableRowStatus OBJECT-TYPE
              SYNTAX      RowStatus
              MAX-ACCESS  read-write
              STATUS      current
              DESCRIPTION
                      "	This is MIB realted property,
			NOT to be considered as a card property"
              ::= { omtp12PlusPerformanceEntry 193 }


--*****************************************************************************
--				    DIAGNOSTICS
--*****************************************************************************        

	omtp12PlusDiagnosticsTable OBJECT-TYPE
	      SYNTAX  SEQUENCE OF Omtp12PlusDiagnosticsEntry
              MAX-ACCESS  not-accessible
              STATUS  current
              DESCRIPTION
                      "Category contains properties that are used for debugging
                      card software"
		::= { omtp12PlusDiagnostics 1 }	

	omtp12PlusDiagnosticsEntry   OBJECT-TYPE
              SYNTAX  Omtp12PlusDiagnosticsEntry 
              MAX-ACCESS  not-accessible
              STATUS  current
              DESCRIPTION 
              	""
		INDEX   { node, rack , subRack , slot , omtp12PlusInterfaceNumber }
		::= { omtp12PlusDiagnosticsTable 1 }
	
	Omtp12PlusDiagnosticsEntry ::= 
		SEQUENCE {
				omtp12PlusAccessCortinaRegister			INTEGER,
				omtp12PlusCollectCortinaRegisterDump			INTEGER,
				omtp12PlusCollectCortinaModulebGpllRxLockStatus		DisplayString,
				omtp12PlusCollectCortinaModulebGpllTxLockStatus		DisplayString,
				omtp12PlusCollectCortinaModulebTxSerdesLockStatus	DisplayString,
				omtp12PlusCollectCortinaModulebTxSerdesVcoTunedValue	DisplayString,
				omtp12PlusCollectCortinaModulebXfiCupllLockStatus	DisplayString,
				omtp12PlusCollectCortinaModulebAllClockLockStatus	OCTET STRING,
				omtp12PlusDiagnosticTableRowStatus			RowStatus
			}
			
	omtp12PlusAccessCortinaRegister OBJECT-TYPE
		SYNTAX  INTEGER
		MAX-ACCESS  read-write
		STATUS  current
		DESCRIPTION
			"Sets/gets the value of any cortina register
			-----------------------------
			omtp12PlusInterfaceNumber: 0
			-----------------------------
			Values:
			eg:
			example of cortina register - 76071076
			value - 1
			-----------------------------"
	::= { omtp12PlusDiagnosticsEntry 1 }	
	
	omtp12PlusCollectCortinaRegisterDump OBJECT-TYPE
		SYNTAX  INTEGER
		MAX-ACCESS  read-only
		STATUS  current
		DESCRIPTION
			"create register dump of all cortina register
			-----------------------------
			omtp12PlusInterfaceNumber: 0
			-----------------------------
                     	This query will create registe dump in card's 
			root directory
			-----------------------------"
	::= { omtp12PlusDiagnosticsEntry 2 }	

	omtp12PlusCollectCortinaModulebGpllRxLockStatus OBJECT-TYPE
		SYNTAX  DisplayString
		MAX-ACCESS  read-only
		STATUS  current
		DESCRIPTION
			"reads GPLL Rx clock lock status for all slices
			 of module B
			 Expected value : should be 0x00049 to indicate 
			 Value is locked
			 The following register will be read:
			 0x00c59, 0x00c99, 0x00cd9, 0x00d19
			 The register that will be read is GPLLX1_SDS_COMMON_TXLOCKD0_INTSTATUS
			-----------------------------
			omtp12PlusInterfaceNumber: 0
			-----------------------------"
	::= { omtp12PlusDiagnosticsEntry 3 }	
	
	omtp12PlusCollectCortinaModulebGpllTxLockStatus OBJECT-TYPE
		SYNTAX  DisplayString
		MAX-ACCESS  read-only
		STATUS  current
		DESCRIPTION
			"reads GPLL Tx clock lock status for all slices
			 of module B
			 Expected value : should be 0x00049 to indicate 
			 Value is locked
			 The following register will be read:
			 0x00d59, 0x00d99, 0x00dd9, 0x00e19
			 The register that will be read is GPLLX1_SDS_COMMON_TXLOCKD0_INTSTATUS
			-----------------------------
			omtp12PlusInterfaceNumber: 0
			-----------------------------"
	::= { omtp12PlusDiagnosticsEntry 4 }

	omtp12PlusCollectCortinaModulebTxSerdesLockStatus OBJECT-TYPE
		SYNTAX  DisplayString
		MAX-ACCESS  read-only
		STATUS  current
		DESCRIPTION
			"reads Tx serdes clock lock status for all slices
			 of module B
			 Expected value : should be 0x00049 to indicate 
			 Value is locked
			 The following register will be read:
			 0x0303d, 0x0343d, 0x0383d, 0x03c3d
			 The register that will be read is 
			 XFI32X1_SDS_XFI32X1_SDS_COMMON_TXLOCKD0_INTSTATUS
			-----------------------------
			omtp12PlusInterfaceNumber: 0
			-----------------------------"
	::= { omtp12PlusDiagnosticsEntry 5 }	
	
	omtp12PlusCollectCortinaModulebTxSerdesVcoTunedValue OBJECT-TYPE
		SYNTAX  DisplayString
		MAX-ACCESS  read-only
		STATUS  current
		DESCRIPTION
			"reads Tx serdes VCO tuning value for all slices
			 of module B
			 Expected value : Value when correctly tuned should not 
			 be near extremes of 0x3F or 0x00
			 The following register will be read:
			 0x03031, 0x03431, 0x03831, 0x03c31
			 The register that will be read is XFI32X1_SDS_XFI32X1_SDS_COMMON_TXVCO0_STATUS
			-----------------------------
			omtp12PlusInterfaceNumber: 0
			-----------------------------"
	::= { omtp12PlusDiagnosticsEntry 6 }	

	omtp12PlusCollectCortinaModulebXfiCupllLockStatus OBJECT-TYPE
		SYNTAX  DisplayString
		MAX-ACCESS  read-only
		STATUS  current
		DESCRIPTION
			"reads XFI CUPLL Lock status for all slices
			 of module B
			 Expected value : should be 0x00049 to indicate Value is locked 
			 The following register will be read:
			 0x1b438, 0x1b478, 0x1b4b8, 0x1b4f8
			 The register that will be read is XFI_CUPLL_LOCKDET_INTSTATUS
			-----------------------------
			omtp12PlusInterfaceNumber: 0
			-----------------------------"
	::= { omtp12PlusDiagnosticsEntry 7 }	

	omtp12PlusCollectCortinaModulebAllClockLockStatus OBJECT-TYPE
		SYNTAX  OCTET STRING
		MAX-ACCESS  read-only
		STATUS  current
		DESCRIPTION
			"reads Lock status of following clocks:
			 GPLL Rx/Tx, Tx serdes, Tx Serdes VCO tuned value and XFI CUPLLfor all slices
			 of module B.
			 Expected value : should be 0x00049 to indicate Value is locked 
			 The following register will be read:
			 0x1b438, 0x1b478, 0x1b4b8, 0x1b4f8
			 The register that will be read is XFI_CUPLL_LOCKDET_INTSTATUS
			-----------------------------
			omtp12PlusInterfaceNumber: 0
			-----------------------------"
	::= { omtp12PlusDiagnosticsEntry 8 }	

	omtp12PlusDiagnosticTableRowStatus OBJECT-TYPE
              SYNTAX      RowStatus
              MAX-ACCESS  read-write
              STATUS      current
              DESCRIPTION
			"*****************************
			This is MIB realted property,
			NOT to be considered as a card property
			*****************************"
	::= { omtp12PlusDiagnosticsEntry 9 }
        
--*****************************************************************************
--				    ALARM Notification Table
--*****************************************************************************

        omtp12PlusXfpInputPowerFailureAlarmTrap NOTIFICATION-TYPE
         OBJECTS { omtp12PlusXfpInputPowerFailureAlarm }
                STATUS  current
                DESCRIPTION
                        "OMTP12-PLUS XFP input power failure alarm trap"
        ::= { omtp12PlusAlarmNotification 1 }


        omtp12PlusXfpOutputPowerFailureAlarmTrap NOTIFICATION-TYPE
         OBJECTS { omtp12PlusXfpOutputPowerFailureAlarm }
               STATUS  current
               DESCRIPTION
                        "OMTP12-PLUS XFP output power failure alarm trap"
        ::= { omtp12PlusAlarmNotification 2 }


        omtp12PlusXfpHighTemperatureAlarmTrap NOTIFICATION-TYPE
         OBJECTS { omtp12PlusXfpHighTemperatureAlarm }
               STATUS  current
               DESCRIPTION
                        "OMTP12-PLUS XFP high temperature alarm trap"
        ::= { omtp12PlusAlarmNotification 3 }

        omtp12PlusXfpLowTemperatureAlarmTrap NOTIFICATION-TYPE
         OBJECTS { omtp12PlusXfpLowTemperatureAlarm }
               STATUS  current
               DESCRIPTION
                        "OMTP12-PLUS XFP low temperature alarm trap"
        ::= { omtp12PlusAlarmNotification 4 }

        omtp12PlusXfpHighTemperatureWarningTrap NOTIFICATION-TYPE
         OBJECTS { omtp12PlusXfpHighTemperatureWarning }
               STATUS  current
               DESCRIPTION
                        "OMTP12-PLUS XFP high temperature warning trap"
        ::= { omtp12PlusAlarmNotification 5 }

        omtp12PlusXfpLowTemperatureWarningTrap NOTIFICATION-TYPE
         OBJECTS { omtp12PlusXfpLowTemperatureWarning }
               STATUS  current
               DESCRIPTION
                        "OMTP12-PLUS XFP low temperature warning trap"
        ::= { omtp12PlusAlarmNotification 6 }

        omtp12PlusXfpHighBiasCurrentAlarmTrap NOTIFICATION-TYPE
         OBJECTS { omtp12PlusXfpHighBiasCurrentAlarm }
               STATUS  current
               DESCRIPTION
                        "OMTP12-PLUS XFP high bias current alarm trap"
        ::= { omtp12PlusAlarmNotification 7 }

        omtp12PlusXfpLowBiasCurrentAlarmTrap NOTIFICATION-TYPE
         OBJECTS { omtp12PlusXfpLowBiasCurrentAlarm }
               STATUS  current
               DESCRIPTION
                        "OMTP12-PLUS XFP low bias current alarm trap"
        ::= { omtp12PlusAlarmNotification 8 }

        omtp12PlusXfpHighBiasCurrentWarningTrap NOTIFICATION-TYPE
         OBJECTS { omtp12PlusXfpHighBiasCurrentWarning }
               STATUS  current
               DESCRIPTION
                        "OMTP12-PLUS XFP high bias current warning trap"
        ::= { omtp12PlusAlarmNotification 9 }

        omtp12PlusXfpLowBiasCurrentWarningTrap NOTIFICATION-TYPE
         OBJECTS { omtp12PlusXfpLowBiasCurrentWarning }
               STATUS  current
               DESCRIPTION
                        "OMTP12-PLUS XFP low bias current warning trap"
        ::= { omtp12PlusAlarmNotification 10 }

        omtp12PlusXfpInputHighPowerAlarmTrap NOTIFICATION-TYPE
         OBJECTS { omtp12PlusXfpInputHighPowerAlarm }
               STATUS  current
               DESCRIPTION
                        "OMTP12-PLUS XFP input high power alarm trap"
        ::= { omtp12PlusAlarmNotification 11 }

        omtp12PlusXfpInputLowPowerAlarmTrap NOTIFICATION-TYPE
         OBJECTS { omtp12PlusXfpInputLowPowerAlarm }
               STATUS  current
               DESCRIPTION
                        "OMTP12-PLUS XFP input low power alarm trap"
        ::= { omtp12PlusAlarmNotification 12 }

        omtp12PlusXfpInputHighPowerWarningTrap NOTIFICATION-TYPE
         OBJECTS { omtp12PlusXfpInputHighPowerWarning }
               STATUS  current
               DESCRIPTION
                        "OMTP12-PLUS XFP input high power warning trap"
        ::= { omtp12PlusAlarmNotification 13 }

        omtp12PlusXfpInputLowPowerWarningTrap NOTIFICATION-TYPE
         OBJECTS { omtp12PlusXfpInputLowPowerWarning }
               STATUS  current
               DESCRIPTION
                        "OMTP12-PLUS XFP input low power warning trap"
        ::= { omtp12PlusAlarmNotification 14 }

        omtp12PlusXfpOutputHighPowerAlarmTrap NOTIFICATION-TYPE
         OBJECTS { omtp12PlusXfpOutputHighPowerAlarm }
               STATUS  current
               DESCRIPTION
                        "OMTP12-PLUS XFP output high power alarm trap"
        ::= { omtp12PlusAlarmNotification 15 }

        omtp12PlusXfpOutputLowPowerAlarmTrap NOTIFICATION-TYPE
         OBJECTS { omtp12PlusXfpOutputLowPowerAlarm }
               STATUS  current
               DESCRIPTION
                        "OMTP12-PLUS XFP output low power alarm trap"
        ::= { omtp12PlusAlarmNotification 16 }

        omtp12PlusXfpOutputHighPowerWarningTrap NOTIFICATION-TYPE
         OBJECTS { omtp12PlusXfpOutputHighPowerWarning }
               STATUS  current
               DESCRIPTION
                        "OMTP12-PLUS XFP output high power warning trap"
        ::= { omtp12PlusAlarmNotification 17 }

        omtp12PlusXfpOutputLowPowerWarningTrap NOTIFICATION-TYPE
         OBJECTS { omtp12PlusXfpOutputLowPowerWarning }
               STATUS  current
               DESCRIPTION
                        "OMTP12-PLUS XFP output low power warning trap"
        ::= { omtp12PlusAlarmNotification 18 }

        omtp12PlusXfpHighSupplyVoltageAlarmTrap NOTIFICATION-TYPE
         OBJECTS { omtp12PlusXfpHighSupplyVoltageAlarm }
               STATUS  current
               DESCRIPTION
                        "OMTP12-PLUS XFP high supply voltage alarm trap"
        ::= { omtp12PlusAlarmNotification 19 }

        omtp12PlusXfpLowSupplyVoltageAlarmTrap NOTIFICATION-TYPE
         OBJECTS { omtp12PlusXfpLowSupplyVoltageAlarm }
               STATUS  current
               DESCRIPTION
                        "OMTP12-PLUS XFP low supply voltage alarm trap"
        ::= { omtp12PlusAlarmNotification 20 }

        omtp12PlusXfpHighSupplyVoltageWarningTrap NOTIFICATION-TYPE
         OBJECTS { omtp12PlusXfpHighSupplyVoltageWarning }
               STATUS  current
               DESCRIPTION
                        "OMTP12-PLUS XFP high supply voltage warning trap"
        ::= { omtp12PlusAlarmNotification 21 }

        omtp12PlusXfpLowSupplyVoltageWarningTrap NOTIFICATION-TYPE
         OBJECTS { omtp12PlusXfpLowSupplyVoltageWarning }
               STATUS  current
               DESCRIPTION
                        "OMTP12-PLUS XFP low supply voltage warning trap"
        ::= { omtp12PlusAlarmNotification 22 }

        omtp12PlusXfpPresenceAbsenceNotificationTrap NOTIFICATION-TYPE
         OBJECTS { omtp12PlusXfpPresenceAbsenceNotification }
               STATUS  current
               DESCRIPTION
                        "OMTP12-PLUS XFP presence absence notification"
        ::= { omtp12PlusAlarmNotification 23 }

        omtp12PlusOtuLossOfSignalAlarmTrap NOTIFICATION-TYPE
         OBJECTS { omtp12PlusOtuLossOfSignalAlarm }
               STATUS  current
               DESCRIPTION
                        "OMTP12-PLUS OTU loss of signal alarm trap"
        ::= { omtp12PlusAlarmNotification 31 }

        omtp12PlusOtuLossOfFrameAlarmTrap NOTIFICATION-TYPE
         OBJECTS { omtp12PlusOtuLossOfFrameAlarm }
               STATUS  current
               DESCRIPTION
                        "OMTP12-PLUS OTU loss of frame alarm trap"
        ::= { omtp12PlusAlarmNotification 32 }

        omtp12PlusOtuOutOfFrameAlarmTrap NOTIFICATION-TYPE
         OBJECTS { omtp12PlusOtuOutOfFrameAlarm }
               STATUS  current
               DESCRIPTION
                        "OMTP12-PLUS OTU out of frame alarm trap"
        ::= { omtp12PlusAlarmNotification 33 }

        omtp12PlusOtuLossOfMultiFrameAlarmTrap NOTIFICATION-TYPE
         OBJECTS { omtp12PlusOtuLossOfMultiFrameAlarm }
               STATUS  current
               DESCRIPTION
                        "OMTP12-PLUS OTU loss of multi frame alarm trap"
        ::= { omtp12PlusAlarmNotification 34 }

        omtp12PlusOtuOutOfMultiFrameAlarmTrap NOTIFICATION-TYPE
         OBJECTS { omtp12PlusOtuOutOfMultiFrameAlarm }
               STATUS  current
               DESCRIPTION
                        "OMTP12-PLUS OTU out of multi frame alarm trap"
        ::= { omtp12PlusAlarmNotification 35 }

        omtp12PlusOtuSignalFailAlarmTrap NOTIFICATION-TYPE
         OBJECTS { omtp12PlusOtuSignalFailAlarm }
               STATUS  current
               DESCRIPTION
                        "OMTP12-PLUS OTU signal fail alarm trap"
        ::= { omtp12PlusAlarmNotification 36 }

        omtp12PlusOtuSignalDegradeAlarmTrap NOTIFICATION-TYPE
         OBJECTS { omtp12PlusOtuSignalDegradeAlarm }
               STATUS  current
               DESCRIPTION
                        "OMTP12-PLUS OTU signal degrade alarm trap"
        ::= { omtp12PlusAlarmNotification 37 }

        omtp12PlusOtuAlarmIndicationSignalAlarmTrap NOTIFICATION-TYPE
         OBJECTS { omtp12PlusOtuAlarmIndicationSignalAlarm }
               STATUS  current
               DESCRIPTION
                        "OMTP12-PLUS OTU alarm indication signal alarm trap"
        ::= { omtp12PlusAlarmNotification 38 }

        omtp12PlusOtuIncomingAlignmentErrorAlarmTrap NOTIFICATION-TYPE
         OBJECTS { omtp12PlusOtuIncomingAlignmentErrorAlarm }
               STATUS  current
               DESCRIPTION
                        "OMTP12-PLUS OTU incoming alignment error alarm trap"
        ::= { omtp12PlusAlarmNotification 39 }

        omtp12PlusOtuTraceIdentifierMismatchAlarmTrap NOTIFICATION-TYPE
         OBJECTS { omtp12PlusOtuTraceIdentifierMismatchAlarm }
               STATUS  current
               DESCRIPTION
                        "OMTP12-PLUS OTU trace identifier mismatch alarm trap"
        ::= { omtp12PlusAlarmNotification 40 }

        omtp12PlusOtuBackwardIncomingAlignmentErrorAlarmTrap NOTIFICATION-TYPE
         OBJECTS { omtp12PlusOtuBackwardIncomingAlignmentErrorAlarm }
               STATUS  current
               DESCRIPTION
                        "OMTP12-PLUS OTU backward incoming alignment error alarm trap"
        ::= { omtp12PlusAlarmNotification 41 }

        omtp12PlusOtuBackwardDefectIndicationAlarmTrap NOTIFICATION-TYPE
         OBJECTS { omtp12PlusOtuBackwardDefectIndicationAlarm }
               STATUS  current
               DESCRIPTION
                        "OMTP12-PLUS OTU backward defect indication alarm trap"
        ::= { omtp12PlusAlarmNotification 42 }

        omtp12PlusOduSignalFailAlarmTrap NOTIFICATION-TYPE
         OBJECTS { omtp12PlusOduSignalFailAlarm }
               STATUS  current
               DESCRIPTION
                        "OMTP12-PLUS ODU signal fail alarm trap"
        ::= { omtp12PlusAlarmNotification 51 }

        omtp12PlusOduSignalDegradeAlarmTrap NOTIFICATION-TYPE
         OBJECTS { omtp12PlusOduSignalDegradeAlarm }
               STATUS  current
               DESCRIPTION
                        "OMTP12-PLUS ODU signal degrade alarm trap"
        ::= { omtp12PlusAlarmNotification 52 }

        omtp12PlusOduAlarmIndicationSignalAlarmTrap NOTIFICATION-TYPE
         OBJECTS { omtp12PlusOduAlarmIndicationSignalAlarm }
               STATUS  current
               DESCRIPTION
                        "OMTP12-PLUS ODU alarm indication signal alarm trap"
        ::= { omtp12PlusAlarmNotification 53 }

        omtp12PlusOduTcm1IncomingAlignmentErrorAlarmTrap NOTIFICATION-TYPE
         OBJECTS { omtp12PlusOduTcm1IncomingAlignmentErrorAlarm }
               STATUS  current
               DESCRIPTION
                        "OMTP12-PLUS ODU TCM1 incoming alignment error alarm trap"
        ::= { omtp12PlusAlarmNotification 54 }

        omtp12PlusOduTcm2IncomingAlignmentErrorAlarmTrap NOTIFICATION-TYPE
         OBJECTS { omtp12PlusOduTcm2IncomingAlignmentErrorAlarm }
               STATUS  current
               DESCRIPTION
                        "OMTP12-PLUS ODU TCM2 incoming alignment error alarm trap"
        ::= { omtp12PlusAlarmNotification 55 }

        omtp12PlusOduTcm3IncomingAlignmentErrorAlarmTrap NOTIFICATION-TYPE
         OBJECTS { omtp12PlusOduTcm3IncomingAlignmentErrorAlarm }
               STATUS  current
               DESCRIPTION
                        "OMTP12-PLUS ODU TCM3 incoming alignment error alarm trap"
        ::= { omtp12PlusAlarmNotification 56 }

        omtp12PlusOduTcm4IncomingAlignmentErrorAlarmTrap NOTIFICATION-TYPE
         OBJECTS { omtp12PlusOduTcm4IncomingAlignmentErrorAlarm }
               STATUS  current
               DESCRIPTION
                        "OMTP12-PLUS ODU TCM4 incoming alignment error alarm trap"
        ::= { omtp12PlusAlarmNotification 57 }

        omtp12PlusOduTcm5IncomingAlignmentErrorAlarmTrap NOTIFICATION-TYPE
         OBJECTS { omtp12PlusOduTcm5IncomingAlignmentErrorAlarm }
               STATUS  current
               DESCRIPTION
                        "OMTP12-PLUS ODU TCM5 incoming alignment error alarm trap"
        ::= { omtp12PlusAlarmNotification 58 }

        omtp12PlusOduTcm6IncomingAlignmentErrorAlarmTrap NOTIFICATION-TYPE
         OBJECTS { omtp12PlusOduTcm6IncomingAlignmentErrorAlarm }
               STATUS  current
               DESCRIPTION
                        "OMTP12-PLUS ODU TCM6 incoming alignment error alarm trap"
        ::= { omtp12PlusAlarmNotification 59 }

        omtp12PlusOduTraceIdentifierMismatchAlarmTrap NOTIFICATION-TYPE
         OBJECTS { omtp12PlusOduTraceIdentifierMismatchAlarm }
               STATUS  current
               DESCRIPTION
                        "OMTP12-PLUS ODU trace identifier mismatch alarm trap"
        ::= { omtp12PlusAlarmNotification 60 }

        omtp12PlusOduLockedDefectAlarmTrap NOTIFICATION-TYPE
         OBJECTS { omtp12PlusOduLockedDefectAlarm }
               STATUS  current
               DESCRIPTION
                        "OMTP12-PLUS ODU locked defect alarm trap"
        ::= { omtp12PlusAlarmNotification 61 }

        omtp12PlusOduOpenConnectionIndicationAlarmTrap NOTIFICATION-TYPE
         OBJECTS { omtp12PlusOduOpenConnectionIndicationAlarm }
               STATUS  current
               DESCRIPTION
                        "OMTP12-PLUS ODU open connection indication alarm trap"
        ::= { omtp12PlusAlarmNotification 62 }

        omtp12PlusOduBackwardDefectIndicationAlarmTrap NOTIFICATION-TYPE
         OBJECTS { omtp12PlusOduBackwardDefectIndicationAlarm }
               STATUS  current
               DESCRIPTION
                        "OMTP12-PLUS ODU backward defect indication alarm trap"
        ::= { omtp12PlusAlarmNotification 63 }

        omtp12PlusOduTcm1BackwardIncomingAlignmentErrorAlarmTrap NOTIFICATION-TYPE
         OBJECTS { omtp12PlusOduTcm1BackwardIncomingAlignmentErrorAlarm }
               STATUS  current
               DESCRIPTION
                        "OMTP12-PLUS ODU TCM1 backward incoming alignment error alarm trap"
        ::= { omtp12PlusAlarmNotification 64 }

        omtp12PlusOduTcm2BackwardIncomingAlignmentErrorAlarmTrap NOTIFICATION-TYPE
         OBJECTS { omtp12PlusOduTcm2BackwardIncomingAlignmentErrorAlarm }
               STATUS  current
               DESCRIPTION
                        "OMTP12-PLUS ODU TCM2 backward incoming alignment error alarm trap"
        ::= { omtp12PlusAlarmNotification 65 }

        omtp12PlusOduTcm3BackwardIncomingAlignmentErrorAlarmTrap NOTIFICATION-TYPE
         OBJECTS { omtp12PlusOduTcm3BackwardIncomingAlignmentErrorAlarm }
               STATUS  current
               DESCRIPTION
                        "OMTP12-PLUS ODU TCM3 backward incoming alignment error alarm trap"
        ::= { omtp12PlusAlarmNotification 66 }

        omtp12PlusOduTcm4BackwardIncomingAlignmentErrorAlarmTrap NOTIFICATION-TYPE
         OBJECTS { omtp12PlusOduTcm4BackwardIncomingAlignmentErrorAlarm }
               STATUS  current
               DESCRIPTION
                        "OMTP12-PLUS ODU TCM4 backward incoming alignment error alarm trap"
        ::= { omtp12PlusAlarmNotification 67 }

        omtp12PlusOduTcm5BackwardIncomingAlignmentErrorAlarmTrap NOTIFICATION-TYPE
         OBJECTS { omtp12PlusOduTcm5BackwardIncomingAlignmentErrorAlarm }
               STATUS  current
               DESCRIPTION
                        "OMTP12-PLUS ODU TCM5 backward incoming alignment error alarm trap"
        ::= { omtp12PlusAlarmNotification 68 }

        omtp12PlusOduTcm6BackwardIncomingAlignmentErrorAlarmTrap NOTIFICATION-TYPE
         OBJECTS { omtp12PlusOduTcm6BackwardIncomingAlignmentErrorAlarm }
               STATUS  current
               DESCRIPTION
                        "OMTP12-PLUS ODU TCM6 backward incoming alignment error alarm trap"
        ::= { omtp12PlusAlarmNotification 69 }

        omtp12PlusOpuPayloadMismatchAlarmTrap NOTIFICATION-TYPE
         OBJECTS { omtp12PlusOpuPayloadMismatchAlarm }
               STATUS  current
               DESCRIPTION
                        "OMTP12-PLUS OPU payload mismatch alarm trap"
        ::= { omtp12PlusAlarmNotification 70 }
        omtp12PlusOchLossOfPayloadAlarmTrap NOTIFICATION-TYPE
         OBJECTS { omtp12PlusOchLossOfPayloadAlarm }
               STATUS  current
               DESCRIPTION
                        "OMTP12-PLUS Och loss of payload alarm trap"
        ::= { omtp12PlusAlarmNotification 71 }

        omtp12PlusSdhLossOfSignalAlarmTrap NOTIFICATION-TYPE
         OBJECTS { omtp12PlusSdhLossOfSignalAlarm }
               STATUS  current
               DESCRIPTION
                        "OMTP12-PLUS SDH loss of signal alarm trap"
        ::= { omtp12PlusAlarmNotification 81 }

        omtp12PlusSdhOutOfFrameAlarmTrap NOTIFICATION-TYPE
         OBJECTS { omtp12PlusSdhOutOfFrameAlarm }
               STATUS  current
               DESCRIPTION
                        "OMTP12-PLUS SDH out of frame alarm trap"
        ::= { omtp12PlusAlarmNotification 82 }

        omtp12PlusSdhLossOfFrameAlarmTrap NOTIFICATION-TYPE
         OBJECTS { omtp12PlusSdhLossOfFrameAlarm }
               STATUS  current
               DESCRIPTION
                        "OMTP12-PLUS SDH loss of frame alarm trap"
        ::= { omtp12PlusAlarmNotification 83 }

        omtp12PlusSdhRsAlarmIndicationSignalAlarmTrap NOTIFICATION-TYPE
         OBJECTS { omtp12PlusSdhRsAlarmIndicationSignalAlarm }
               STATUS  current
               DESCRIPTION
                        "OMTP12-PLUS SDH rs alarm indication signal alarm trap"
        ::= { omtp12PlusAlarmNotification 84 }

        omtp12PlusSdhRsTraceIdentifierMismatchAlarmTrap NOTIFICATION-TYPE
         OBJECTS { omtp12PlusSdhRsTraceIdentifierMismatchAlarm }
               STATUS  current
               DESCRIPTION
                        "OMTP12-PLUS SDH rs trace identifier mismatch alarm trap"
        ::= { omtp12PlusAlarmNotification 85 }

        omtp12PlusSdhAuAlarmIndicationSignalAlarmTrap NOTIFICATION-TYPE
         OBJECTS { omtp12PlusSdhAuAlarmIndicationSignalAlarm }
               STATUS  current
               DESCRIPTION
                        "OMTP12-PLUS SDH au alarm indication signal alarm trap"
        ::= { omtp12PlusAlarmNotification 86 }

        omtp12PlusSdhAuLossOfPointerAlarmTrap NOTIFICATION-TYPE
         OBJECTS { omtp12PlusSdhAuLossOfPointerAlarm }
               STATUS  current
               DESCRIPTION
                        "OMTP12-PLUS SDH au loss of pointer alarm trap"
        ::= { omtp12PlusAlarmNotification 87 }

        omtp12PlusSdhMsAlarmIndicationSignalAlarmTrap NOTIFICATION-TYPE
         OBJECTS { omtp12PlusSdhMsAlarmIndicationSignalAlarm }
               STATUS  current
               DESCRIPTION
                        "OMTP12-PLUS SDH ms alarm indication signal alarm trap"
        ::= { omtp12PlusAlarmNotification 88 }

        omtp12PlusSdhMsRemoteErrorIndicationAlarmTrap NOTIFICATION-TYPE
         OBJECTS { omtp12PlusSdhMsRemoteErrorIndicationAlarm }
               STATUS  current
               DESCRIPTION
                        "OMTP12-PLUS SDH ms remote error indication alarm trap"
        ::= { omtp12PlusAlarmNotification 89 }

        omtp12PlusSdhMsRemoteDefectIndicationAlarmTrap NOTIFICATION-TYPE
         OBJECTS { omtp12PlusSdhMsRemoteDefectIndicationAlarm }
               STATUS  current
               DESCRIPTION
                        "OMTP12-PLUS SDH ms remote defect indication alarm trap"
        ::= { omtp12PlusAlarmNotification 90 }

        omtp12PlusSdhMsRemoteFailureIndicationAlarmTrap NOTIFICATION-TYPE
         OBJECTS { omtp12PlusSdhMsRemoteFailureIndicationAlarm }
               STATUS  current
               DESCRIPTION
                        "OMTP12-PLUS SDH ms remote failure indication alarm trap"
        ::= { omtp12PlusAlarmNotification 91 }

        omtp12PlusSdhMsB2ExcessiveErrorAlarmTrap NOTIFICATION-TYPE
         OBJECTS { omtp12PlusSdhMsB2ExcessiveErrorAlarm }
               STATUS  current
               DESCRIPTION
                        "OMTP12-PLUS SDH ms b2 signal fail alarm trap"
        ::= { omtp12PlusAlarmNotification 92 }

        omtp12PlusSdhMsB2SignalDegradeAlarmTrap NOTIFICATION-TYPE
         OBJECTS { omtp12PlusSdhMsB2SignalDegradeAlarm }
               STATUS  current
               DESCRIPTION
                        "OMTP12-PLUS SDH ms b2 signal degrade alarm trap"
        ::= { omtp12PlusAlarmNotification 93 }

        omtp12PlusSdhLossOfSequenceSynchronisationAlarmTrap NOTIFICATION-TYPE
         OBJECTS { omtp12PlusSdhLossOfSequenceSynchronisationAlarm }
               STATUS  current
               DESCRIPTION
                        "OMTP12-PLUS SDH loss of sequence synchronisation alarm trap"
        ::= { omtp12PlusAlarmNotification 94 }

 	omtp12PlusSdhHigherOrderPathPayloadLabelMismatchAlarmTrap NOTIFICATION-TYPE
         OBJECTS { omtp12PlusSdhHigherOrderPathPayloadLabelMismatchAlarm }
               STATUS  current
               DESCRIPTION
                        "OMTP12-PLUS SDH higher order Payload Label Mismatch alarm trap"
        ::= { omtp12PlusAlarmNotification 95 }

        omtp12PlusSdhHigherOrderPathUnequippedAlarmTrap NOTIFICATION-TYPE
         OBJECTS { omtp12PlusSdhHigherOrderPathUnequippedAlarm }
               STATUS  current
               DESCRIPTION
                        "OMTP12-PLUS SDH higher order path unequipped alarm trap"
        ::= { omtp12PlusAlarmNotification 96 }

        omtp12PlusWan10gLossOfSignalAlarmTrap NOTIFICATION-TYPE
         OBJECTS { omtp12PlusWan10gLossOfSignalAlarm }
               STATUS  current
               DESCRIPTION
                        "OMTP12-PLUS WAN10G loss of signal alarm trap"
        ::= { omtp12PlusAlarmNotification 101 }

        omtp12PlusWan10gOutOfFrameAlarmTrap NOTIFICATION-TYPE
         OBJECTS { omtp12PlusWan10gOutOfFrameAlarm }
               STATUS  current
               DESCRIPTION
                        "OMTP12-PLUS WAN10G out of frame alarm trap"
        ::= { omtp12PlusAlarmNotification 102 }

        omtp12PlusWan10gLossOfFrameAlarmTrap NOTIFICATION-TYPE
         OBJECTS { omtp12PlusWan10gLossOfFrameAlarm }
               STATUS  current
               DESCRIPTION
                        "OMTP12-PLUS WAN10G loss of frame alarm trap"
        ::= { omtp12PlusAlarmNotification 97 }

        omtp12PlusWan10gRsAlarmIndicationSignalAlarmTrap NOTIFICATION-TYPE
         OBJECTS { omtp12PlusWan10gRsAlarmIndicationSignalAlarm }
               STATUS  current
               DESCRIPTION
                        "OMTP12-PLUS WAN10G rs alarm indication signal alarm trap"
        ::= { omtp12PlusAlarmNotification 103 }

        omtp12PlusWan10gRsTraceIdentifierMismatchAlarmTrap NOTIFICATION-TYPE
         OBJECTS { omtp12PlusWan10gRsTraceIdentifierMismatchAlarm }
               STATUS  current
               DESCRIPTION
                        "OMTP12-PLUS WAN10G rs trace identifier mismatch alarm trap"
        ::= { omtp12PlusAlarmNotification 104 }

        omtp12PlusWan10gAuAlarmIndicationSignalAlarmTrap NOTIFICATION-TYPE
         OBJECTS { omtp12PlusWan10gAuAlarmIndicationSignalAlarm }
               STATUS  current
               DESCRIPTION
                        "OMTP12-PLUS WAN10G au alarm indication signal alarm trap"
        ::= { omtp12PlusAlarmNotification 105 }

        omtp12PlusWan10gAuLossOfPointerAlarmTrap NOTIFICATION-TYPE
         OBJECTS { omtp12PlusWan10gAuLossOfPointerAlarm }
               STATUS  current
               DESCRIPTION
                        "OMTP12-PLUS WAN10G au loss of pointer alarm trap"
        ::= { omtp12PlusAlarmNotification 106 }

        omtp12PlusWan10gMsAlarmIndicationSignalAlarmTrap NOTIFICATION-TYPE
         OBJECTS { omtp12PlusWan10gMsAlarmIndicationSignalAlarm }
               STATUS  current
               DESCRIPTION
                        "OMTP12-PLUS WAN10G ms alarm indication signal alarm trap"
        ::= { omtp12PlusAlarmNotification 107 }

        omtp12PlusWan10gMsRemoteErrorIndicationAlarmTrap NOTIFICATION-TYPE
         OBJECTS { omtp12PlusWan10gMsRemoteErrorIndicationAlarm }
               STATUS  current
               DESCRIPTION
                        "OMTP12-PLUS WAN10G ms remote error indication alarm trap"
        ::= { omtp12PlusAlarmNotification 108 }

        omtp12PlusWan10gMsRemoteDefectIndicationAlarmTrap NOTIFICATION-TYPE
         OBJECTS { omtp12PlusWan10gMsRemoteDefectIndicationAlarm }
               STATUS  current
               DESCRIPTION
                        "OMTP12-PLUS WAN10G ms remote defect indication alarm trap"
        ::= { omtp12PlusAlarmNotification 109 }

        omtp12PlusWan10gMsRemoteFailureIndicationAlarmTrap NOTIFICATION-TYPE
         OBJECTS { omtp12PlusWan10gMsRemoteFailureIndicationAlarm }
               STATUS  current
               DESCRIPTION
                        "OMTP12-PLUS WAN10G ms remote failure indication alarm trap"
        ::= { omtp12PlusAlarmNotification 110 }

        omtp12PlusWan10gMsB2ExcessiveErrorAlarmTrap NOTIFICATION-TYPE
         OBJECTS { omtp12PlusWan10gMsB2ExcessiveErrorAlarm }
               STATUS  current
               DESCRIPTION
                        "OMTP12-PLUS WAN10G ms b2 signal fail alarm trap"
        ::= { omtp12PlusAlarmNotification 111 }

        omtp12PlusWan10gMsB2SignalDegradeAlarmTrap NOTIFICATION-TYPE
         OBJECTS { omtp12PlusWan10gMsB2SignalDegradeAlarm }
               STATUS  current
               DESCRIPTION
                        "OMTP12-PLUS WAN10G ms b2 signal degrade alarm trap"
        ::= { omtp12PlusAlarmNotification 112 }

        omtp12PlusWan10gLossOfSequenceSynchronisationAlarmTrap NOTIFICATION-TYPE
         OBJECTS { omtp12PlusWan10gLossOfSequenceSynchronisationAlarm }
               STATUS  current
               DESCRIPTION
                        "OMTP12-PLUS WAN10G loss of sequence synchronisation alarm trap"
        ::= { omtp12PlusAlarmNotification 113 }

       omtp12PlusWan10gHigherOrderPathPayloadLabelMismatchAlarmTrap NOTIFICATION-TYPE
         OBJECTS { omtp12PlusWan10gHigherOrderPathPayloadLabelMismatchAlarm }
               STATUS  current
               DESCRIPTION
                        "OMTP12-PLUS Wan10g higher order Payload Label Mismatch alarm trap"
        ::= { omtp12PlusAlarmNotification 114 }

        omtp12PlusWan10gHigherOrderPathUnequippedAlarmTrap NOTIFICATION-TYPE
         OBJECTS { omtp12PlusWan10gHigherOrderPathUnequippedAlarm }
               STATUS  current
               DESCRIPTION
                        "OMTP12-PLUS Wan10g higher order path unequipped alarm trap"
        ::= { omtp12PlusAlarmNotification 115 }

        omtp12PlusLan10gLossOfSignalAlarmTrap NOTIFICATION-TYPE
         OBJECTS { omtp12PlusLan10gLossOfSignalAlarm }
               STATUS  current
               DESCRIPTION
                        "OMTP12-PLUS LAN10g loss of signal alarm trap"
        ::= { omtp12PlusAlarmNotification 121 }

        omtp12PlusLan10gLossOfSignalSyncAlarmTrap NOTIFICATION-TYPE
         OBJECTS { omtp12PlusLan10gLossOfSignalSyncAlarm }
               STATUS  current
               DESCRIPTION
                        "OMTP12-PLUS LAN10g loss of signal sync alarm trap"
        ::= { omtp12PlusAlarmNotification 122 }

        omtp12PlusLan10gLinkFailureAlarmTrap NOTIFICATION-TYPE
         OBJECTS { omtp12PlusLan10gLinkFailureAlarm }
               STATUS  current
               DESCRIPTION
                        "OMTP12-PLUS LAN10g link failure alarm trap"
        ::= { omtp12PlusAlarmNotification 123 }

        omtp12PlusLan10gFrameCheckSequenceAlarmTrap NOTIFICATION-TYPE
         OBJECTS { omtp12PlusLan10gFrameCheckSequenceAlarm }
               STATUS  current
               DESCRIPTION
                        "OMTP12-PLUS LAN10g frame check sequence alarm trap"
        ::= { omtp12PlusAlarmNotification 124 }

        omtp12PlusLan10gCarrierStatusAlarmTrap NOTIFICATION-TYPE
         OBJECTS { omtp12PlusLan10gCarrierStatusAlarm }
               STATUS  current
               DESCRIPTION
                        "OMTP12-PLUS LAN10g carrier status alarm trap"
        ::= { omtp12PlusAlarmNotification 125 }

        omtp12PlusLan10gHighBerAlarmTrap NOTIFICATION-TYPE
         OBJECTS { omtp12PlusLan10gHighBerAlarm }
               STATUS  current
               DESCRIPTION
                        "OMTP12-PLUS LAN10g high ber Alarm trap"
        ::= { omtp12PlusAlarmNotification 126 }

        omtp12PlusLan10gLocalFaultAlarmTrap NOTIFICATION-TYPE
         OBJECTS { omtp12PlusLan10gLocalFaultAlarm }
               STATUS  current
               DESCRIPTION
                        "OMTP12-PLUS LAN10g local fault alarm trap"
        ::= { omtp12PlusAlarmNotification 127 }

        omtp12PlusLan10gRemoteFaultAlarmTrap NOTIFICATION-TYPE
         OBJECTS { omtp12PlusLan10gRemoteFaultAlarm }
               STATUS  current
               DESCRIPTION
                        "OMTP12-PLUS LAN10g remote fault alarm trap"
        ::= { omtp12PlusAlarmNotification 128 }

        omtp12PlusFcTransmitDisparityInversionDefectAlarmTrap NOTIFICATION-TYPE
         OBJECTS { omtp12PlusFcTransmitDisparityInversionDefectAlarm }
               STATUS  current
               DESCRIPTION
                        "OMTP12-PLUS FC transmit display invert alarm trap"
        ::= { omtp12PlusAlarmNotification 141 }

        omtp12PlusFcTransmitDigitalLossOfLinkDefectAlarmTrap NOTIFICATION-TYPE
         OBJECTS { omtp12PlusFcTransmitDigitalLossOfLinkDefectAlarm }
               STATUS  current
               DESCRIPTION
                        "OMTP12-PLUS FC transmit dlolb alarm trap"
        ::= { omtp12PlusAlarmNotification 142 }

        omtp12PlusFcTrasnmitLossofSynchronizationDefectAlarmTrap NOTIFICATION-TYPE
         OBJECTS { omtp12PlusFcTrasnmitLossofSynchronizationDefectAlarm }
               STATUS  current
               DESCRIPTION
                        "OMTP12-PLUS FC transmit sync alarm trap"
        ::= { omtp12PlusAlarmNotification 143 }

        omtp12PlusFcReceiveDigitalLossofLinkDefectAlarmTrap NOTIFICATION-TYPE
         OBJECTS { omtp12PlusFcReceiveDigitalLossofLinkDefectAlarm }
               STATUS  current
               DESCRIPTION
                        "OMTP12-PLUS FC receive dlolb alarm trap"
        ::= { omtp12PlusAlarmNotification 144 }

        omtp12PlusFcReceiveLossofSynchronizationDefectAlarmTrap NOTIFICATION-TYPE
         OBJECTS { omtp12PlusFcReceiveLossofSynchronizationDefectAlarm }
               STATUS  current
               DESCRIPTION
                        "OMTP12-PLUS FC receive sync alarm trap"
        ::= { omtp12PlusAlarmNotification 145 }

        omtp12PlusFcReceiveTransitionDetectDefectAlarmTrap NOTIFICATION-TYPE
         OBJECTS { omtp12PlusFcReceiveTransitionDetectDefectAlarm }
               STATUS  current
               DESCRIPTION
                        "OMTP12-PLUS FC receive xdet alarm trap"
        ::= { omtp12PlusAlarmNotification 146 }

        omtp12PlusFcReceiveAnalogLossofSignalDefectAlarmTrap NOTIFICATION-TYPE
         OBJECTS { omtp12PlusFcReceiveAnalogLossofSignalDefectAlarm }
               STATUS  current
               DESCRIPTION
                        "OMTP12-PLUS FC receive asd alarm trap"
        ::= { omtp12PlusAlarmNotification 147 }

        omtp12PlusFcReceiveLineCodeViolationDefectAlarmTrap NOTIFICATION-TYPE
         OBJECTS { omtp12PlusFcReceiveLineCodeViolationDefectAlarm }
               STATUS  current
               DESCRIPTION
                        "OMTP12-PLUS FC receive lcv alarm trap"
        ::= { omtp12PlusAlarmNotification 148 }

        omtp12PlusGfpCsfSignalFailAlarmTrap NOTIFICATION-TYPE
         OBJECTS { omtp12PlusGfpCsfSignalFailAlarm }
               STATUS  current
               DESCRIPTION
                        "OMTP12-PLUS GFP signal failure alarm trap"
        ::= { omtp12PlusAlarmNotification 161 }

        omtp12PlusGfpCsfLinkFailAlarmTrap NOTIFICATION-TYPE
         OBJECTS { omtp12PlusGfpCsfLinkFailAlarm }
               STATUS  current
               DESCRIPTION
                        "OMTP12-PLUS GFP link failure alarm trap"
        ::= { omtp12PlusAlarmNotification 162 }

        omtp12PlusGfpCoreHeaderErrorAlarmTrap NOTIFICATION-TYPE
         OBJECTS { omtp12PlusGfpCoreHeaderErrorAlarm }
               STATUS  current
               DESCRIPTION
                        "OMTP12-PLUS GFP core header error alarm trap"
        ::= { omtp12PlusAlarmNotification 163 }

        omtp12PlusGfpExtentionHeaderErrorAlarmTrap NOTIFICATION-TYPE
         OBJECTS { omtp12PlusGfpExtentionHeaderErrorAlarm }
               STATUS  current
               DESCRIPTION
                        "OMTP12-PLUS GFP extention header error alarm"
        ::= { omtp12PlusAlarmNotification 164 }

             
--*****************************************************************************
--				    ALARM NOTIFICATION
--*****************************************************************************

	snmpCurrentNotificationsGroup NOTIFICATION-GROUP
		NOTIFICATIONS { 
					omtp12PlusXfpInputPowerFailureAlarmTrap,
					omtp12PlusXfpOutputPowerFailureAlarmTrap,
					omtp12PlusXfpHighTemperatureAlarmTrap,
					omtp12PlusXfpLowTemperatureAlarmTrap,
					omtp12PlusXfpHighTemperatureWarningTrap,
					omtp12PlusXfpLowTemperatureWarningTrap,
					omtp12PlusXfpHighBiasCurrentAlarmTrap,
					omtp12PlusXfpLowBiasCurrentAlarmTrap,
					omtp12PlusXfpHighBiasCurrentWarningTrap,
					omtp12PlusXfpLowBiasCurrentWarningTrap,
					omtp12PlusXfpInputHighPowerAlarmTrap,
					omtp12PlusXfpInputLowPowerAlarmTrap,
					omtp12PlusXfpInputHighPowerWarningTrap,
					omtp12PlusXfpInputLowPowerWarningTrap,
					omtp12PlusXfpOutputHighPowerAlarmTrap,
					omtp12PlusXfpOutputLowPowerAlarmTrap,
					omtp12PlusXfpOutputHighPowerWarningTrap,
					omtp12PlusXfpOutputLowPowerWarningTrap,
					omtp12PlusXfpHighSupplyVoltageAlarmTrap,
					omtp12PlusXfpLowSupplyVoltageAlarmTrap,
					omtp12PlusXfpHighSupplyVoltageWarningTrap,
					omtp12PlusXfpLowSupplyVoltageWarningTrap,
					omtp12PlusXfpPresenceAbsenceNotificationTrap,
					omtp12PlusOtuLossOfSignalAlarmTrap,
					omtp12PlusOtuLossOfFrameAlarmTrap,
					omtp12PlusOtuOutOfFrameAlarmTrap,
					omtp12PlusOtuLossOfMultiFrameAlarmTrap,
					omtp12PlusOtuOutOfMultiFrameAlarmTrap,
					omtp12PlusOtuSignalFailAlarmTrap,
					omtp12PlusOtuSignalDegradeAlarmTrap,
					omtp12PlusOtuAlarmIndicationSignalAlarmTrap,
					omtp12PlusOtuIncomingAlignmentErrorAlarmTrap,
					omtp12PlusOtuTraceIdentifierMismatchAlarmTrap,
					omtp12PlusOtuBackwardIncomingAlignmentErrorAlarmTrap,
					omtp12PlusOtuBackwardDefectIndicationAlarmTrap,
					omtp12PlusOduSignalFailAlarmTrap,
					omtp12PlusOduSignalDegradeAlarmTrap,
					omtp12PlusOduAlarmIndicationSignalAlarmTrap,
					omtp12PlusOduTcm1IncomingAlignmentErrorAlarmTrap,
					omtp12PlusOduTcm2IncomingAlignmentErrorAlarmTrap,
					omtp12PlusOduTcm3IncomingAlignmentErrorAlarmTrap,
					omtp12PlusOduTcm4IncomingAlignmentErrorAlarmTrap,
					omtp12PlusOduTcm5IncomingAlignmentErrorAlarmTrap,
					omtp12PlusOduTcm6IncomingAlignmentErrorAlarmTrap,
					omtp12PlusOduTraceIdentifierMismatchAlarmTrap,
					omtp12PlusOduLockedDefectAlarmTrap,
					omtp12PlusOduOpenConnectionIndicationAlarmTrap,
					omtp12PlusOduBackwardDefectIndicationAlarmTrap,
					omtp12PlusOduTcm1BackwardIncomingAlignmentErrorAlarmTrap,
					omtp12PlusOduTcm2BackwardIncomingAlignmentErrorAlarmTrap,
					omtp12PlusOduTcm3BackwardIncomingAlignmentErrorAlarmTrap,
					omtp12PlusOduTcm4BackwardIncomingAlignmentErrorAlarmTrap,
					omtp12PlusOduTcm5BackwardIncomingAlignmentErrorAlarmTrap,
					omtp12PlusOduTcm6BackwardIncomingAlignmentErrorAlarmTrap,
					omtp12PlusOpuPayloadMismatchAlarmTrap,
					omtp12PlusOchLossOfPayloadAlarmTrap,
					omtp12PlusSdhLossOfSignalAlarmTrap,
					omtp12PlusSdhOutOfFrameAlarmTrap,
					omtp12PlusSdhLossOfFrameAlarmTrap,
					omtp12PlusSdhRsAlarmIndicationSignalAlarmTrap,
					omtp12PlusSdhRsTraceIdentifierMismatchAlarmTrap,
					omtp12PlusSdhAuAlarmIndicationSignalAlarmTrap,
					omtp12PlusSdhAuLossOfPointerAlarmTrap,
					omtp12PlusSdhMsAlarmIndicationSignalAlarmTrap,
					omtp12PlusSdhMsRemoteErrorIndicationAlarmTrap,
					omtp12PlusSdhMsRemoteDefectIndicationAlarmTrap,
					omtp12PlusSdhMsRemoteFailureIndicationAlarmTrap,
					omtp12PlusSdhMsB2ExcessiveErrorAlarmTrap,
					omtp12PlusSdhMsB2SignalDegradeAlarmTrap,
					omtp12PlusSdhLossOfSequenceSynchronisationAlarmTrap,
					omtp12PlusSdhHigherOrderPathPayloadLabelMismatchAlarmTrap,
					omtp12PlusSdhHigherOrderPathUnequippedAlarmTrap,
					omtp12PlusWan10gLossOfSignalAlarmTrap,
					omtp12PlusWan10gOutOfFrameAlarmTrap,
					omtp12PlusWan10gLossOfFrameAlarmTrap,
					omtp12PlusWan10gRsAlarmIndicationSignalAlarmTrap,
					omtp12PlusWan10gRsTraceIdentifierMismatchAlarmTrap,
					omtp12PlusWan10gAuAlarmIndicationSignalAlarmTrap,
					omtp12PlusWan10gAuLossOfPointerAlarmTrap,
					omtp12PlusWan10gMsAlarmIndicationSignalAlarmTrap,
					omtp12PlusWan10gMsRemoteErrorIndicationAlarmTrap,
					omtp12PlusWan10gMsRemoteDefectIndicationAlarmTrap,
					omtp12PlusWan10gMsRemoteFailureIndicationAlarmTrap,
					omtp12PlusWan10gMsB2ExcessiveErrorAlarmTrap,
					omtp12PlusWan10gMsB2SignalDegradeAlarmTrap,
					omtp12PlusWan10gLossOfSequenceSynchronisationAlarmTrap,
					omtp12PlusWan10gHigherOrderPathPayloadLabelMismatchAlarmTrap,
					omtp12PlusWan10gHigherOrderPathUnequippedAlarmTrap,
					omtp12PlusLan10gLossOfSignalAlarmTrap,
					omtp12PlusLan10gLossOfSignalSyncAlarmTrap,
					omtp12PlusLan10gLinkFailureAlarmTrap,
					omtp12PlusLan10gFrameCheckSequenceAlarmTrap,
					omtp12PlusLan10gCarrierStatusAlarmTrap,
					omtp12PlusLan10gHighBerAlarmTrap,
					omtp12PlusLan10gLocalFaultAlarmTrap,
					omtp12PlusLan10gRemoteFaultAlarmTrap,
					omtp12PlusFcTransmitDisparityInversionDefectAlarmTrap,
					omtp12PlusFcTransmitDigitalLossOfLinkDefectAlarmTrap,
					omtp12PlusFcTrasnmitLossofSynchronizationDefectAlarmTrap,
					omtp12PlusFcReceiveDigitalLossofLinkDefectAlarmTrap,
					omtp12PlusFcReceiveLossofSynchronizationDefectAlarmTrap,
					omtp12PlusFcReceiveTransitionDetectDefectAlarmTrap,
					omtp12PlusFcReceiveAnalogLossofSignalDefectAlarmTrap,
					omtp12PlusFcReceiveLineCodeViolationDefectAlarmTrap,
					omtp12PlusGfpCsfSignalFailAlarmTrap,
					omtp12PlusGfpCsfLinkFailAlarmTrap,
					omtp12PlusGfpCoreHeaderErrorAlarmTrap,
					omtp12PlusGfpExtentionHeaderErrorAlarmTrap
		}
  	  STATUS current
  	  DESCRIPTION
		"The UTL OMTP12-PLUS current notifications group"
  	  ::= { omtp12Plus 6 }

	snmpcurrentGroup OBJECT-GROUP
		OBJECTS {
				omtp12PlusInterfaceNumber, 
				omtp12PlusEepromCardId,
				omtp12PlusEepromCardName,
				omtp12PlusEepromPartCode,
				omtp12PlusEepromCardSerialNumber,
				omtp12PlusEepromHardwareExternalReleaseVersion,
				omtp12PlusSoftwareExternalReleaseVersion,
				omtp12PlusEepromHardwareInternalReleaseVersion,
				omtp12PlusSoftwareInternalReleaseVersion,
				omtp12PlusEepromCardUidNumber,
				omtp12PlusEepromCardEui48Number,
				omtp12PlusEepromCardEui64Number,
				omtp12PlusCardRootFileSystemVersion,
				omtp12PlusCardInstallationDate,
				omtp12PlusCardCommissionDate,
				omtp12PlusCardRunningTime,
				omtp12PlusCardRestartCount,
				omtp12PlusXfpReadyForOperation,
				omtp12PlusXfpI2cCommunicationStatus,
				omtp12PlusXfpEepromPage,
				omtp12PlusCheckCodeOfXfpEepromPage,
				omtp12PlusExtendedCheckCodeOfXfpEepromPage,
				omtp12PlusXfpVendorName,
				omtp12PlusXfpVendorIeeeId,
				omtp12PlusXfpPartNumber,
				omtp12PlusXfpSerialNumber,
				omtp12PlusXfpRevisionNumber,
				omtp12PlusXfpManufacturingDate,
				omtp12PlusFixedXfpLaserWavelength,
				omtp12PlusXfpLaserWavelengthTolerance,
				omtp12PlusXfpWavelengthTunabilitySupported,
				omtp12PlusTunableXfpLaserWavelengthError,
				omtp12PlusTunableXfpLaserFrequencyError,
				omtp12PlusTunableXfpLaserFirstFrequency,
				omtp12PlusTunableXfpLaserLastFrequency,
				omtp12PlusTunableXfpWavelengthGridSpacing,
				omtp12PlusXfpConnectorType,
				omtp12PlusXfpLinkLength,
				omtp12PlusXfpCdrRateSupported,
				omtp12PlusXfpSignalEncodingTypeSupported,
				omtp12PlusXfpTransceiverCodesSupported,
				omtp12PlusXfpMaximumBitrateSupported,
				omtp12PlusXfpMinimumBitrateSupported,
				omtp12PlusXfpMaximumCaseTemperatureSupported,
				omtp12PlusXfpMaximumPowerDissipationSupported,
				omtp12PlusXfpMaximumPowerDissipationSupportedAtPowerDownMode,
				omtp12PlusXfpMaximumCurrentLimitSupportedAtPlus5vSupply,
				omtp12PlusXfpMaximumCurrentLimitSupportedAtPlus3Point3vSupply,
				omtp12PlusXfpMaximumCurrentLimitSupportedAtPlus1Point8vSupply,
				omtp12PlusXfpMaximumCurrentLimitSupportedAtMinus5Point2vSupply,
				omtp12PlusXfpLineLoopbackSupported,
				omtp12PlusXfpXfiLoopbackSupported,
				omtp12PlusXfpOptionalVpsSupported,
				omtp12PlusXfpLaserDisableThroughI2cSupported,
				omtp12PlusXfpPowerDownThroughI2cSupported,
				omtp12PlusXfpVpsLvRegulatorModeSupported,
				omtp12PlusXfpVpsBypassedRegulatorModeSupported,
				omtp12PlusXfpActiveFecControlSupported,
				omtp12PlusXfpOptionalCmuModeSupported,
				omtp12PlusXfpFecBerSupported,
				omtp12PlusXfpReceivePowerMeasurementIsInOmaOrAverage,
				omtp12PlusXfpActiveWavelengthControlSupported,
				omtp12PlusXfpTransmitterIsCooledOrUncooled,
				omtp12PlusXfpReceiverTypeIsPinOrApd,
				omtp12PlusCardGeneralDetailsTableRowStatus,
				omtp12PlusCardSoftwareUpgrade,
				omtp12PlusCardSignalMonitorState,
				omtp12PlusCardOpticalMonitorState,
				omtp12PlusCardSoftReset,
				omtp12PlusCardFactoryReset,
				omtp12PlusCardAccessStatus,
				omtp12PlusSyncSystemTimeWithNtpServer,
				omtp12PlusSyncRtcWithNtpServer,
				omtp12PlusSyncRtcWithSystemTime,
				omtp12PlusUpdateGivenTimeIntoSystem,
				omtp12PlusUpdateGivenTimeIntoRtc,
				omtp12PlusSystemTimeAndRtcTime,
				omtp12PlusTrafficConfiguration,
				omtp12PlusLoopbackState,
				omtp12PlusPortSignalMonitorState,
				omtp12PlusPortOpticalMonitorState,
				omtp12PlusClearSignalPerformance,
				omtp12PlusAlsState,
				omtp12PlusAlsPulseRepetitionTime,
				omtp12PlusOtuFecConfiguration,
				omtp12PlusOtuSignalFailThreshold,
				omtp12PlusOtuSignalDegradeThreshold,
				omtp12PlusOtuAlarmIndicationSignalAlarmInsertion,
				omtp12PlusOtuSapiTransmitTraceMessage,
				omtp12PlusOtuDapiTransmitTraceMessage,
				omtp12PlusOtuOperatorSpecificTransmitTraceMessage,
				omtp12PlusOtuSapiExpectedTraceMessage,
				omtp12PlusOtuDapiExpectedTraceMessage,
				omtp12PlusOtuOperatorSpecificExpectedTraceMessage,
				omtp12PlusOtuSapiReceivedTraceMessage,
				omtp12PlusOtuDapiReceivedTraceMessage,
				omtp12PlusOtuOperatorSpecificReceivedTraceMessage,
				omtp12PlusOduSignalFailThreshold,
				omtp12PlusOduSignalDegradeThreshold,
				omtp12PlusOduAlarmIndicationSignalAlarmInsertion,
				omtp12PlusOduLockedDefectAlarmInsertion,
				omtp12PlusOduOpenConnectionIndicationAlarmInsertion,
				omtp12PlusOduSapiTransmitTraceMessage,
				omtp12PlusOduDapiTransmitTraceMessage,
				omtp12PlusOduOperatorSpecificTransmitTraceMessage,
				omtp12PlusOduSapiExpectedTraceMessage,
				omtp12PlusOduDapiExpectedTraceMessage,
				omtp12PlusOduOperatorSpecificExpectedTraceMessage,
				omtp12PlusOduSapiReceivedTraceMessage,
				omtp12PlusOduDapiReceivedTraceMessage,
				omtp12PlusOduOperatorSpecificReceivedTraceMessage,
				omtp12PlusOpuTransmitPayloadType,
				omtp12PlusOpuReceivedPayloadType,
				omtp12PlusSdhMsB2ExcessiveErrorThreshold,
				omtp12PlusSdhMsB2SignalDegradeThreshold,
				omtp12PlusWan10gMsB2ExcessiveErrorThreshold,
				omtp12PlusWan10gMsB2SignalDegradeThreshold,
				omtp12PlusApsLinePathSwitchingMode,
				omtp12PlusApsUserChoiceOfLinePath,
				omtp12PlusApsCurrentOperationalLinePath,
				omtp12PlusTunableXfpLaserWavelength,
				omtp12PlusTunableXfpLaserChannelNumber,
				omtp12PlusXfpLaserState,
				omtp12PlusXfpReset,
				omtp12PlusXfpPowerDownMode,
				omtp12PlusXfpLineLoopback,
				omtp12PlusXfpXfiLoopback,
				omtp12PlusXfpAmplitudeThresholdOfReceiverForFecControl,
				omtp12PlusXfpPhaseInEyeDiagramForFecControl,
				omtp12PlusXfpSystemReportingBer,
				omtp12PlusXfpHighTemperatureAlarmThreshold,
				omtp12PlusXfpLowTemperatureAlarmThreshold,
				omtp12PlusXfpHighTemperatureWarningThreshold,
				omtp12PlusXfpLowTemperatureWarningThreshold,
				omtp12PlusXfpHighBiasCurrentAlarmThreshold,
				omtp12PlusXfpLowBiasCurrentAlarmThreshold,
				omtp12PlusXfpHighBiasCurrentWarningThreshold,
				omtp12PlusXfpLowBiasCurrentWarningThreshold,
				omtp12PlusXfpInputHighPowerAlarmThreshold,
				omtp12PlusXfpInputLowPowerAlarmThreshold,
				omtp12PlusXfpInputHighPowerWarningThreshold,
				omtp12PlusXfpInputLowPowerWarningThreshold,
				omtp12PlusXfpOutputHighPowerAlarmThreshold,
				omtp12PlusXfpOutputLowPowerAlarmThreshold,
				omtp12PlusXfpOutputHighPowerWarningThreshold,
				omtp12PlusXfpOutputLowPowerWarningThreshold,
				omtp12PlusXfpHighSupplyVoltageAlarmThreshold,
				omtp12PlusXfpLowSupplyVoltageAlarmThreshold,
				omtp12PlusXfpHighSupplyVoltageWarningThreshold,
				omtp12PlusXfpLowSupplyVoltageWarningThreshold,
				omtp12PlusXfpInputPowerFailureAlarmInhibit,
				omtp12PlusXfpOutputPowerFailureAlarmInhibit,
				omtp12PlusXfpHighTemperatureAlarmInhibit,
				omtp12PlusXfpLowTemperatureAlarmInhibit,
				omtp12PlusXfpHighTemperatureWarningInhibit,
				omtp12PlusXfpLowTemperatureWarningInhibit,
				omtp12PlusXfpHighBiasCurrentAlarmInhibit,
				omtp12PlusXfpLowBiasCurrentAlarmInhibit,
				omtp12PlusXfpHighBiasCurrentWarningInhibit,
				omtp12PlusXfpLowBiasCurrentWarningInhibit,
				omtp12PlusXfpInputHighPowerAlarmInhibit,
				omtp12PlusXfpInputLowPowerAlarmInhibit,
				omtp12PlusXfpInputHighPowerWarningInhibit,
				omtp12PlusXfpInputLowPowerWarningInhibit,
				omtp12PlusXfpOutputHighPowerAlarmInhibit,
				omtp12PlusXfpOutputLowPowerAlarmInhibit,
				omtp12PlusXfpOutputHighPowerWarningInhibit,
				omtp12PlusXfpOutputLowPowerWarningInhibit,
				omtp12PlusXfpHighSupplyVoltageAlarmInhibit,
				omtp12PlusXfpLowSupplyVoltageAlarmInhibit,
				omtp12PlusXfpHighSupplyVoltageWarningInhibit,
				omtp12PlusXfpLowSupplyVoltageWarningInhibit,
				omtp12PlusXfpPresenceAbsenceNotificationInhibit,
				omtp12PlusOtuLossOfSignalAlarmInhibit,
				omtp12PlusOtuLossOfFrameAlarmInhibit,
				omtp12PlusOtuOutOfFrameAlarmInhibit,
				omtp12PlusOtuLossOfMultiFrameAlarmInhibit,
				omtp12PlusOtuOutOfMultiFrameAlarmInhibit,
				omtp12PlusOtuSignalFailAlarmInhibit,
				omtp12PlusOtuSignalDegradeAlarmInhibit,
				omtp12PlusOtuAlarmIndicationSignalAlarmInhibit,
				omtp12PlusOtuIncomingAlignmentErrorAlarmInhibit,
				omtp12PlusOtuTraceIdentifierMismatchAlarmInhibit,
				omtp12PlusOtuBackwardIncomingAlignmentErrorAlarmInhibit,
				omtp12PlusOtuBackwardDefectIndicationAlarmInhibit,
				omtp12PlusOduSignalFailAlarmInhibit,
				omtp12PlusOduSignalDegradeAlarmInhibit,
				omtp12PlusOduAlarmIndicationSignalAlarmInhibit,
				omtp12PlusOduTcm1IncomingAlignmentErrorAlarmInhibit,
				omtp12PlusOduTcm2IncomingAlignmentErrorAlarmInhibit,
				omtp12PlusOduTcm3IncomingAlignmentErrorAlarmInhibit,
				omtp12PlusOduTcm4IncomingAlignmentErrorAlarmInhibit,
				omtp12PlusOduTcm5IncomingAlignmentErrorAlarmInhibit,
				omtp12PlusOduTcm6IncomingAlignmentErrorAlarmInhibit,
				omtp12PlusOduTraceIdentifierMismatchAlarmInhibit,
				omtp12PlusOduLockedDefectAlarmInhibit,
				omtp12PlusOduOpenConnectionIndicationAlarmInhibit,
				omtp12PlusOduBackwardDefectIndicationAlarmInhibit,
				omtp12PlusOduTcm1BackwardIncomingAlignmentErrorAlarmInhibit,
				omtp12PlusOduTcm2BackwardIncomingAlignmentErrorAlarmInhibit,
				omtp12PlusOduTcm3BackwardIncomingAlignmentErrorAlarmInhibit,
				omtp12PlusOduTcm4BackwardIncomingAlignmentErrorAlarmInhibit,
				omtp12PlusOduTcm5BackwardIncomingAlignmentErrorAlarmInhibit,
				omtp12PlusOduTcm6BackwardIncomingAlignmentErrorAlarmInhibit,
				omtp12PlusOpuPayloadMismatchAlarmInhibit,
				omtp12PlusOchLossOfPayloadAlarmInhibit,
				omtp12PlusSdhLossOfSignalAlarmInhibit,
				omtp12PlusSdhOutOfFrameAlarmInhibit,
				omtp12PlusSdhLossOfFrameAlarmInhibit,
				omtp12PlusSdhRsAlarmIndicationSignalAlarmInhibit,
				omtp12PlusSdhRsTraceIdentifierMismatchAlarmInhibit,
				omtp12PlusSdhAuAlarmIndicationSignalAlarmInhibit,
				omtp12PlusSdhAuLossOfPointerAlarmInhibit,
				omtp12PlusSdhMsAlarmIndicationSignalAlarmInhibit,
				omtp12PlusSdhMsRemoteErrorIndicationAlarmInhibit,
				omtp12PlusSdhMsRemoteDefectIndicationAlarmInhibit,
				omtp12PlusSdhMsRemoteFailureIndicationAlarmInhibit,
				omtp12PlusSdhMsB2ExcessiveErrorAlarmInhibit,
				omtp12PlusSdhMsB2SignalDegradeAlarmInhibit,
				omtp12PlusSdhLossOfSequenceSynchronisationAlarmInhibit,
				omtp12PlusSdhHigherOrderPathPayloadLabelMismatchAlarmInhibit,
				omtp12PlusSdhHigherOrderPathUnequippedAlarmInhibit,
				omtp12PlusWan10gLossOfSignalAlarmInhibit,
				omtp12PlusWan10gOutOfFrameAlarmInhibit,
				omtp12PlusWan10gLossOfFrameAlarmInhibit,
				omtp12PlusWan10gRsAlarmIndicationSignalAlarmInhibit,
				omtp12PlusWan10gRsTraceIdentifierMismatchAlarmInhibit,
				omtp12PlusWan10gAuAlarmIndicationSignalAlarmInhibit,
				omtp12PlusWan10gAuLossOfPointerAlarmInhibit,
				omtp12PlusWan10gMsAlarmIndicationSignalAlarmInhibit,
				omtp12PlusWan10gMsRemoteErrorIndicationAlarmInhibit,
				omtp12PlusWan10gMsRemoteDefectIndicationAlarmInhibit,
				omtp12PlusWan10gMsRemoteFailureIndicationAlarmInhibit,
				omtp12PlusWan10gMsB2ExcessiveErrorAlarmInhibit,
				omtp12PlusWan10gMsB2SignalDegradeAlarmInhibit,
				omtp12PlusWan10gLossOfSequenceSynchronisationAlarmInhibit,
				omtp12PlusWan10gHigherOrderPathPayloadLabelMismatchAlarmInhibit,
				omtp12PlusWan10gHigherOrderPathUnequippedAlarmInhibit,
				omtp12PlusLan10gLossOfSignalAlarmInhibit,
				omtp12PlusLan10gLossOfSignalSyncAlarmInhibit,
				omtp12PlusLan10gLinkFailureAlarmInhibit,
				omtp12PlusLan10gFrameCheckSequenceAlarmInhibit,
				omtp12PlusLan10gCarrierStatusAlarmInhibit,
				omtp12PlusLan10gHighBerAlarmInhibit,
				omtp12PlusLan10gLocalFaultAlarmInhibit,
				omtp12PlusLan10gRemoteFaultAlarmInhibit,
				omtp12PlusFcTransmitDisparityInversionDefectAlarmInhibit,
				omtp12PlusFcTransmitDigitalLossOfLinkDefectAlarmInhibit,
				omtp12PlusFcTrasnmitLossofSynchronizationDefectAlarmInhibit,
				omtp12PlusFcReceiveDigitalLossofLinkDefectAlarmInhibit,
				omtp12PlusFcReceiveLossofSynchronizationDefectAlarmInhibit,
				omtp12PlusFcReceiveTransitionDetectDefectAlarmInhibit,
				omtp12PlusFcReceiveAnalogLossofSignalDefectAlarmInhibit,
				omtp12PlusFcReceiveLineCodeViolationDefectAlarmInhibit,
				omtp12PlusGfpCsfSignalFailAlarmInhibit,
				omtp12PlusGfpCsfLinkFailAlarmInhibit,
				omtp12PlusGfpCoreHeaderErrorAlarmInhibit,
				omtp12PlusGfpExtentionHeaderErrorAlarmInhibit,
				omtp12PlusXfpInputPowerFailureAlarmSeverity,
				omtp12PlusXfpOutputPowerFailureAlarmSeverity,
				omtp12PlusXfpHighTemperatureAlarmSeverity,
				omtp12PlusXfpLowTemperatureAlarmSeverity,
				omtp12PlusXfpHighTemperatureWarningSeverity,
				omtp12PlusXfpLowTemperatureWarningSeverity,
				omtp12PlusXfpHighBiasCurrentAlarmSeverity,
				omtp12PlusXfpLowBiasCurrentAlarmSeverity,
				omtp12PlusXfpHighBiasCurrentWarningSeverity,
				omtp12PlusXfpLowBiasCurrentWarningSeverity,
				omtp12PlusXfpInputHighPowerAlarmSeverity,
				omtp12PlusXfpInputLowPowerAlarmSeverity,
				omtp12PlusXfpInputHighPowerWarningSeverity,
				omtp12PlusXfpInputLowPowerWarningSeverity,
				omtp12PlusXfpOutputHighPowerAlarmSeverity,
				omtp12PlusXfpOutputLowPowerAlarmSeverity,
				omtp12PlusXfpOutputHighPowerWarningSeverity,
				omtp12PlusXfpOutputLowPowerWarningSeverity,
				omtp12PlusXfpHighSupplyVoltageAlarmSeverity,
				omtp12PlusXfpLowSupplyVoltageAlarmSeverity,
				omtp12PlusXfpHighSupplyVoltageWarningSeverity,
				omtp12PlusXfpLowSupplyVoltageWarningSeverity,
				omtp12PlusXfpPresenceAbsenceNotificationSeverity,
				omtp12PlusOtuLossOfSignalAlarmSeverity,
				omtp12PlusOtuLossOfFrameAlarmSeverity,
				omtp12PlusOtuOutOfFrameAlarmSeverity,
				omtp12PlusOtuLossOfMultiFrameAlarmSeverity,
				omtp12PlusOtuOutOfMultiFrameAlarmSeverity,
				omtp12PlusOtuSignalFailAlarmSeverity,
				omtp12PlusOtuSignalDegradeAlarmSeverity,
				omtp12PlusOtuAlarmIndicationSignalAlarmSeverity,
				omtp12PlusOtuIncomingAlignmentErrorAlarmSeverity,
				omtp12PlusOtuTraceIdentifierMismatchAlarmSeverity,
				omtp12PlusOtuBackwardIncomingAlignmentErrorAlarmSeverity,
				omtp12PlusOtuBackwardDefectIndicationAlarmSeverity,
				omtp12PlusOduSignalFailAlarmSeverity,
				omtp12PlusOduSignalDegradeAlarmSeverity,
				omtp12PlusOduAlarmIndicationSignalAlarmSeverity,
				omtp12PlusOduTcm1IncomingAlignmentErrorAlarmSeverity,
				omtp12PlusOduTcm2IncomingAlignmentErrorAlarmSeverity,
				omtp12PlusOduTcm3IncomingAlignmentErrorAlarmSeverity,
				omtp12PlusOduTcm4IncomingAlignmentErrorAlarmSeverity,
				omtp12PlusOduTcm5IncomingAlignmentErrorAlarmSeverity,
				omtp12PlusOduTcm6IncomingAlignmentErrorAlarmSeverity,
				omtp12PlusOduTraceIdentifierMismatchAlarmSeverity,
				omtp12PlusOduLockedDefectAlarmSeverity,
				omtp12PlusOduOpenConnectionIndicationAlarmSeverity,
				omtp12PlusOduBackwardDefectIndicationAlarmSeverity,
				omtp12PlusOduTcm1BackwardIncomingAlignmentErrorAlarmSeverity,
				omtp12PlusOduTcm2BackwardIncomingAlignmentErrorAlarmSeverity,
				omtp12PlusOduTcm3BackwardIncomingAlignmentErrorAlarmSeverity,
				omtp12PlusOduTcm4BackwardIncomingAlignmentErrorAlarmSeverity,
				omtp12PlusOduTcm5BackwardIncomingAlignmentErrorAlarmSeverity,
				omtp12PlusOduTcm6BackwardIncomingAlignmentErrorAlarmSeverity,
				omtp12PlusOpuPayloadMismatchAlarmSeverity,
				omtp12PlusOchLossOfPayloadAlarmSeverity,
				omtp12PlusSdhLossOfSignalAlarmSeverity,
				omtp12PlusSdhOutOfFrameAlarmSeverity,
				omtp12PlusSdhLossOfFrameAlarmSeverity,
				omtp12PlusSdhRsAlarmIndicationSignalAlarmSeverity,
				omtp12PlusSdhRsTraceIdentifierMismatchAlarmSeverity,
				omtp12PlusSdhAuAlarmIndicationSignalAlarmSeverity,
				omtp12PlusSdhAuLossOfPointerAlarmSeverity,
				omtp12PlusSdhMsAlarmIndicationSignalAlarmSeverity,
				omtp12PlusSdhMsRemoteErrorIndicationAlarmSeverity,
				omtp12PlusSdhMsRemoteDefectIndicationAlarmSeverity,
				omtp12PlusSdhMsRemoteFailureIndicationAlarmSeverity,
				omtp12PlusSdhMsB2ExcessiveErrorAlarmSeverity,
				omtp12PlusSdhMsB2SignalDegradeAlarmSeverity,
				omtp12PlusSdhLossOfSequenceSynchronisationAlarmSeverity,
				omtp12PlusSdhHigherOrderPathPayloadLabelMismatchAlarmSeverity,
				omtp12PlusSdhHigherOrderPathUnequippedAlarmSeverity,
				omtp12PlusWan10gLossOfSignalAlarmSeverity,
				omtp12PlusWan10gOutOfFrameAlarmSeverity,
				omtp12PlusWan10gLossOfFrameAlarmSeverity,
				omtp12PlusWan10gRsAlarmIndicationSignalAlarmSeverity,
				omtp12PlusWan10gRsTraceIdentifierMismatchAlarmSeverity,
				omtp12PlusWan10gAuAlarmIndicationSignalAlarmSeverity,
				omtp12PlusWan10gAuLossOfPointerAlarmSeverity,
				omtp12PlusWan10gMsAlarmIndicationSignalAlarmSeverity,
				omtp12PlusWan10gMsRemoteErrorIndicationAlarmSeverity,
				omtp12PlusWan10gMsRemoteDefectIndicationAlarmSeverity,
				omtp12PlusWan10gMsRemoteFailureIndicationAlarmSeverity,
				omtp12PlusWan10gMsB2ExcessiveErrorAlarmSeverity,
				omtp12PlusWan10gMsB2SignalDegradeAlarmSeverity,
				omtp12PlusWan10gLossOfSequenceSynchronisationAlarmSeverity,
				omtp12PlusWan10gHigherOrderPathPayloadLabelMismatchAlarmSeverity,
				omtp12PlusWan10gHigherOrderPathUnequippedAlarmSeverity,
				omtp12PlusLan10gLossOfSignalAlarmSeverity,
				omtp12PlusLan10gLossOfSignalSyncAlarmSeverity,
				omtp12PlusLan10gLinkFailureAlarmSeverity,
				omtp12PlusLan10gFrameCheckSequenceAlarmSeverity,
				omtp12PlusLan10gCarrierStatusAlarmSeverity,
				omtp12PlusLan10gHighBerAlarmSeverity,
				omtp12PlusLan10gLocalFaultAlarmSeverity,
				omtp12PlusLan10gRemoteFaultAlarmSeverity,
				omtp12PlusFcTransmitDisparityInversionDefectAlarmSeverity,
				omtp12PlusFcTransmitDigitalLossOfLinkDefectAlarmSeverity,
				omtp12PlusFcTrasnmitLossofSynchronizationDefectAlarmSeverity,
				omtp12PlusFcReceiveDigitalLossofLinkDefectAlarmSeverity,
				omtp12PlusFcReceiveLossofSynchronizationDefectAlarmSeverity,
				omtp12PlusFcReceiveTransitionDetectDefectAlarmSeverity,
				omtp12PlusFcReceiveAnalogLossofSignalDefectAlarmSeverity,
				omtp12PlusFcReceiveLineCodeViolationDefectAlarmSeverity,
				omtp12PlusGfpCsfSignalFailAlarmSeverity,
				omtp12PlusGfpCsfLinkFailAlarmSeverity,
				omtp12PlusGfpCoreHeaderErrorAlarmSeverity,
				omtp12PlusGfpExtentionHeaderErrorAlarmSeverity,
				omtp12PlusConfigurationTableRowStatus,
				omtp12PlusXfpInputPowerFailureAlarm,
				omtp12PlusXfpOutputPowerFailureAlarm,
				omtp12PlusXfpHighTemperatureAlarm,
				omtp12PlusXfpLowTemperatureAlarm,
				omtp12PlusXfpHighTemperatureWarning,
				omtp12PlusXfpLowTemperatureWarning,
				omtp12PlusXfpHighBiasCurrentAlarm,
				omtp12PlusXfpLowBiasCurrentAlarm,
				omtp12PlusXfpHighBiasCurrentWarning,
				omtp12PlusXfpLowBiasCurrentWarning,
				omtp12PlusXfpInputHighPowerAlarm,
				omtp12PlusXfpInputLowPowerAlarm,
				omtp12PlusXfpInputHighPowerWarning,
				omtp12PlusXfpInputLowPowerWarning,
				omtp12PlusXfpOutputHighPowerAlarm,
				omtp12PlusXfpOutputLowPowerAlarm,
				omtp12PlusXfpOutputHighPowerWarning,
				omtp12PlusXfpOutputLowPowerWarning,
				omtp12PlusXfpHighSupplyVoltageAlarm,
				omtp12PlusXfpLowSupplyVoltageAlarm,
				omtp12PlusXfpHighSupplyVoltageWarning,
				omtp12PlusXfpLowSupplyVoltageWarning,
				omtp12PlusXfpPresenceAbsenceNotification,
				omtp12PlusOtuLossOfSignalAlarm,
				omtp12PlusOtuLossOfFrameAlarm,
				omtp12PlusOtuOutOfFrameAlarm,
				omtp12PlusOtuLossOfMultiFrameAlarm,
				omtp12PlusOtuOutOfMultiFrameAlarm,
				omtp12PlusOtuSignalFailAlarm,
				omtp12PlusOtuSignalDegradeAlarm,
				omtp12PlusOtuAlarmIndicationSignalAlarm,
				omtp12PlusOtuIncomingAlignmentErrorAlarm,
				omtp12PlusOtuTraceIdentifierMismatchAlarm,
				omtp12PlusOtuBackwardIncomingAlignmentErrorAlarm,
				omtp12PlusOtuBackwardDefectIndicationAlarm,
				omtp12PlusOduSignalFailAlarm,
				omtp12PlusOduSignalDegradeAlarm,
				omtp12PlusOduAlarmIndicationSignalAlarm,
				omtp12PlusOduTcm1IncomingAlignmentErrorAlarm,
				omtp12PlusOduTcm2IncomingAlignmentErrorAlarm,
				omtp12PlusOduTcm3IncomingAlignmentErrorAlarm,
				omtp12PlusOduTcm4IncomingAlignmentErrorAlarm,
				omtp12PlusOduTcm5IncomingAlignmentErrorAlarm,
				omtp12PlusOduTcm6IncomingAlignmentErrorAlarm,
				omtp12PlusOduTraceIdentifierMismatchAlarm,
				omtp12PlusOduLockedDefectAlarm,
				omtp12PlusOduOpenConnectionIndicationAlarm,
				omtp12PlusOduBackwardDefectIndicationAlarm,
				omtp12PlusOduTcm1BackwardIncomingAlignmentErrorAlarm,
				omtp12PlusOduTcm2BackwardIncomingAlignmentErrorAlarm,
				omtp12PlusOduTcm3BackwardIncomingAlignmentErrorAlarm,
				omtp12PlusOduTcm4BackwardIncomingAlignmentErrorAlarm,
				omtp12PlusOduTcm5BackwardIncomingAlignmentErrorAlarm,
				omtp12PlusOduTcm6BackwardIncomingAlignmentErrorAlarm,
				omtp12PlusOpuPayloadMismatchAlarm,
				omtp12PlusOchLossOfPayloadAlarm,
				omtp12PlusSdhLossOfSignalAlarm,
				omtp12PlusSdhOutOfFrameAlarm,
				omtp12PlusSdhLossOfFrameAlarm,
				omtp12PlusSdhRsAlarmIndicationSignalAlarm,
				omtp12PlusSdhRsTraceIdentifierMismatchAlarm,
				omtp12PlusSdhAuAlarmIndicationSignalAlarm,
				omtp12PlusSdhAuLossOfPointerAlarm,
				omtp12PlusSdhMsAlarmIndicationSignalAlarm,
				omtp12PlusSdhMsRemoteErrorIndicationAlarm,
				omtp12PlusSdhMsRemoteDefectIndicationAlarm,
				omtp12PlusSdhMsRemoteFailureIndicationAlarm,
				omtp12PlusSdhMsB2ExcessiveErrorAlarm,
				omtp12PlusSdhMsB2SignalDegradeAlarm,
				omtp12PlusSdhLossOfSequenceSynchronisationAlarm,
				omtp12PlusSdhHigherOrderPathPayloadLabelMismatchAlarm,
				omtp12PlusSdhHigherOrderPathUnequippedAlarm,
				omtp12PlusWan10gLossOfSignalAlarm,
				omtp12PlusWan10gOutOfFrameAlarm,
				omtp12PlusWan10gLossOfFrameAlarm,
				omtp12PlusWan10gRsAlarmIndicationSignalAlarm,
				omtp12PlusWan10gRsTraceIdentifierMismatchAlarm,
				omtp12PlusWan10gAuAlarmIndicationSignalAlarm,
				omtp12PlusWan10gAuLossOfPointerAlarm,
				omtp12PlusWan10gMsAlarmIndicationSignalAlarm,
				omtp12PlusWan10gMsRemoteErrorIndicationAlarm,
				omtp12PlusWan10gMsRemoteDefectIndicationAlarm,
				omtp12PlusWan10gMsRemoteFailureIndicationAlarm,
				omtp12PlusWan10gMsB2ExcessiveErrorAlarm,
				omtp12PlusWan10gMsB2SignalDegradeAlarm,
				omtp12PlusWan10gLossOfSequenceSynchronisationAlarm,
				omtp12PlusWan10gHigherOrderPathPayloadLabelMismatchAlarm,
				omtp12PlusWan10gHigherOrderPathUnequippedAlarm,
				omtp12PlusLan10gLossOfSignalAlarm,
				omtp12PlusLan10gLossOfSignalSyncAlarm,
				omtp12PlusLan10gLinkFailureAlarm,
				omtp12PlusLan10gFrameCheckSequenceAlarm,
				omtp12PlusLan10gCarrierStatusAlarm,
				omtp12PlusLan10gHighBerAlarm,
				omtp12PlusLan10gLocalFaultAlarm,
				omtp12PlusLan10gRemoteFaultAlarm,
				omtp12PlusFcTransmitDisparityInversionDefectAlarm,
				omtp12PlusFcTransmitDigitalLossOfLinkDefectAlarm,
				omtp12PlusFcTrasnmitLossofSynchronizationDefectAlarm,
				omtp12PlusFcReceiveDigitalLossofLinkDefectAlarm,
				omtp12PlusFcReceiveLossofSynchronizationDefectAlarm,
				omtp12PlusFcReceiveTransitionDetectDefectAlarm,
				omtp12PlusFcReceiveAnalogLossofSignalDefectAlarm,
				omtp12PlusFcReceiveLineCodeViolationDefectAlarm,
				omtp12PlusGfpCsfSignalFailAlarm,
				omtp12PlusGfpCsfLinkFailAlarm,
				omtp12PlusGfpCoreHeaderErrorAlarm,
				omtp12PlusGfpExtentionHeaderErrorAlarm,
				omtp12PlusAlarmQueryTableRowStatus,
				omtp12PlusXfpInputPower,
				omtp12PlusXfpOutputPower,
				omtp12PlusXfpBiasCurrent,
				omtp12PlusXfpSupplyVoltage,
				omtp12PlusXfpTemperature,
				omtp12PlusOtnFecUncorrectedWords,
				omtp12PlusOtnFecCorrectedBits,
				omtp12PlusOtnFecZerosCorrectedBits,
				omtp12PlusOtnFecOnesCorrectedBits,
				omtp12PlusOtuBitInterleavedParityErrors,
				omtp12PlusOtuIncomingAlignmentErrorSeconds,
				omtp12PlusOtuBackwardErrorIndicationErrorCount,
				omtp12PlusOtuBackwardIncomingAlignmentErrorSeconds,
				omtp12PlusOtuErrorFreeSeconds,
				omtp12PlusOtuErrorSeconds,
				omtp12PlusOtuBackgroundBlockErrors,
				omtp12PlusOtuSevereErrorSeconds,
				omtp12PlusOtuUnavailableSeconds,
				omtp12PlusOtuBackgroundBlockErrorRatio,
				omtp12PlusOtuSevereErrorSecondsErrorRatio,
				omtp12PlusOtuFarEndErrorFreeSeconds,
				omtp12PlusOtuFarEndErrorSeconds,
				omtp12PlusOtuFarEndBackgroundBlockErrors,
				omtp12PlusOtuFarEndSevereErrorSeconds,
				omtp12PlusOtuFarEndUnavailableSeconds,
				omtp12PlusOtuFarEndBackgroundBlockErrorRatio,
				omtp12PlusOtuFarEndSevereErrorSecondsErrorRatio,
				omtp12PlusOtuErrorRatio,
				omtp12PlusOtuBitErrorRate,
				omtp12PlusOtuFramesReceived,
				omtp12PlusOduBitInterleavedParityErrors,
				omtp12PlusOduTcm1BitInterleavedParityErrors,
				omtp12PlusOduTcm2BitInterleavedParityErrors,
				omtp12PlusOduTcm3BitInterleavedParityErrors,
				omtp12PlusOduTcm4BitInterleavedParityErrors,
				omtp12PlusOduTcm5BitInterleavedParityErrors,
				omtp12PlusOduTcm6BitInterleavedParityErrors,
				omtp12PlusOduTcm1IncomingAlignmentErrorSeconds,
				omtp12PlusOduBackwardErrorIndicationErrorCount,
				omtp12PlusOduTcm1BackwardErrorIndicationErrorCount,
				omtp12PlusOduTcm2BackwardErrorIndicationErrorCount,
				omtp12PlusOduTcm3BackwardErrorIndicationErrorCount,
				omtp12PlusOduTcm4BackwardErrorIndicationErrorCount,
				omtp12PlusOduTcm5BackwardErrorIndicationErrorCount,
				omtp12PlusOduTcm6BackwardErrorIndicationErrorCount,
				omtp12PlusOduTcm1BackwardIncomingAlignmentErrorSeconds,
				omtp12PlusOduDelayMeasurement,
				omtp12PlusOduErrorFreeSeconds,
				omtp12PlusOduErrorSeconds,
				omtp12PlusOduBackgroundBlockErrors,
				omtp12PlusOduSevereErrorSeconds,
				omtp12PlusOduUnavailableSeconds,
				omtp12PlusOduBackgroundBlockErrorRatio,
				omtp12PlusOduSevereErrorSecondsErrorRatio,
				omtp12PlusOduFarEndErrorFreeSeconds,
				omtp12PlusOduFarEndErrorSeconds,
				omtp12PlusOduFarEndBackgroundBlockErrors,
				omtp12PlusOduFarEndSevereErrorSeconds,
				omtp12PlusOduFarEndUnavailableSeconds,
				omtp12PlusOduFarEndBackgroundBlockErrorRatio,
				omtp12PlusOduFarEndSevereErrorSecondsErrorRatio,
				omtp12PlusSdhRsB1BitInterleavedParityErrors,
				omtp12PlusSdhMsB2BitInterleavedParityErrors,
				omtp12PlusSdhMsB3BitInterleavedParityErrors,
				omtp12PlusSdhMsRemoteErrorIndicationErrorCount,
				omtp12PlusSdhMsRemoteDefectIndicationErrorCount,
				omtp12PlusSdhErrorFreeSeconds,
				omtp12PlusSdhErrorSeconds,
				omtp12PlusSdhBackgroundBlockErrors,
				omtp12PlusSdhSevereErrorSeconds,
				omtp12PlusSdhUnavailableSeconds,
				omtp12PlusSdhErrorSecondsErrorRatio,
				omtp12PlusSdhBackgroundBlockErrorRatio,
				omtp12PlusSdhSevereErrorSecondsErrorRatio,
				omtp12PlusWan10gRsB1BitInterleavedParityErrors,
				omtp12PlusWan10gMsB2BitInterleavedParityErrors,
				omtp12PlusWan10gMsB3BitInterleavedParityErrors,
				omtp12PlusWan10gMsRemoteErrorIndicationErrorCount,
				omtp12PlusWan10gMsRemoteDefectIndicationErrorCount,
				omtp12PlusWan10gErrorFreeSeconds,
				omtp12PlusWan10gErrorSeconds,
				omtp12PlusWan10gBackgroundBlockErrors,
				omtp12PlusWan10gSevereErrorSeconds,
				omtp12PlusWan10gUnavailableSeconds,
				omtp12PlusWan10gErrorSecondsErrorRatio,
				omtp12PlusWan10gBackgroundBlockErrorRatio,
				omtp12PlusWan10gSevereErrorSecondsErrorRatio,
				omtp12PlusLan10gMacTerminatedFramesTransmitted,
				omtp12PlusLan10gMacTerminatedFramesReceived,
				omtp12PlusLan10gMacTerminatedPauseFramesTransmitted,
				omtp12PlusLan10gMacTerminatedPauseFramesReceived,
				omtp12PlusLan10gMacTerminatedUnicastFramesTransmitted,
				omtp12PlusLan10gMacTerminatedUnicastFramesReceived,
				omtp12PlusLan10gMacTerminatedMulticastFramesTransmitted,
				omtp12PlusLan10gMacTerminatedMulticastFramesReceived,
				omtp12PlusLan10gMacTerminatedBroadcastFramesTransmitted,
				omtp12PlusLan10gMacTerminatedBroadcastFramesReceived,
				omtp12PlusLan10gMacTerminatedUnderSizeFramesTransmitted,
				omtp12PlusLan10gMacTerminatedUnderSizeFramesReceived,
				omtp12PlusLan10gMacTerminatedOverSizeFramesTransmitted,
				omtp12PlusLan10gMacTerminatedOverSizeFramesReceived,
				omtp12PlusLan10gMacTerminatedVlanTaggedFramesTransmitted,
				omtp12PlusLan10gMacTerminatedVlanTaggedFramesReceived,
				omtp12PlusLan10gMacTerminatedFrameSymbolErrorsReceived,
				omtp12PlusLan10gMacTerminatedFragmentFramesReceived,
				omtp12PlusLan10gMacTerminatedFrameCheckSequenceErrorsReceived,
				omtp12PlusLan10gMacTerminatedFramesReceivedWithNoDefect,
				omtp12PlusLan10gMacTerminatedBytesTransmitted,
				omtp12PlusLan10gMacTerminatedBytesReceived,
				omtp12PlusLan10gMacTerminatedControlFramesTransmitted,
				omtp12PlusLan10gMacTerminatedControlFramesReceived,
				omtp12PlusLan10gTransparentTransmitLcvCount,
				omtp12PlusLan10gTransparentTransmitPropagationErrorDeletionCount,
				omtp12PlusLan10gTransparentTransmitIdleDeletionCount,
				omtp12PlusLan10gTransparentTransmitConfDeletionCount,
				omtp12PlusLan10gTransparentTransmitPropagationInsertionCount,
				omtp12PlusLan10gTransparentTransmitIdleInsertionCount,
				omtp12PlusLan10gTransparentTransmitConfInsertionCount,
				omtp12PlusLan10gTransparentReceiveLcvCount,
				omtp12PlusLan10gTransparentReceivePropagationErrorDeletionCount,
				omtp12PlusLan10gTransparentReceiveIdleDeletionCount,
				omtp12PlusLan10gTransparentReceiveConfDeletionCount,
				omtp12PlusLan10gTransparentReceivePacketDeletionCount,
				omtp12PlusGfpCoreHeaderErrorCount,
				omtp12PlusGfpExtentionHeaderErrorCount,
				omtp12PlusGfpFrameCountWithSingleBitError,
				omtp12PlusGfpTypeHeaderErrorCount,
				omtp12PlusGfpReceiveDropFrameCount,
				omtp12PlusGfpReceiveExtensionHeaderIdentifierFilterDropCount,
				omtp12PlusFcTransmitWordCount,
				omtp12PlusFcTransmitBadCrc,
				omtp12PlusFcTransmitTotalPackets,
				omtp12PlusFcTransmitLcvCount,
				omtp12PlusFcReceiveWordCount,
				omtp12PlusFcReceiveBadCrc,
				omtp12PlusFcReceiveTotalPackets,
				omtp12PlusFcReceiveLcvCount,
				omtp12PlusFcTransmitFillWordInsertionCount,
				omtp12PlusFcTransmitPrimitiveSequenceInsertionCount,
				omtp12PlusFcTransmitFillWordDeletionCount,
				omtp12PlusFcTransmitPrimitiveSequenceDeletionCount,
				omtp12PlusPerformanceTableRowStatus,
				omtp12PlusDiagnosticTableRowStatus,
				omtp12PlusAccessCortinaRegister,
				omtp12PlusCollectCortinaRegisterDump,
				omtp12PlusCollectCortinaModulebGpllRxLockStatus,
				omtp12PlusCollectCortinaModulebGpllTxLockStatus,
				omtp12PlusCollectCortinaModulebTxSerdesLockStatus,
				omtp12PlusCollectCortinaModulebTxSerdesVcoTunedValue,
				omtp12PlusCollectCortinaModulebXfiCupllLockStatus,
				omtp12PlusCollectCortinaModulebAllClockLockStatus
		}
		STATUS  current
		DESCRIPTION
	    		"A collection of objects from RFC 1213 made current by this MIB module."
		::= { utlrnd 2 }

END

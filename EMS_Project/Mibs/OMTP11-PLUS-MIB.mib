--*****************************************************************************
--			MIB FILE FOR THE OMTP11-PLUS CARD
--*****************************************************************************

	OMTP11-PLUS-MIB DEFINITIONS ::= BEGIN

	IMPORTS

	RowStatus                               FROM STANDARD-MIB
	DisplayString                           FROM RFC1213-MIB
	   
	OBJECT-IDENTITY, 
	NOTIFICATION-TYPE, 
	MODULE-IDENTITY, 
	Integer32, 
	Unsigned32,
	IpAddress,

	TimeTicks		                FROM SNMPv2-SMI
	OBJECT-TYPE                             FROM RFC-1212

	MODULE-COMPLIANCE, 
	OBJECT-GROUP, 
	NOTIFICATION-GROUP                      FROM SNMPv2-CONF

	node, 
	rack, 
	subRack, 
	slot                                    FROM SCC-MIB 

	enterprises                             FROM RFC1155-SMI		

	;

	utl   MODULE-IDENTITY
		LAST-UPDATED    	"1807130630Z"
		ORGANIZATION    	"United Telecoms Limited, Bangalore-560048."
		CONTACT-INFO    	"Website: http://www.utlindia.com."                                           
		DESCRIPTION     	"MIB module for NFS."
		REVISION 	    	"1807130630Z"
		DESCRIPTION    	    	"MIB module for OMTP11-PLUS Card."
		::= { enterprises 18036 }

	utlrnd  OBJECT-IDENTITY
		STATUS  current
		DESCRIPTION "UTL Research and Development."
		::= { utl 1 }

	dwdm OBJECT IDENTIFIER				::=	{ utlrnd 1 }
	indus OBJECT IDENTIFIER				::=	{ dwdm 1 }
	omtp11Plus OBJECT IDENTIFIER 			::=	{ indus 71 }

	omtp11PlusCardGeneralDetails OBJECT IDENTIFIER	::=	{ omtp11Plus 1 }
	omtp11PlusConfiguration OBJECT IDENTIFIER	::=	{ omtp11Plus 2 }
	omtp11PlusAlarm OBJECT IDENTIFIER		::=	{ omtp11Plus 3 }
	omtp11PlusPerformance OBJECT IDENTIFIER		::=	{ omtp11Plus 4 }
	omtp11PlusDiagnostics OBJECT IDENTIFIER 	::=	{ omtp11Plus 5 }
	
	omtp11PlusAlarmQuery OBJECT IDENTIFIER		::=	{ omtp11PlusAlarm 1 }
	omtp11PlusAlarmNotification OBJECT IDENTIFIER	::=	{ omtp11PlusAlarm 2 }

--*****************************************************************************
--				   CARD GENERAL DETAILS
--*****************************************************************************

	omtp11PlusCardGeneralDetailsTable OBJECT-TYPE
		SYNTAX SEQUENCE OF Omtp11PlusCardGeneralDetailsEntry
		MAX-ACCESS not-accessible
		STATUS current
		DESCRIPTION
			"Contains card general details' queries for the OMTP11-PLUS card"
		::= { omtp11PlusCardGeneralDetails 1 }

	omtp11PlusCardGeneralDetailsEntry OBJECT-TYPE
		SYNTAX Omtp11PlusCardGeneralDetailsEntry
		MAX-ACCESS not-accessible
		STATUS current
		DESCRIPTION
			""				  	
		INDEX   { node, rack , subRack , slot , omtp11PlusInterfaceNumber}
		::= { omtp11PlusCardGeneralDetailsTable 1 }

	Omtp11PlusCardGeneralDetailsEntry ::= 
		SEQUENCE { 
				omtp11PlusInterfaceNumber					INTEGER,
				omtp11PlusEepromCardId					        INTEGER,
				omtp11PlusEepromCardName					DisplayString,
				omtp11PlusEepromPartCode					DisplayString,
				omtp11PlusEepromCardSerialNumber				DisplayString,
				omtp11PlusEepromHardwareExternalReleaseVersion		        DisplayString,
				omtp11PlusSoftwareExternalReleaseVersion		        DisplayString,
				omtp11PlusEepromHardwareInternalReleaseVersion		        DisplayString,
				omtp11PlusSoftwareInternalReleaseVersion		        DisplayString,
				omtp11PlusEepromCardUidNumber			                DisplayString,
				omtp11PlusEepromCardEui48Number				        DisplayString,
				omtp11PlusEepromCardEui64Number				        DisplayString,
				omtp11PlusCardRootFileSystemVersion				DisplayString,
				omtp11PlusCardInstallationDate				        DisplayString,
				omtp11PlusCardCommissionDate				        DisplayString,
				omtp11PlusCardRunningTime					DisplayString,
				omtp11PlusCardRestartCount					INTEGER,
				omtp11PlusXfpReadyForOperation				        INTEGER,
				omtp11PlusXfpI2cCommunicationStatus				INTEGER,
				omtp11PlusXfpEepromPage					        INTEGER,
				omtp11PlusCheckCodeOfXfpEepromPage				INTEGER,
				omtp11PlusExtendedCheckCodeOfXfpEepromPage			INTEGER,
				omtp11PlusXfpVendorName					        DisplayString,
				omtp11PlusXfpVendorIeeeId					DisplayString,
				omtp11PlusXfpPartNumber					        DisplayString,
				omtp11PlusXfpSerialNumber					DisplayString,
				omtp11PlusXfpRevisionNumber					DisplayString,
				omtp11PlusXfpManufacturingDate				        DisplayString,
				omtp11PlusFixedXfpLaserWavelength				DisplayString,
				omtp11PlusXfpLaserWavelengthTolerance				DisplayString,
				omtp11PlusXfpWavelengthTunabilitySupported			INTEGER,
				omtp11PlusTunableXfpLaserWavelengthError			DisplayString,
				omtp11PlusTunableXfpLaserFrequencyError			        DisplayString,
				omtp11PlusTunableXfpLaserFirstFrequency			        DisplayString,
				omtp11PlusTunableXfpLaserLastFrequency			        DisplayString,
				omtp11PlusTunableXfpWavelengthGridSpacing			DisplayString,
				omtp11PlusXfpConnectorType					DisplayString,
				omtp11PlusXfpLinkLength					        DisplayString,
				omtp11PlusXfpCdrRateSupported				        INTEGER,
				omtp11PlusXfpSignalEncodingTypeSupported			INTEGER,
				omtp11PlusXfpTransceiverCodesSupported			        INTEGER,
				omtp11PlusXfpMaximumBitrateSupported			        DisplayString,
				omtp11PlusXfpMinimumBitrateSupported			        DisplayString,
				omtp11PlusXfpMaximumCaseTemperatureSupported		        INTEGER,
				omtp11PlusXfpMaximumPowerDissipationSupported			INTEGER,
				omtp11PlusXfpMaximumPowerDissipationSupportedAtPowerDownMode	INTEGER,
				omtp11PlusXfpMaximumCurrentLimitSupportedAtPlus5vSupply		INTEGER,
				omtp11PlusXfpMaximumCurrentLimitSupportedAtPlus3Point3vSupply	INTEGER,
				omtp11PlusXfpMaximumCurrentLimitSupportedAtPlus1Point8vSupply	INTEGER,
				omtp11PlusXfpMaximumCurrentLimitSupportedAtMinus5Point2vSupply	INTEGER,
				omtp11PlusXfpLineLoopbackSupported				INTEGER,
				omtp11PlusXfpXfiLoopbackSupported				INTEGER,
				omtp11PlusXfpOptionalVpsSupported				INTEGER,
				omtp11PlusXfpLaserDisableThroughI2cSupported			INTEGER,
				omtp11PlusXfpPowerDownThroughI2cSupported			INTEGER,
				omtp11PlusXfpVpsLvRegulatorModeSupported			INTEGER,
				omtp11PlusXfpVpsBypassedRegulatorModeSupported			INTEGER,
				omtp11PlusXfpActiveFecControlSupported				INTEGER,
				omtp11PlusXfpOptionalCmuModeSupported				INTEGER,
				omtp11PlusXfpFecBerSupported					INTEGER,
				omtp11PlusXfpReceivePowerMeasurementIsInOmaOrAverage		INTEGER,
				omtp11PlusXfpActiveWavelengthControlSupported			INTEGER,
				omtp11PlusXfpTransmitterIsCooledOrUncooled			INTEGER,
				omtp11PlusXfpReceiverTypeIsPinOrApd				INTEGER,
				omtp11PlusCardGeneralDetailsTableRowStatus			RowStatus
		}

	omtp11PlusInterfaceNumber OBJECT-TYPE
		SYNTAX INTEGER
		MAX-ACCESS not-accessible
		STATUS current
		DESCRIPTION
			"Interface number represents the port number
			InterfaceNumber to port mapping is as follows:
			1 - CLIENT-1
			2 - LINE-1
			-----------------------------
			For properties which do not apply on any interface,
			the interface number must be passed as 0
			-----------------------------"

		::= { omtp11PlusCardGeneralDetailsEntry 1 }
		
	omtp11PlusEepromCardId OBJECT-TYPE
		SYNTAX INTEGER
		MAX-ACCESS read-only
		STATUS current
		DESCRIPTION
			"Tells the card ID of the OMTP11-PLUS card, present in the EEPROM
			-----------------------------
			omtp11PlusInterfaceNumber: 0
			-----------------------------"
		::= { omtp11PlusCardGeneralDetailsEntry 2 }
		
	omtp11PlusEepromCardName OBJECT-TYPE
		SYNTAX DisplayString
		MAX-ACCESS read-only
		STATUS current
		DESCRIPTION
			"Tells the card name of the OMTP11-PLUS card, present in the EEPROM
			-----------------------------
			omtp11PlusInterfaceNumber: 0
			-----------------------------"
		::= { omtp11PlusCardGeneralDetailsEntry 3 }
		
	omtp11PlusEepromPartCode OBJECT-TYPE
		SYNTAX DisplayString
		MAX-ACCESS read-only
		STATUS current
		DESCRIPTION
			"Tells the part code of the OMTP11-PLUS card, present in the EEPROM
			-----------------------------
			omtp11PlusInterfaceNumber: 0
			-----------------------------"
		::= { omtp11PlusCardGeneralDetailsEntry 4 }
		
	omtp11PlusEepromCardSerialNumber OBJECT-TYPE
		SYNTAX DisplayString
		MAX-ACCESS read-write
		STATUS current
		DESCRIPTION
			"This property get / set the information about 
			OMTP11-PLUS Card's Serial Number.
			-----------------------------
			omtp11PlusInterfaceNumber: 0
			-----------------------------
			Values:
			eg: 123456
			-----------------------------"
		::= { omtp11PlusCardGeneralDetailsEntry 5 }
		
	omtp11PlusEepromHardwareExternalReleaseVersion OBJECT-TYPE
		SYNTAX DisplayString
		MAX-ACCESS read-only
		STATUS current
		DESCRIPTION
			"Get the Card's Hardware External Release Version. 
			This detail will be displayed to the customer.
			This version will increment only if there are significant
			architectural changes in the product
			-----------------------------
			omtp11PlusInterfaceNumber: 0
			-----------------------------
			Values:
			eg: 0.1
			-----------------------------"
		::= { omtp11PlusCardGeneralDetailsEntry 6 }
		
	omtp11PlusSoftwareExternalReleaseVersion OBJECT-TYPE
		SYNTAX DisplayString
		MAX-ACCESS read-only
		STATUS current
		DESCRIPTION
			"Get the Card's Software External Release Version. 
			This detail will be displayed to the customer.
			This version will increment only if there are
			significant architectural changes in the product
			-----------------------------
			omtp11PlusInterfaceNumber: 0
			-----------------------------
			Values:
			eg: 0.1
			-----------------------------"
		::= { omtp11PlusCardGeneralDetailsEntry 7 }
		
	omtp11PlusEepromHardwareInternalReleaseVersion OBJECT-TYPE
		SYNTAX DisplayString
		MAX-ACCESS read-only
		STATUS current
		DESCRIPTION
			"Get the Card's Hardware Internal Release Version.
			This detail is used for development purposes only.
			It differs from the external hardware version.
			-----------------------------
			omtp11PlusInterfaceNumber: 0
			-----------------------------
			Values:
			eg: 4.1
			-----------------------------"
		::= { omtp11PlusCardGeneralDetailsEntry 8 }
		
	omtp11PlusSoftwareInternalReleaseVersion OBJECT-TYPE
		SYNTAX DisplayString
		MAX-ACCESS read-only
		STATUS current
		DESCRIPTION
			"Gets the Card's Software Internal Release Version.
			This detail is used for development purposes only.
			It differs from the external software version.
		      	-----------------------------
			omtp11PlusInterfaceNumber: 0
			-----------------------------
			Values:
			eg: 5.1
			-----------------------------"
		::= { omtp11PlusCardGeneralDetailsEntry 9 }
		
	omtp11PlusEepromCardUidNumber OBJECT-TYPE
		SYNTAX DisplayString
		MAX-ACCESS read-only
		STATUS current
		DESCRIPTION
			"Tells the Card Unique IDentifier. It is a 4 byte
			address used to uniquely identify a card.
			----------------------------
			omtp11PlusInterfaceNumber: 0
			------------------------------
			Values:
		      	eg: 12345678
			-----------------------------"
		::= { omtp11PlusCardGeneralDetailsEntry 10 }
		
	omtp11PlusEepromCardEui48Number OBJECT-TYPE
		SYNTAX DisplayString
		MAX-ACCESS read-only
		STATUS current
		DESCRIPTION
			"Tells the Card EUI-48 Number. It’s a 6 byte address
			used to uniquely identify a card.
			-----------------------------
			omtp11PlusInterfaceNumber: 0
			-----------------------------
			Values:
		      	eg: 0004A3123456
			-----------------------------"
		::= { omtp11PlusCardGeneralDetailsEntry 11 }
		
	omtp11PlusEepromCardEui64Number OBJECT-TYPE
		SYNTAX DisplayString
		MAX-ACCESS read-only
		STATUS current
		DESCRIPTION
			"Tells the Card EUI-64 Number. It’s a 8 byte address
			used to uniquely identify a card.
			-----------------------------
			omtp11PlusInterfaceNumber: 0
			-----------------------------
			Values:
		      	eg: 0004A31234567890
			-----------------------------"
		::= { omtp11PlusCardGeneralDetailsEntry 12 }
		
        omtp11PlusCardRootFileSystemVersion OBJECT-TYPE		 
		SYNTAX  DisplayString
		MAX-ACCESS  read-only
		STATUS current
		DESCRIPTION
			"Tells the Card's Root File System Version
			-----------------------------
			omtp11PlusInterfaceNumber: 0
			-----------------------------
			Value:
		      	eg: 8
			-----------------------------"
		::= { omtp11PlusCardGeneralDetailsEntry 13 }
		
	omtp11PlusCardInstallationDate OBJECT-TYPE
		SYNTAX DisplayString
		MAX-ACCESS read-write
		STATUS current
		DESCRIPTION
			"Get the card's installation date in
			dd/mm/yyyy format
			-----------------------------
			omtp11PlusInterfaceNumber: 0
			-----------------------------
			Values:
		      	eg: 12/03/2016
			-----------------------------"
		::= { omtp11PlusCardGeneralDetailsEntry 21 }

	omtp11PlusCardCommissionDate OBJECT-TYPE
		SYNTAX DisplayString
		MAX-ACCESS read-write
		STATUS current
		DESCRIPTION
			"Get the card's commission date in
			dd/mm/yyyy format
			-----------------------------
			omtp11PlusInterfaceNumber: 0
			-----------------------------
			Values:
		      	eg: 20/03/2016
			-----------------------------"
		::= { omtp11PlusCardGeneralDetailsEntry 22 }

	omtp11PlusCardRunningTime OBJECT-TYPE
		SYNTAX DisplayString
		MAX-ACCESS read-only
		STATUS current
		DESCRIPTION
			"Get the duration of time for which the card is
			operational/running
			-----------------------------
			omtp11PlusInterfaceNumber: 0
			-----------------------------
			Values:
		      	eg: 3d 2h 1m
			-----------------------------"
		::= { omtp11PlusCardGeneralDetailsEntry 23 }
		
	omtp11PlusCardRestartCount OBJECT-TYPE
		SYNTAX INTEGER
		MAX-ACCESS read-only
		STATUS current
		DESCRIPTION
			"Get the number of times the card has been soft reset.
			This value will get reset to 0 on factory reset.
			-----------------------------
			omtp11PlusInterfaceNumber: 0
			-----------------------------
			Values:
		      	eg: 10
			-----------------------------"
		::= { omtp11PlusCardGeneralDetailsEntry 24 }
		
	omtp11PlusXfpReadyForOperation OBJECT-TYPE
		SYNTAX INTEGER
		MAX-ACCESS read-only
		STATUS current
		DESCRIPTION
			"Module not ready indicates that the XFP
			has detected a condition that tells
			transmit or receive data is invalid.
			It shall consist of logical OR of the
			following signals:
			> Transmit Signal Conditioner Loss of Lock
			> Transmitter Laser Fault
			> Receiver Signal Conditioner Loss of Lock
			(Ref: INF-8077 2.4.1)
			-----------------------------
			omtp11PlusInterfaceNumber:
			1 - CLIENT-1
			2 - LINE-1
			-----------------------------
			Values:		
			1 - XFP is ready for operation 
			0 - XFP is not ready for operation
			-----------------------------"
		::= { omtp11PlusCardGeneralDetailsEntry 31 }
		
	omtp11PlusXfpI2cCommunicationStatus OBJECT-TYPE
		SYNTAX INTEGER
		MAX-ACCESS read-write
		STATUS current
		DESCRIPTION
			"Tells whether the XFP can be accessed
			on a single 2-wire interface bus or not.
			(Ref: INF-8077 2.4.2)
			-----------------------------
			omtp11PlusInterfaceNumber:
			1 - CLIENT-1
			2 - LINE-1
			-----------------------------
			Values:			
			1 - Enable I2C communication for XFP
				i.e. the XFP responds to 2-wire serial
				communication commands.
			0 - Disable I2C communication for XFP
				i.e. the XFP will not respond to or
				acknowledge any 2-wire interface communication
				from the host.
			-----------------------------"
		::= { omtp11PlusCardGeneralDetailsEntry 32 }
		
	omtp11PlusXfpEepromPage OBJECT-TYPE
		SYNTAX INTEGER
		MAX-ACCESS read-write
		STATUS current
		DESCRIPTION
			"This property sets/gets the XFP EEPROM page, 
			the value represents the XFP EEPROM page number.
			-----------------------------
			omtp11PlusInterfaceNumber:
			1 - CLIENT-1
			2 - LINE-1
			-----------------------------
			Values:			
			eg: 1(EEPROM Page number)
			-----------------------------"
		::= { omtp11PlusCardGeneralDetailsEntry 33 }
		
	omtp11PlusCheckCodeOfXfpEepromPage OBJECT-TYPE
		SYNTAX INTEGER
		MAX-ACCESS read-only
		STATUS current
		DESCRIPTION
			"This property provides the XFP
			check code(checksum) value for bytes 128 to 190
			present in XFP EEPROM Page number 1. 
			-----------------------------
			omtp11PlusInterfaceNumber:
			1 - CLIENT-1
			2 - LINE-1
			-----------------------------
			Values:			
			eg: 1(EEPROM Page number)
			-----------------------------"
		::= { omtp11PlusCardGeneralDetailsEntry 34 }
		
	omtp11PlusExtendedCheckCodeOfXfpEepromPage OBJECT-TYPE
		SYNTAX INTEGER
		MAX-ACCESS read-only
		STATUS current
		DESCRIPTION
			"This property provides the XFP
			extended check code(checksum) value for bytes 192 to 222
			present in XFP EEPROM Page number 1. 
			-----------------------------
			omtp11PlusInterfaceNumber:
			1 - CLIENT-1
			2 - LINE-1
			-----------------------------
			Values:			
			eg: 1(EEPROM Page number)
			-----------------------------"
		::= { omtp11PlusCardGeneralDetailsEntry 35 }
		
	omtp11PlusXfpVendorName OBJECT-TYPE
		SYNTAX DisplayString
		MAX-ACCESS read-only
		STATUS current
		DESCRIPTION
			"This property provides Vendor Name for given XFP. 
			The vendor name shall be the full name of the 
			corporation, a commonly accepted abbreviation of 
			the name of the corporation, the SCSI company code
			for the corporation, or the stock exchange code for
			the corporation.
			-----------------------------
			omtp11PlusInterfaceNumber:
			1 - CLIENT-1
			2 - LINE-1
			-----------------------------
			Values:			
			eg: WTD
			-----------------------------"
		::= { omtp11PlusCardGeneralDetailsEntry 36 }
		
	omtp11PlusXfpVendorIeeeId OBJECT-TYPE
		SYNTAX DisplayString
		MAX-ACCESS read-only
		STATUS current
		DESCRIPTION
			"This property defines the IEEE company Identifier for
			the vendor of XFP. A value of all zero in the 3-byte
			field indicates that the Vendor OUI is unspecified.
			-----------------------------
			omtp11PlusInterfaceNumber:
			1 - CLIENT-1
			2 - LINE-1
			-----------------------------
			Values:			
			eg: 010
			-----------------------------"
		::= { omtp11PlusCardGeneralDetailsEntry 37 }
		
	omtp11PlusXfpPartNumber OBJECT-TYPE
		SYNTAX DisplayString
		MAX-ACCESS read-only
		STATUS current
		DESCRIPTION
			"This property defines the vendor part number or
			product name of the XFP. A value of all zero
			indicates that the vendor Part Number is unspecified.
			-----------------------------
			omtp11PlusInterfaceNumber:
			1 - CLIENT-1
			2 - LINE-1
			-----------------------------
			Values:			
			eg: FTRX-1811-2D2
			-----------------------------"
		::= { omtp11PlusCardGeneralDetailsEntry 38 }
		
	omtp11PlusXfpSerialNumber OBJECT-TYPE
		SYNTAX DisplayString
		MAX-ACCESS read-only
		STATUS current
		DESCRIPTION
			"This property provides vendor serial number defining
			the vendor’s serial number for the XFP. A value of all
			zero in the 16-byte field indicates that the vendor
			serial number is unspecified.
			-----------------------------
			omtp11PlusInterfaceNumber:
			1 - CLIENT-1
			2 - LINE-1
			-----------------------------
			Values:			
			eg: KBG02CU
			-----------------------------"
		::= { omtp11PlusCardGeneralDetailsEntry 39 }
		
	omtp11PlusXfpRevisionNumber OBJECT-TYPE
		SYNTAX DisplayString
		MAX-ACCESS read-only
		STATUS current
		DESCRIPTION
			"The vendor revision number defining the vendor’s
			 product revision number. A value of all zero indicates
			 that the vendor revision number is unspecified
			-----------------------------
			omtp11PlusInterfaceNumber:
			1 - CLIENT-1
			2 - LINE-1
			-----------------------------
			Values:			
			eg: RT
			-----------------------------"
		::= { omtp11PlusCardGeneralDetailsEntry 40 }
		
	omtp11PlusXfpManufacturingDate OBJECT-TYPE
		SYNTAX DisplayString
		MAX-ACCESS read-only
		STATUS current
		DESCRIPTION
			"This property defines the manufacturing date for 
			XFP. A value of 8-byte field in ASCII which represents
			year, month and date of each two bytes. 
			Extra two bytes may be blank
			-----------------------------
			omtp11PlusInterfaceNumber:
			1 - CLIENT-1
			2 - LINE-1
			-----------------------------
			Values:			
			eg: 160224
			-----------------------------"
		::= { omtp11PlusCardGeneralDetailsEntry 41 }
		
	omtp11PlusFixedXfpLaserWavelength OBJECT-TYPE
		SYNTAX DisplayString
		MAX-ACCESS read-only
		STATUS current
		DESCRIPTION
			"This property provides transmitter LASER wavelength(nm)
			of the XFP
			-----------------------------
			omtp11PlusInterfaceNumber:
			1 - CLIENT-1
			2 - LINE-1
			-----------------------------
			Values:			
			eg: 1310
			-----------------------------"
		::= { omtp11PlusCardGeneralDetailsEntry 42 }
		
	omtp11PlusXfpLaserWavelengthTolerance OBJECT-TYPE
		SYNTAX DisplayString
		MAX-ACCESS read-only
		STATUS current
		DESCRIPTION
			"This property provides XFP wavelength tolerance in GhZ
			-----------------------------
			omtp11PlusInterfaceNumber:
			1 - CLIENT-1
			2 - LINE-1
			-----------------------------
			Values:			
			eg: 0.02
			-----------------------------"
		::= { omtp11PlusCardGeneralDetailsEntry 43 }
		
	omtp11PlusXfpWavelengthTunabilitySupported OBJECT-TYPE
		SYNTAX INTEGER
		MAX-ACCESS read-only
		STATUS current
		DESCRIPTION
			"This property provides information whether the XFP
			supports wavelength tunability or not.
			-----------------------------
			omtp11PlusInterfaceNumber:
			1 - CLIENT-1
			2 - LINE-1
			-----------------------------
			Values:			
			1 - XFP supports wavelength tunability
			0 - XFP not supports wavelength tunability
			-----------------------------"
		::= { omtp11PlusCardGeneralDetailsEntry 44 }

	omtp11PlusTunableXfpLaserWavelengthError OBJECT-TYPE
		SYNTAX DisplayString
		MAX-ACCESS read-only
		STATUS current
		DESCRIPTION
			"This property provides wavelength error in pm
			-----------------------------
			omtp11PlusInterfaceNumber:
			1 - CLIENT-1
			2 - LINE-1
			-----------------------------
			Values:			
			eg: 0.02
			-----------------------------"
		::= { omtp11PlusCardGeneralDetailsEntry 45 }
		
	omtp11PlusTunableXfpLaserFrequencyError OBJECT-TYPE
		SYNTAX DisplayString
		MAX-ACCESS read-only
		STATUS current
		DESCRIPTION
			"This property defines the monitor of current frequency
			Error of XFP. Frequency error is reported in Ghz.
			-----------------------------
			omtp11PlusInterfaceNumber:
			1 - CLIENT-1
			2 - LINE-1
			-----------------------------
			Values:			
			eg: 0.03
			-----------------------------"
		::= { omtp11PlusCardGeneralDetailsEntry 46 }
		
	omtp11PlusTunableXfpLaserFirstFrequency OBJECT-TYPE
		SYNTAX DisplayString
		MAX-ACCESS read-only
		STATUS current
		DESCRIPTION
			"This property defines the first LASER frequency of XFP.
			The two byte value is specified in units of THz.
			-----------------------------
			omtp11PlusInterfaceNumber:
			1 - CLIENT-1
			2 - LINE-1
			-----------------------------
			Values:			
			eg: 1529.45
			-----------------------------"
		::= { omtp11PlusCardGeneralDetailsEntry 47 }
		
	omtp11PlusTunableXfpLaserLastFrequency OBJECT-TYPE
		SYNTAX DisplayString
		MAX-ACCESS read-only
		STATUS current
		DESCRIPTION
			"This property defines the last laser frequency of XFP.
		 	 The two byte value is specified in units of THz.
			-----------------------------
			omtp11PlusInterfaceNumber:
			1 - CLIENT-1
			2 - LINE-1
			-----------------------------
			Values:			
			eg: 1563.45
			-----------------------------"
		::= { omtp11PlusCardGeneralDetailsEntry 48 }
		
	omtp11PlusTunableXfpWavelengthGridSpacing OBJECT-TYPE
		SYNTAX DisplayString
		MAX-ACCESS read-only
		STATUS current
		DESCRIPTION
			"This property gives difference in the wavelength
			between two channels In GhZ
			-----------------------------
			omtp11PlusInterfaceNumber:
			1 - CLIENT-1
			2 - LINE-1
			-----------------------------
			Values:
			eg: 50
			-----------------------------"
		::= { omtp11PlusCardGeneralDetailsEntry 49 }
		
	omtp11PlusXfpConnectorType OBJECT-TYPE
		SYNTAX DisplayString
		MAX-ACCESS read-only
		STATUS current
		DESCRIPTION
			"This property provides information of the XFP
			connector, value indicates the external connector
			provided on the XFP.
			-----------------------------
			omtp11PlusInterfaceNumber:
			1 - CLIENT-1
			2 - LINE-1
			-----------------------------
			Values:
			00h 	Unknown or unspecified
			01h 	SC
			02h 	Fibre Channel Style 1 copper connector
			03h 	Fibre Channel Style 2 copper connector
			04h 	BNC/TNC
			05h 	Fibre Channel coaxial headers
			06h 	FiberJack
			07h 	LC
			08h 	MT-RJ
			09h 	MU
			0Ah 	SG
			0Bh 	Optical pigtail
			0C-1Fh 	Reserved
			20h 	HSSDC II
			21h 	Copper Pigtail
			22h-7Fh Reserved
			80-FFh 	Vendor specific
			-----------------------------"
		::= { omtp11PlusCardGeneralDetailsEntry 50 }
		
	omtp11PlusXfpLinkLength OBJECT-TYPE
		SYNTAX DisplayString
		MAX-ACCESS read-only
		STATUS current
		DESCRIPTION
			"This property provides link length suported by the XFP
			-----------------------------
			omtp11PlusInterfaceNumber:
			1 - CLIENT-1
			2 - LINE-1
			-----------------------------
			Values:
			eg: 80.00
			-----------------------------"
		::= { omtp11PlusCardGeneralDetailsEntry 51 }
		
	omtp11PlusXfpCdrRateSupported OBJECT-TYPE
		SYNTAX INTEGER
		MAX-ACCESS read-only
		STATUS current
		DESCRIPTION
			"This property indicates which rates are supported by
			the CDR present in XFP.
			-----------------------------
			omtp11PlusInterfaceNumber:
			1 - CLIENT-1
			2 - LINE-1
			-----------------------------
			Values:

			Return value 1-Byte represetation:
			Byte-1  CDR Rates
			Bit-7	9.95 Gb/s
			Bit-6	10.3 Gb/s
			Bit-5	10.5 Gb/s
			Bit-4	10.7 Gb/s
			Bit-3	11.1 Gb/s
			Bit-2	Reserved
			Bit-1	Dont care for this property
			Bit-0	Dont care for this property
			-----------------------------"
		::= { omtp11PlusCardGeneralDetailsEntry 52 }
		
	omtp11PlusXfpSignalEncodingTypeSupported OBJECT-TYPE
		SYNTAX INTEGER
		MAX-ACCESS read-only
		STATUS current
		DESCRIPTION
			"This property indicates the serial encoding mechanisms
			that are supported by the XFP.
			-----------------------------
			omtp11PlusInterfaceNumber:
			1 - CLIENT-1
			2 - LINE-1
			-----------------------------
			Values:

			Return value 1-Byte represetation:
			Byte-1  Encoding Type
			Bit-7	64B/66B          
			Bit-6	8B10B     	 	 
			Bit-5	SONET Scrambled  
			Bit-4	NRZ              
			Bit-3	RZ              
			Bit-2	Reserved        
			Bit-1	Reserved         
			Bit-0	Reserved 
			-----------------------------"
		::= { omtp11PlusCardGeneralDetailsEntry 53 }
		
	omtp11PlusXfpTransceiverCodesSupported OBJECT-TYPE
		SYNTAX INTEGER
		MAX-ACCESS read-only
		STATUS current
		DESCRIPTION
			"The identifier value specifies which transceiver
			codes are supported by the XFP
			-----------------------------
			omtp11PlusInterfaceNumber:
			1 - CLIENT-1
			2 - LINE-1
			-----------------------------
			Values:

			Return value 8-Byte represetation:
			---------------------------------------------------------------------------------------------------------------------------------------
				  Byte-1	  Byte-2	          Byte-3	  Byte-4	          Byte-5    Byte-6    Byte-7	        Byte-8
			---------------------------------------------------------------------------------------------------------------------------------------
			Bit-7	 10GBASE-SR	 1200-MX-SN-I        	 Reserved	 1000BASE-SX/1xFC MMF	 I-64.1r   S-64.1    L-64.1	       V-64.2a
			Bit-6	 10GBASE-LR	 1200-SM-LL-L	         Reserved	 1000BASE-LX/1xFC-SMF	 I-64.1	   S-64.2a   L-64.2a	       V-64.2b
			Bit-5	 10GBASE-ER	 Extended 1550 nm	 Reserved	 2xFC-MMF/2xFC-SMF	 I-64.2r   S-64.2b   L-64.2b	       V-64.3
			Bit-4	 10GBASE-LRM	 Intermediate 1300 nm	 Reserved	 OC-48-SR	         I-64.2	   S-64.3a   L-64.2c	       Reserved
			Bit-3	 10GBASE-SW	 Reserved	         Reserved	 OC-48-IR	         I-64.3	   S-64.3b   L-64.3	       Reserved
			Bit-2	 10GBASE-LW	 Reserved	         Reserved	 OC-48-LR	         I-64.5	   S-64.5a   G.959.1 P1L1-2D2  Reserved
			Bit-1	 10GBASE-EW	 Reserved	         Reserved	 Reserved	         Reserved  S-64.5b   Reserved	       Reserved
			Bit-0	 Reserved	 Reserved	         Reserved	 Reserved	         Reserved  Reserved  Reserved	       Reserved
			-----------------------------"
		::= { omtp11PlusCardGeneralDetailsEntry 54 }
		
	omtp11PlusXfpMaximumBitrateSupported OBJECT-TYPE
		SYNTAX DisplayString
		MAX-ACCESS read-only
		STATUS current
		DESCRIPTION
			"This property provides maximum bit rate value of the
			given XFP
			-----------------------------
			omtp11PlusInterfaceNumber:
			1 - CLIENT-1
			2 - LINE-1
			-----------------------------
			Values: 9.5
			-----------------------------"
		::= { omtp11PlusCardGeneralDetailsEntry 55 }
		
	omtp11PlusXfpMinimumBitrateSupported OBJECT-TYPE
		SYNTAX DisplayString
		MAX-ACCESS read-only
		STATUS current
		DESCRIPTION
			"This property provides minimum bit rate value of the 
			given XFP
			-----------------------------
			omtp11PlusInterfaceNumber:
			1 - CLIENT-1
			2 - LINE-1
			-----------------------------
			Values: 5.5
			-----------------------------"
		::= { omtp11PlusCardGeneralDetailsEntry 56 }
		
	omtp11PlusXfpMaximumCaseTemperatureSupported OBJECT-TYPE
		SYNTAX INTEGER
		MAX-ACCESS read-only
		STATUS current
		DESCRIPTION
			"This property provides the maximum case temperature
			(degree celcius) supported by XFP.
			-----------------------------
			omtp11PlusInterfaceNumber:
			1 - CLIENT-1
			2 - LINE-1
			-----------------------------
			Values:
			eg: 70
			-----------------------------"

		::= { omtp11PlusCardGeneralDetailsEntry 57 }
		
	omtp11PlusXfpMaximumPowerDissipationSupported OBJECT-TYPE
		SYNTAX INTEGER
		MAX-ACCESS read-only
		STATUS current
		DESCRIPTION
			"This property provides the maximum power dissipation(mW)
			supported from XFP.
			-----------------------------
			omtp11PlusInterfaceNumber:
			1 - CLIENT-1
			2 - LINE-1
			-----------------------------
			Values:
			eg: 25
			-----------------------------"
		::= { omtp11PlusCardGeneralDetailsEntry 58 }
		
	omtp11PlusXfpMaximumPowerDissipationSupportedAtPowerDownMode OBJECT-TYPE
		SYNTAX INTEGER
		MAX-ACCESS read-only
		STATUS current
		DESCRIPTION
			"This property provides the maximum power dissipation(mW)
			supported from XFP in power-down mode.
			-----------------------------
			omtp11PlusInterfaceNumber:
			1 - CLIENT-1
			2 - LINE-1
			-----------------------------
			Values:
			eg: 20
			-----------------------------"
		::= { omtp11PlusCardGeneralDetailsEntry 59 }
		
	omtp11PlusXfpMaximumCurrentLimitSupportedAtPlus5vSupply OBJECT-TYPE
		SYNTAX INTEGER
		MAX-ACCESS read-only
		STATUS current
		DESCRIPTION
			"This property defines the maximum current(mA) required
			by XFP at +5V power supply.
			-----------------------------
			omtp11PlusInterfaceNumber:
			1 - CLIENT-1
			2 - LINE-1
			-----------------------------
			Values:
			eg: 50
			-----------------------------"
		::= { omtp11PlusCardGeneralDetailsEntry 60 }
		
	omtp11PlusXfpMaximumCurrentLimitSupportedAtPlus3Point3vSupply OBJECT-TYPE
		SYNTAX INTEGER
		MAX-ACCESS read-only
		STATUS current
		DESCRIPTION
			"This property defines the maximum current(mA) required
			by XFP at +3.3V power supply.
			-----------------------------
			omtp11PlusInterfaceNumber:
			1 - CLIENT-1
			2 - LINE-1
			-----------------------------
			Values:
			eg: 50
			-----------------------------"
		::= { omtp11PlusCardGeneralDetailsEntry 61 }
		
	omtp11PlusXfpMaximumCurrentLimitSupportedAtPlus1Point8vSupply OBJECT-TYPE
		SYNTAX INTEGER
		MAX-ACCESS read-only
		STATUS current
		DESCRIPTION
			"This property defines the maximum current(mA) required
			by XFP at +1.8V power supply.
			-----------------------------
			omtp11PlusInterfaceNumber:
			1 - CLIENT-1
			2 - LINE-1
			-----------------------------
			Values:
			eg: 50
			-----------------------------"
		::= { omtp11PlusCardGeneralDetailsEntry 62 }
		
	omtp11PlusXfpMaximumCurrentLimitSupportedAtMinus5Point2vSupply OBJECT-TYPE
		SYNTAX INTEGER
		MAX-ACCESS read-only
		STATUS current
		DESCRIPTION
			"This property defines the maximum current(mA) required
			by XFP at -5.2V power supply.
			-----------------------------
			omtp11PlusInterfaceNumber:
			1 - CLIENT-1
			2 - LINE-1
			-----------------------------
			Values:
			eg: 50
			-----------------------------"
		::= { omtp11PlusCardGeneralDetailsEntry 63 }
		
	omtp11PlusXfpLineLoopbackSupported OBJECT-TYPE
		SYNTAX INTEGER
		MAX-ACCESS read-only
		STATUS current
		DESCRIPTION
			"This property provides information whether Line side
			loopback is supported or not.
			-----------------------------
			omtp11PlusInterfaceNumber:
			1 - CLIENT-1
			2 - LINE-1
			-----------------------------
			Values:
			1 - Lineside Loopback is supported in XFP
			0 - No Lineside Loopback is supported
			-----------------------------"
		::= { omtp11PlusCardGeneralDetailsEntry 64 }
		
	omtp11PlusXfpXfiLoopbackSupported OBJECT-TYPE
		SYNTAX INTEGER
		MAX-ACCESS read-only
		STATUS current
		DESCRIPTION
			"This property provides information whether Line side
			loopback at the Xfi level is supported or not.
			-----------------------------
			omtp11PlusInterfaceNumber:
			1 - CLIENT-1
			2 - LINE-1
			-----------------------------
			Values:
			1 - Xfi Loopback is supported in XFP
			0 - No Xfi Loopback is supported
			-----------------------------"
		::= { omtp11PlusCardGeneralDetailsEntry 65 }
		
	omtp11PlusXfpOptionalVpsSupported OBJECT-TYPE
		SYNTAX INTEGER
		MAX-ACCESS read-only
		STATUS current
		DESCRIPTION
			"This property provides information whether XFP
			supports optional variable power supply or not.
			-----------------------------
			omtp11PlusInterfaceNumber:
			1 - CLIENT-1
			2 - LINE-1
			-----------------------------
			Values:
			1 - XFP supports optional vps
			0 - XFP not supports optional vps
			-----------------------------"
		::= { omtp11PlusCardGeneralDetailsEntry 66 }
		
	omtp11PlusXfpLaserDisableThroughI2cSupported OBJECT-TYPE
		SYNTAX INTEGER
		MAX-ACCESS read-only
		STATUS current
		DESCRIPTION
			"This property provides information whether XFP
			LASER can be operated through single 2-wire interface
			bus or not.
			-----------------------------
			omtp11PlusInterfaceNumber:
			1 - CLIENT-1
			2 - LINE-1
			-----------------------------
			Values:
			1 - XFP supports LASER disable through I2C
			0 - XFP does not support LASER disable through I2C
			-----------------------------"
		::= { omtp11PlusCardGeneralDetailsEntry 67 }
		
	omtp11PlusXfpPowerDownThroughI2cSupported OBJECT-TYPE
		SYNTAX INTEGER
		MAX-ACCESS read-only
		STATUS current
		DESCRIPTION
			"This property provides information whether XFP-
			Power-down can be operated through single 2-wire 
			interface bus or not.
			-----------------------------
			omtp11PlusInterfaceNumber:
			1 - CLIENT-1
			2 - LINE-1
			-----------------------------
			Values:
			1 - XFP Supports XFP-power-down through I2C  
			0 - XFP does not supports XFP-power-down through I2C  
			-----------------------------"
		::= { omtp11PlusCardGeneralDetailsEntry 68 }
		
	omtp11PlusXfpVpsLvRegulatorModeSupported OBJECT-TYPE
		SYNTAX INTEGER
		MAX-ACCESS read-only
		STATUS current
		DESCRIPTION
			"This property provides information whether XFP
			supports VPS_LV_regulator_mode or not.
			-----------------------------
			omtp11PlusInterfaceNumber:
			1 - CLIENT-1
			2 - LINE-1
			-----------------------------
			Values:
			1 - XFP supports VPS_LV_regulator_mode
			0 - XFP not supports VPS_LV_regulator_mode
			-----------------------------"
		::= { omtp11PlusCardGeneralDetailsEntry 69 }
		
	omtp11PlusXfpVpsBypassedRegulatorModeSupported OBJECT-TYPE
		SYNTAX INTEGER
		MAX-ACCESS read-only
		STATUS current
		DESCRIPTION
			"This property provides information whether XFP
			supports VPS bypassed regulator mode or not.
			-----------------------------
			omtp11PlusInterfaceNumber:
			1 - CLIENT-1
			2 - LINE-1
			-----------------------------
			Values:
			1 - XFP supports VPS bypassed regulator mode
			0 - XFP not supports active VPS bypassed regulator mode
			-----------------------------"
		::= { omtp11PlusCardGeneralDetailsEntry 70 }
		
	omtp11PlusXfpActiveFecControlSupported OBJECT-TYPE
		SYNTAX INTEGER
		MAX-ACCESS read-only
		STATUS current
		DESCRIPTION
			"This property provides information whether XFP
			supports active FEC control functions or not.
			-----------------------------
			omtp11PlusInterfaceNumber:
			1 - CLIENT-1
			2 - LINE-1
			-----------------------------
			Values:
			1 - XFP supports active FEC control functions
			0 - XFP not supports active FEC control functions
			-----------------------------"
		::= { omtp11PlusCardGeneralDetailsEntry 71 }
		
	omtp11PlusXfpOptionalCmuModeSupported OBJECT-TYPE
		SYNTAX INTEGER
		MAX-ACCESS read-only
		STATUS current
		DESCRIPTION
			"This property provides information whether XFP
			supports CMU mode or not.
			-----------------------------
			omtp11PlusInterfaceNumber:
			1 - CLIENT-1
			2 - LINE-1
			-----------------------------
			Values:
			1 - XFP supports CMU mode
			0 - XFP not supports CMU mode
			-----------------------------"
		::= { omtp11PlusCardGeneralDetailsEntry 72 }
		
	omtp11PlusXfpFecBerSupported OBJECT-TYPE
		SYNTAX INTEGER
		MAX-ACCESS read-only
		STATUS current
		DESCRIPTION
			"This property provides information whether XFP
			supports FEC BER or not.
			-----------------------------
			omtp11PlusInterfaceNumber:
			1 - CLIENT-1
			2 - LINE-1
			-----------------------------
			Values:
			1 - XFP supports FEC BER
			0 - XFP not supports FEC BER
			-----------------------------"
		::= { omtp11PlusCardGeneralDetailsEntry 73 }
		
	omtp11PlusXfpReceivePowerMeasurementIsInOmaOrAverage OBJECT-TYPE
		SYNTAX INTEGER
		MAX-ACCESS read-only
		STATUS current
		DESCRIPTION
			"This property tells whether the received power  
			measurement from XFP is given as Oma or Average.
			-----------------------------
			omtp11PlusInterfaceNumber:
			1 - CLIENT-1
			2 - LINE-1
			-----------------------------
			Values:
			1 - OMA
			0 - Average Power
			-----------------------------"
		::= { omtp11PlusCardGeneralDetailsEntry 74 }
		
	omtp11PlusXfpActiveWavelengthControlSupported OBJECT-TYPE
		SYNTAX INTEGER
		MAX-ACCESS read-only
		STATUS current
		DESCRIPTION
			"This property provides whether the XFP wavelength 
			controlling state is active or not
			-----------------------------
			omtp11PlusInterfaceNumber:
			1 - CLIENT-1
			2 - LINE-1
			-----------------------------
			Values:
			1 - active
			0 - not active
			-----------------------------"
		::= { omtp11PlusCardGeneralDetailsEntry 75 }
		
	omtp11PlusXfpTransmitterIsCooledOrUncooled OBJECT-TYPE
		SYNTAX INTEGER
		MAX-ACCESS read-only
		STATUS current
		DESCRIPTION
			"This property provide information on which type of
			diode used in transmitter of the XFP
			-----------------------------
			omtp11PlusInterfaceNumber:
			1 - CLIENT-1
			2 - LINE-1
			-----------------------------
			Values:
			1 - Cooling circuit supported for XFP transmitter. 
			0 - Cooling circuit not supported for XFP transmitter.
			-----------------------------"
		::= { omtp11PlusCardGeneralDetailsEntry 76 }
		
	omtp11PlusXfpReceiverTypeIsPinOrApd OBJECT-TYPE
		SYNTAX INTEGER
		MAX-ACCESS read-only
		STATUS current
		DESCRIPTION
			"This property provide information on which type of
			diode used in transmitter of the XFP.
			-----------------------------
			omtp11PlusInterfaceNumber:
			1 - CLIENT-1
			2 - LINE-1
			-----------------------------
			Values:
			1 - PIN detector
			0 - APD detector			 
			-----------------------------"
		::= { omtp11PlusCardGeneralDetailsEntry 77 }

	omtp11PlusCardGeneralDetailsTableRowStatus OBJECT-TYPE
              SYNTAX      RowStatus
              MAX-ACCESS  read-write
              STATUS      current
              DESCRIPTION
                      "	This is MIB realted property,
			NOT to be considered as a card property"
              ::= { omtp11PlusCardGeneralDetailsEntry 78 }	

--*****************************************************************************
--				CONFIGURATION
--*****************************************************************************

        omtp11PlusConfigurationTable OBJECT-TYPE
                SYNTAX SEQUENCE OF Omtp11PlusConfigurationEntry
                MAX-ACCESS not-accessible
                STATUS current
                DESCRIPTION
                	"Contains configuration queries of the OMTP11-PLUS card"
                ::= { omtp11PlusConfiguration 1 }

	omtp11PlusConfigurationEntry OBJECT-TYPE
		SYNTAX  Omtp11PlusConfigurationEntry
		MAX-ACCESS  not-accessible
		STATUS  current
		DESCRIPTION 
			""
		INDEX   { node, rack , subRack , slot , omtp11PlusInterfaceNumber}
		::= { omtp11PlusConfigurationTable 1 }

	Omtp11PlusConfigurationEntry ::= 
		SEQUENCE { 
				omtp11PlusCardSoftwareUpgrade						DisplayString,
				omtp11PlusCardSignalMonitorState					INTEGER,
				omtp11PlusCardOpticalMonitorState					INTEGER,
				omtp11PlusCardSoftReset							INTEGER,
				omtp11PlusCardFactoryReset						INTEGER,
				omtp11PlusCardAccessStatus						INTEGER,
				omtp11PlusSyncSystemTimeWithNtpServer				DisplayString,
				omtp11PlusSyncRtcWithNtpServer						DisplayString,
				omtp11PlusSyncRtcWithSystemTime						DisplayString,
				omtp11PlusUpdateGivenTimeIntoSystem					DisplayString,
				omtp11PlusUpdateGivenTimeIntoRtc					DisplayString,
				omtp11PlusSystemTimeAndRtcTime						DisplayString,
				omtp11PlusTrafficConfiguration						INTEGER,
				omtp11PlusLoopbackState							INTEGER,
				omtp11PlusPortSignalMonitorState					INTEGER,
				omtp11PlusPortOpticalMonitorState					INTEGER,
				omtp11PlusClearSignalPerformance					INTEGER,
				omtp11PlusAlsState							INTEGER,
				omtp11PlusAlsPulseRepetitionTime					INTEGER,
				omtp11PlusOtuFecConfiguration						INTEGER,
				omtp11PlusOtuSignalFailThreshold					INTEGER,
				omtp11PlusOtuSignalDegradeThreshold					INTEGER,
				omtp11PlusOtuAlarmIndicationSignalAlarmInsertion			INTEGER,
				omtp11PlusOtuSapiTransmitTraceMessage					DisplayString,
				omtp11PlusOtuDapiTransmitTraceMessage					DisplayString,
				omtp11PlusOtuOperatorSpecificTransmitTraceMessage			DisplayString,
				omtp11PlusOtuSapiExpectedTraceMessage					DisplayString,
				omtp11PlusOtuDapiExpectedTraceMessage					DisplayString,
				omtp11PlusOtuOperatorSpecificExpectedTraceMessage			DisplayString,
				omtp11PlusOtuSapiReceivedTraceMessage					DisplayString,
				omtp11PlusOtuDapiReceivedTraceMessage					DisplayString,
				omtp11PlusOtuOperatorSpecificReceivedTraceMessage			DisplayString,
				omtp11PlusOduSignalFailThreshold					INTEGER,
				omtp11PlusOduSignalDegradeThreshold					INTEGER,
				omtp11PlusOduAlarmIndicationSignalAlarmInsertion			INTEGER,
				omtp11PlusOduLockedDefectAlarmInsertion					INTEGER,
				omtp11PlusOduOpenConnectionIndicationAlarmInsertion			INTEGER,
				omtp11PlusOduSapiTransmitTraceMessage					DisplayString,
				omtp11PlusOduDapiTransmitTraceMessage					DisplayString,
				omtp11PlusOduOperatorSpecificTransmitTraceMessage			DisplayString,
				omtp11PlusOduSapiExpectedTraceMessage					DisplayString,
				omtp11PlusOduDapiExpectedTraceMessage					DisplayString,
				omtp11PlusOduOperatorSpecificExpectedTraceMessage			DisplayString,
				omtp11PlusOduSapiReceivedTraceMessage					DisplayString,
				omtp11PlusOduDapiReceivedTraceMessage					DisplayString,
				omtp11PlusOduOperatorSpecificReceivedTraceMessage			DisplayString,
				omtp11PlusOpuTransmitPayloadType					INTEGER,
				omtp11PlusOpuReceivedPayloadType					INTEGER,
				omtp11PlusSdhMsB2ExcessiveErrorThreshold				INTEGER,
				omtp11PlusSdhMsB2SignalDegradeThreshold					INTEGER,
				omtp11PlusWan10gMsB2ExcessiveErrorThreshold					INTEGER,
				omtp11PlusWan10gMsB2SignalDegradeThreshold				INTEGER,
				omtp11PlusTunableXfpLaserWavelength					INTEGER,
				omtp11PlusTunableXfpLaserChannelNumber					INTEGER,
				omtp11PlusXfpLaserState							INTEGER,
				omtp11PlusXfpReset							INTEGER,
				omtp11PlusXfpPowerDownMode						INTEGER,
				omtp11PlusXfpLineLoopback						INTEGER,
				omtp11PlusXfpXfiLoopback						INTEGER,
				omtp11PlusXfpAmplitudeThresholdOfReceiverForFecControl			INTEGER,
				omtp11PlusXfpPhaseInEyeDiagramForFecControl				INTEGER,
				omtp11PlusXfpSystemReportingBer						INTEGER,
				omtp11PlusXfpHighTemperatureAlarmThreshold				DisplayString,
				omtp11PlusXfpLowTemperatureAlarmThreshold				DisplayString,
				omtp11PlusXfpHighTemperatureWarningThreshold				DisplayString,
				omtp11PlusXfpLowTemperatureWarningThreshold				DisplayString,
				omtp11PlusXfpHighBiasCurrentAlarmThreshold				DisplayString,
				omtp11PlusXfpLowBiasCurrentAlarmThreshold				DisplayString,
				omtp11PlusXfpHighBiasCurrentWarningThreshold				DisplayString,
				omtp11PlusXfpLowBiasCurrentWarningThreshold				DisplayString,
				omtp11PlusXfpInputHighPowerAlarmThreshold				DisplayString,
				omtp11PlusXfpInputLowPowerAlarmThreshold				DisplayString,
				omtp11PlusXfpInputHighPowerWarningThreshold				DisplayString,
				omtp11PlusXfpInputLowPowerWarningThreshold				DisplayString,
				omtp11PlusXfpOutputHighPowerAlarmThreshold				DisplayString,
				omtp11PlusXfpOutputLowPowerAlarmThreshold				DisplayString,
				omtp11PlusXfpOutputHighPowerWarningThreshold				DisplayString,
				omtp11PlusXfpOutputLowPowerWarningThreshold				DisplayString,
				omtp11PlusXfpHighSupplyVoltageAlarmThreshold				DisplayString,
				omtp11PlusXfpLowSupplyVoltageAlarmThreshold				DisplayString,
				omtp11PlusXfpHighSupplyVoltageWarningThreshold				DisplayString,
				omtp11PlusXfpLowSupplyVoltageWarningThreshold				DisplayString,
				omtp11PlusXfpInputPowerFailureAlarmInhibit				INTEGER,
				omtp11PlusXfpOutputPowerFailureAlarmInhibit				INTEGER,
				omtp11PlusXfpHighTemperatureAlarmInhibit				INTEGER,
				omtp11PlusXfpLowTemperatureAlarmInhibit					INTEGER,
				omtp11PlusXfpHighTemperatureWarningInhibit				INTEGER,
				omtp11PlusXfpLowTemperatureWarningInhibit				INTEGER,
				omtp11PlusXfpHighBiasCurrentAlarmInhibit				INTEGER,
				omtp11PlusXfpLowBiasCurrentAlarmInhibit					INTEGER,
				omtp11PlusXfpHighBiasCurrentWarningInhibit				INTEGER,
				omtp11PlusXfpLowBiasCurrentWarningInhibit				INTEGER,
				omtp11PlusXfpInputHighPowerAlarmInhibit					INTEGER,
				omtp11PlusXfpInputLowPowerAlarmInhibit					INTEGER,
				omtp11PlusXfpInputHighPowerWarningInhibit				INTEGER,
				omtp11PlusXfpInputLowPowerWarningInhibit				INTEGER,
				omtp11PlusXfpOutputHighPowerAlarmInhibit				INTEGER,
				omtp11PlusXfpOutputLowPowerAlarmInhibit					INTEGER,
				omtp11PlusXfpOutputHighPowerWarningInhibit				INTEGER,
				omtp11PlusXfpOutputLowPowerWarningInhibit				INTEGER,
				omtp11PlusXfpHighSupplyVoltageAlarmInhibit				INTEGER,
				omtp11PlusXfpLowSupplyVoltageAlarmInhibit				INTEGER,
				omtp11PlusXfpHighSupplyVoltageWarningInhibit				INTEGER,
				omtp11PlusXfpLowSupplyVoltageWarningInhibit				INTEGER,
				omtp11PlusXfpPresenceAbsenceNotificationInhibit				INTEGER,
				omtp11PlusOtuLossOfSignalAlarmInhibit					INTEGER,
				omtp11PlusOtuLossOfFrameAlarmInhibit					INTEGER,
				omtp11PlusOtuOutOfFrameAlarmInhibit					INTEGER,
				omtp11PlusOtuLossOfMultiFrameAlarmInhibit				INTEGER,
				omtp11PlusOtuOutOfMultiFrameAlarmInhibit				INTEGER,
				omtp11PlusOtuSignalFailAlarmInhibit					INTEGER,
				omtp11PlusOtuSignalDegradeAlarmInhibit					INTEGER,
				omtp11PlusOtuAlarmIndicationSignalAlarmInhibit				INTEGER,
				omtp11PlusOtuIncomingAlignmentErrorAlarmInhibit				INTEGER,
				omtp11PlusOtuTraceIdentifierMismatchAlarmInhibit			INTEGER,
				omtp11PlusOtuBackwardIncomingAlignmentErrorAlarmInhibit			INTEGER,
				omtp11PlusOtuBackwardDefectIndicationAlarmInhibit			INTEGER,
				omtp11PlusOduSignalFailAlarmInhibit					INTEGER,
				omtp11PlusOduSignalDegradeAlarmInhibit					INTEGER,
				omtp11PlusOduAlarmIndicationSignalAlarmInhibit				INTEGER,
				omtp11PlusOduTcm1IncomingAlignmentErrorAlarmInhibit			INTEGER,
				omtp11PlusOduTcm2IncomingAlignmentErrorAlarmInhibit			INTEGER,
				omtp11PlusOduTcm3IncomingAlignmentErrorAlarmInhibit			INTEGER,
				omtp11PlusOduTcm4IncomingAlignmentErrorAlarmInhibit			INTEGER,
				omtp11PlusOduTcm5IncomingAlignmentErrorAlarmInhibit			INTEGER,
				omtp11PlusOduTcm6IncomingAlignmentErrorAlarmInhibit			INTEGER,
				omtp11PlusOduTraceIdentifierMismatchAlarmInhibit			INTEGER,
				omtp11PlusOduLockedDefectAlarmInhibit					INTEGER,
				omtp11PlusOduOpenConnectionIndicationAlarmInhibit			INTEGER,
				omtp11PlusOduBackwardDefectIndicationAlarmInhibit			INTEGER,
				omtp11PlusOduTcm1BackwardIncomingAlignmentErrorAlarmInhibit		INTEGER,
				omtp11PlusOduTcm2BackwardIncomingAlignmentErrorAlarmInhibit		INTEGER,
				omtp11PlusOduTcm3BackwardIncomingAlignmentErrorAlarmInhibit		INTEGER,
				omtp11PlusOduTcm4BackwardIncomingAlignmentErrorAlarmInhibit		INTEGER,
				omtp11PlusOduTcm5BackwardIncomingAlignmentErrorAlarmInhibit		INTEGER,
				omtp11PlusOduTcm6BackwardIncomingAlignmentErrorAlarmInhibit		INTEGER,
				omtp11PlusOpuPayloadMismatchAlarmInhibit				INTEGER,
				omtp11PlusOchLossOfPayloadAlarmInhibit					INTEGER,
				omtp11PlusSdhLossOfSignalAlarmInhibit					INTEGER,
				omtp11PlusSdhOutOfFrameAlarmInhibit					INTEGER,
				omtp11PlusSdhLossOfFrameAlarmInhibit					INTEGER,
				omtp11PlusSdhRsAlarmIndicationSignalAlarmInhibit			INTEGER,
				omtp11PlusSdhRsTraceIdentifierMismatchAlarmInhibit			INTEGER,
				omtp11PlusSdhAuAlarmIndicationSignalAlarmInhibit			INTEGER,
				omtp11PlusSdhAuLossOfPointerAlarmInhibit				INTEGER,
				omtp11PlusSdhMsAlarmIndicationSignalAlarmInhibit			INTEGER,
				omtp11PlusSdhMsRemoteErrorIndicationAlarmInhibit			INTEGER,
				omtp11PlusSdhMsRemoteDefectIndicationAlarmInhibit			INTEGER,
				omtp11PlusSdhMsRemoteFailureIndicationAlarmInhibit			INTEGER,
				omtp11PlusSdhMsB2ExcessiveErrorAlarmInhibit                             INTEGER,
				omtp11PlusSdhMsB2SignalDegradeAlarmInhibit				INTEGER,
				omtp11PlusSdhLossOfSequenceSynchronisationAlarmInhibit			INTEGER,
				omtp11PlusSdhHigherOrderPathPayloadLabelMismatchAlarmInhibit		INTEGER,
				omtp11PlusSdhHigherOrderPathUnequippedAlarmInhibit			INTEGER,
				omtp11PlusWan10gLossOfSignalAlarmInhibit				INTEGER,
				omtp11PlusWan10gOutOfFrameAlarmInhibit					INTEGER,
				omtp11PlusWan10gLossOfFrameAlarmInhibit					INTEGER,
				omtp11PlusWan10gRsAlarmIndicationSignalAlarmInhibit			INTEGER,
				omtp11PlusWan10gRsTraceIdentifierMismatchAlarmInhibit			INTEGER,
				omtp11PlusWan10gAuAlarmIndicationSignalAlarmInhibit			INTEGER,
				omtp11PlusWan10gAuLossOfPointerAlarmInhibit				INTEGER,
				omtp11PlusWan10gMsAlarmIndicationSignalAlarmInhibit			INTEGER,
				omtp11PlusWan10gMsRemoteErrorIndicationAlarmInhibit			INTEGER,
				omtp11PlusWan10gMsRemoteDefectIndicationAlarmInhibit			INTEGER,
				omtp11PlusWan10gMsRemoteFailureIndicationAlarmInhibit			INTEGER,
				omtp11PlusWan10gMsB2ExcessiveErrorAlarmInhibit				INTEGER,
				omtp11PlusWan10gMsB2SignalDegradeAlarmInhibit				INTEGER,
				omtp11PlusWan10gLossOfSequenceSynchronisationAlarmInhibit		INTEGER,
				omtp11PlusWan10gHigherOrderPathPayloadLabelMismatchAlarmInhibit		INTEGER,
				omtp11PlusWan10gHigherOrderPathUnequippedAlarmInhibit			INTEGER,
				omtp11PlusLan10gLossOfSignalAlarmInhibit				INTEGER,
				omtp11PlusLan10gLossOfSignalSyncAlarmInhibit				INTEGER,
				omtp11PlusLan10gLinkFailureAlarmInhibit					INTEGER,
				omtp11PlusLan10gFrameCheckSequenceAlarmInhibit				INTEGER,
				omtp11PlusLan10gCarrierStatusAlarmInhibit				INTEGER,
				omtp11PlusLan10gHighBerAlarmInhibit					INTEGER,
				omtp11PlusLan10gLocalFaultAlarmInhibit					INTEGER,
				omtp11PlusLan10gRemoteFaultAlarmInhibit					INTEGER,
				omtp11PlusFcTransmitDisparityInversionDefectAlarmInhibit		INTEGER,
				omtp11PlusFcTransmitDigitalLossOfLinkDefectAlarmInhibit			INTEGER,
				omtp11PlusFcTrasnmitLossofSynchronizationDefectAlarmInhibit		INTEGER,
				omtp11PlusFcReceiveDigitalLossofLinkDefectAlarmInhibit			INTEGER,
				omtp11PlusFcReceiveLossofSynchronizationDefectAlarmInhibit		INTEGER,
				omtp11PlusFcReceiveTransitionDetectDefectAlarmInhibit			INTEGER,
				omtp11PlusFcReceiveAnalogLossofSignalDefectAlarmInhibit			INTEGER,
				omtp11PlusFcReceiveLineCodeViolationDefectAlarmInhibit			INTEGER,
				omtp11PlusGfpCsfSignalFailAlarmInhibit					INTEGER,
				omtp11PlusGfpCsfLinkFailAlarmInhibit					INTEGER,
				omtp11PlusGfpCoreHeaderErrorAlarmInhibit				INTEGER,
				omtp11PlusGfpExtentionHeaderErrorAlarmInhibit				INTEGER,
				omtp11PlusXfpInputPowerFailureAlarmSeverity				DisplayString,
				omtp11PlusXfpOutputPowerFailureAlarmSeverity				DisplayString,
				omtp11PlusXfpHighTemperatureAlarmSeverity				DisplayString,
				omtp11PlusXfpLowTemperatureAlarmSeverity				DisplayString,
				omtp11PlusXfpHighTemperatureWarningSeverity				DisplayString,
				omtp11PlusXfpLowTemperatureWarningSeverity				DisplayString,
				omtp11PlusXfpHighBiasCurrentAlarmSeverity				DisplayString,
				omtp11PlusXfpLowBiasCurrentAlarmSeverity				DisplayString,
				omtp11PlusXfpHighBiasCurrentWarningSeverity				DisplayString,
				omtp11PlusXfpLowBiasCurrentWarningSeverity				DisplayString,
				omtp11PlusXfpInputHighPowerAlarmSeverity				DisplayString,
				omtp11PlusXfpInputLowPowerAlarmSeverity					DisplayString,
				omtp11PlusXfpInputHighPowerWarningSeverity				DisplayString,
				omtp11PlusXfpInputLowPowerWarningSeverity				DisplayString,
				omtp11PlusXfpOutputHighPowerAlarmSeverity				DisplayString,
				omtp11PlusXfpOutputLowPowerAlarmSeverity				DisplayString,
				omtp11PlusXfpOutputHighPowerWarningSeverity				DisplayString,
				omtp11PlusXfpOutputLowPowerWarningSeverity				DisplayString,
				omtp11PlusXfpHighSupplyVoltageAlarmSeverity				DisplayString,
				omtp11PlusXfpLowSupplyVoltageAlarmSeverity				DisplayString,
				omtp11PlusXfpHighSupplyVoltageWarningSeverity				DisplayString,
				omtp11PlusXfpLowSupplyVoltageWarningSeverity				DisplayString,
				omtp11PlusXfpPresenceAbsenceNotificationSeverity			DisplayString,
				omtp11PlusOtuLossOfSignalAlarmSeverity					DisplayString,
				omtp11PlusOtuLossOfFrameAlarmSeverity					DisplayString,
				omtp11PlusOtuOutOfFrameAlarmSeverity					DisplayString,
				omtp11PlusOtuLossOfMultiFrameAlarmSeverity				DisplayString,
				omtp11PlusOtuOutOfMultiFrameAlarmSeverity				DisplayString,
				omtp11PlusOtuSignalFailAlarmSeverity					DisplayString,
				omtp11PlusOtuSignalDegradeAlarmSeverity					DisplayString,
				omtp11PlusOtuAlarmIndicationSignalAlarmSeverity				DisplayString,
				omtp11PlusOtuIncomingAlignmentErrorAlarmSeverity			DisplayString,
				omtp11PlusOtuTraceIdentifierMismatchAlarmSeverity			DisplayString,
				omtp11PlusOtuBackwardIncomingAlignmentErrorAlarmSeverity		DisplayString,
				omtp11PlusOtuBackwardDefectIndicationAlarmSeverity			DisplayString,
				omtp11PlusOduSignalFailAlarmSeverity					DisplayString,
				omtp11PlusOduSignalDegradeAlarmSeverity					DisplayString,
				omtp11PlusOduAlarmIndicationSignalAlarmSeverity				DisplayString,
				omtp11PlusOduTcm1IncomingAlignmentErrorAlarmSeverity			DisplayString,
				omtp11PlusOduTcm2IncomingAlignmentErrorAlarmSeverity			DisplayString,
				omtp11PlusOduTcm3IncomingAlignmentErrorAlarmSeverity			DisplayString,
				omtp11PlusOduTcm4IncomingAlignmentErrorAlarmSeverity			DisplayString,
				omtp11PlusOduTcm5IncomingAlignmentErrorAlarmSeverity			DisplayString,
				omtp11PlusOduTcm6IncomingAlignmentErrorAlarmSeverity			DisplayString,
				omtp11PlusOduTraceIdentifierMismatchAlarmSeverity			DisplayString,
				omtp11PlusOduLockedDefectAlarmSeverity					DisplayString,
				omtp11PlusOduOpenConnectionIndicationAlarmSeverity			DisplayString,
				omtp11PlusOduBackwardDefectIndicationAlarmSeverity			DisplayString,
				omtp11PlusOduTcm1BackwardIncomingAlignmentErrorAlarmSeverity		DisplayString,
				omtp11PlusOduTcm2BackwardIncomingAlignmentErrorAlarmSeverity		DisplayString,
				omtp11PlusOduTcm3BackwardIncomingAlignmentErrorAlarmSeverity		DisplayString,
				omtp11PlusOduTcm4BackwardIncomingAlignmentErrorAlarmSeverity		DisplayString,
				omtp11PlusOduTcm5BackwardIncomingAlignmentErrorAlarmSeverity		DisplayString,
				omtp11PlusOduTcm6BackwardIncomingAlignmentErrorAlarmSeverity		DisplayString,
				omtp11PlusOpuPayloadMismatchAlarmSeverity				DisplayString,
				omtp11PlusOchLossOfPayloadAlarmSeverity					DisplayString,
				omtp11PlusSdhLossOfSignalAlarmSeverity					DisplayString,
				omtp11PlusSdhOutOfFrameAlarmSeverity					DisplayString,
				omtp11PlusSdhLossOfFrameAlarmSeverity					DisplayString,
				omtp11PlusSdhRsAlarmIndicationSignalAlarmSeverity			DisplayString,
				omtp11PlusSdhRsTraceIdentifierMismatchAlarmSeverity			DisplayString,
				omtp11PlusSdhAuAlarmIndicationSignalAlarmSeverity			DisplayString,
				omtp11PlusSdhAuLossOfPointerAlarmSeverity				DisplayString,
				omtp11PlusSdhMsAlarmIndicationSignalAlarmSeverity			DisplayString,
				omtp11PlusSdhMsRemoteErrorIndicationAlarmSeverity			DisplayString,
				omtp11PlusSdhMsRemoteDefectIndicationAlarmSeverity			DisplayString,
				omtp11PlusSdhMsRemoteFailureIndicationAlarmSeverity			DisplayString,
				omtp11PlusSdhMsB2ExcessiveErrorAlarmSeverity                            DisplayString,
				omtp11PlusSdhMsB2SignalDegradeAlarmSeverity				DisplayString,
				omtp11PlusSdhLossOfSequenceSynchronisationAlarmSeverity			DisplayString,
				omtp11PlusSdhHigherOrderPathPayloadLabelMismatchAlarmSeverity		DisplayString,
				omtp11PlusSdhHigherOrderPathUnequippedAlarmSeverity			DisplayString,
				omtp11PlusWan10gLossOfSignalAlarmSeverity				DisplayString,
				omtp11PlusWan10gOutOfFrameAlarmSeverity					DisplayString,
				omtp11PlusWan10gLossOfFrameAlarmSeverity				DisplayString,
				omtp11PlusWan10gRsAlarmIndicationSignalAlarmSeverity			DisplayString,
				omtp11PlusWan10gRsTraceIdentifierMismatchAlarmSeverity			DisplayString,
				omtp11PlusWan10gAuAlarmIndicationSignalAlarmSeverity			DisplayString,
				omtp11PlusWan10gAuLossOfPointerAlarmSeverity				DisplayString,
				omtp11PlusWan10gMsAlarmIndicationSignalAlarmSeverity			DisplayString,
				omtp11PlusWan10gMsRemoteErrorIndicationAlarmSeverity			DisplayString,
				omtp11PlusWan10gMsRemoteDefectIndicationAlarmSeverity			DisplayString,
				omtp11PlusWan10gMsRemoteFailureIndicationAlarmSeverity			DisplayString,
				omtp11PlusWan10gMsB2ExcessiveErrorAlarmSeverity				DisplayString,
				omtp11PlusWan10gMsB2SignalDegradeAlarmSeverity				DisplayString,
				omtp11PlusWan10gLossOfSequenceSynchronisationAlarmSeverity		DisplayString,
				omtp11PlusWan10gHigherOrderPathPayloadLabelMismatchAlarmSeverity	DisplayString,            
				omtp11PlusWan10gHigherOrderPathUnequippedAlarmSeverity			DisplayString,
				omtp11PlusLan10gLossOfSignalAlarmSeverity				DisplayString,
				omtp11PlusLan10gLossOfSignalSyncAlarmSeverity				DisplayString,
				omtp11PlusLan10gLinkFailureAlarmSeverity				DisplayString,
				omtp11PlusLan10gFrameCheckSequenceAlarmSeverity				DisplayString,
				omtp11PlusLan10gCarrierStatusAlarmSeverity				DisplayString,
				omtp11PlusLan10gHighBerAlarmSeverity					DisplayString,
				omtp11PlusLan10gLocalFaultAlarmSeverity					DisplayString,
				omtp11PlusLan10gRemoteFaultAlarmSeverity				DisplayString,
				omtp11PlusFcTransmitDisparityInversionDefectAlarmSeverity		DisplayString,
				omtp11PlusFcTransmitDigitalLossOfLinkDefectAlarmSeverity		DisplayString,
				omtp11PlusFcTrasnmitLossofSynchronizationDefectAlarmSeverity		DisplayString,
				omtp11PlusFcReceiveDigitalLossofLinkDefectAlarmSeverity			DisplayString,
				omtp11PlusFcReceiveLossofSynchronizationDefectAlarmSeverity		DisplayString,
				omtp11PlusFcReceiveTransitionDetectDefectAlarmSeverity			DisplayString,
				omtp11PlusFcReceiveAnalogLossofSignalDefectAlarmSeverity		DisplayString,
				omtp11PlusFcReceiveLineCodeViolationDefectAlarmSeverity			DisplayString,
				omtp11PlusGfpCsfSignalFailAlarmSeverity					DisplayString,
				omtp11PlusGfpCsfLinkFailAlarmSeverity					DisplayString,
				omtp11PlusGfpCoreHeaderErrorAlarmSeverity				DisplayString,
				omtp11PlusGfpExtentionHeaderErrorAlarmSeverity				DisplayString,
				omtp11PlusConfigurationTableRowStatus					RowStatus
		}
		
	omtp11PlusCardSoftwareUpgrade OBJECT-TYPE
		SYNTAX DisplayString
		MAX-ACCESS read-write
		STATUS current
		DESCRIPTION
			"Valid only as SET command.
			This property upgrades the software of the OMTP11-PLUS card
			It takes the path of the software release as
			a value
			-----------------------------
			omtp11PlusInterfaceNumber: 0
			-----------------------------
			Values:
			eg: /root/home/rel-2.0.0.tar.gz
			-----------------------------"

		::= { omtp11PlusConfigurationEntry 1 }
		
	omtp11PlusCardSignalMonitorState OBJECT-TYPE
		SYNTAX INTEGER
		MAX-ACCESS read-write
		STATUS current
		DESCRIPTION
			"This property sets or gets the card's signal
			monitoring state. Disabling card signal monitoring 
			will not provide any signal alarms and performances
			information to the user.
			-----------------------------
			omtp11PlusInterfaceNumber: 0
			-----------------------------
			Values:
			1 - Card Signal Monitoring is enabled
			0 - Card Signal Monitoring is disabled
			-----------------------------"
		::= { omtp11PlusConfigurationEntry 2 }

	omtp11PlusCardOpticalMonitorState OBJECT-TYPE
		SYNTAX INTEGER
		MAX-ACCESS read-write
		STATUS current
		DESCRIPTION
			"This property sets or gets the card's optical
			monitoring state. Disabling card signal monitoring 
			will not provide any signal alarms and performances
			information to the user.
			-----------------------------
			omtp11PlusInterfaceNumber: 0
			-----------------------------
			Values:
			1 - Card Optical Monitoring is enabled
			0 - Card Optical Monitoring is disabled
			-----------------------------"
		::= { omtp11PlusConfigurationEntry 3 }
		
	omtp11PlusCardSoftReset OBJECT-TYPE
		SYNTAX INTEGER
		MAX-ACCESS read-write
		STATUS current
		DESCRIPTION
			"Valid only as a SET command.
			Reboots the Card, Reconfigures the Card 
			i.e All Configuration Parameter	like Laser State,
			Traffic configuration, Loopback, FEC, optical and 
			signal thresholds, switching mode,
			user choice of line path, TTI messages
			will be restored to previous state
			-----------------------------
			omtp11PlusInterfaceNumber: 0
			-----------------------------
			Values:
			Dont care, any value
			eg: 0
			-----------------------------"
		::= { omtp11PlusConfigurationEntry 4 }
		
	omtp11PlusCardFactoryReset OBJECT-TYPE
		SYNTAX INTEGER
		MAX-ACCESS read-write
		STATUS current
		DESCRIPTION
			"Valid only as a SET command.
			Sets the Card To Factory Default State
			i.e All User Configuration Parameters like Laser State,
			Traffic configuration, Loopback, FEC, optical and 
			signal thresholds, switching mode,
			user choice of line path, TTI messages
			will be set to default state
			-----------------------------
			omtp11PlusInterfaceNumber: 0
			-----------------------------
			Values:
			Dont care, any value
			eg: 0
			-----------------------------"
		::= { omtp11PlusConfigurationEntry 5 }
		
	omtp11PlusCardAccessStatus OBJECT-TYPE
		SYNTAX INTEGER
		MAX-ACCESS read-write
		STATUS current
		DESCRIPTION
			"This property will tell whether the card is 
			accessible from EMS/LCT or not. Turning off the
			accessbility to the card, will not allow the user
			to access any configuration, alarm or performance
			of the card and also turns off fast alarm
			triggering, global alarm led indication
			-----------------------------
			omtp11PlusInterfaceNumber: 0
			-----------------------------
			Values:
			1 - Card is accessible from EMS/LCT
			0 - Card is inaccessible from EMS/LCT
			-----------------------------"
		::= { omtp11PlusConfigurationEntry 6 }

	omtp11PlusSyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that ilarticular server. 
					If we are not providing NTP server IP address 
					then the system will be synced with the NTP server 
					which is already been registered with card. 
					If both are absent then error message will be returned
					-----------------------------
						Interface : 0
					-----------------------------
						If we want to provide NTP server IP address then
						Value should be a valid IP address as shown below
						: 192.168.21.25
						
						If we don't want to provide NTP server address then no
						need to pass any value. 
					---------------------------"
  						
  		::= { omtp11PlusConfigurationEntry 7 }
  		
  	omtp11PlusSyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 192.168.21.25
							
						If we don't want to provide NTP server address, then no
						need to ilass any value. 
						---------------------------"
  						
  		::= { omtp11PlusConfigurationEntry 8 }
  		
  	omtp11PlusSyncRtcWithSystemTime	 OBJECT-TYPE
		SYNTAX  		DisplayString
  		MAX-ACCESS  	read-write
  		STATUS  		current
  		DESCRIPTION	 	" when we want to manually sync the time value
  						present in RTC with the time value in linux kernel
  						we can use this OID. With this set operation, 
  						the time available with linux kernel will be updated
  						into RTC. It is not required to provide any value for 
  						this operation"
  						
  		::= { omtp11PlusConfigurationEntry 9 }
  		
  	omtp11PlusUpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2017-10-31 15:20:44
						---------------------------"
						
  		::= { omtp11PlusConfigurationEntry 10 }
  		
  	omtp11PlusUpdateGivenTimeIntoRtc	 OBJECT-TYPE
		SYNTAX  		DisplayString
  		MAX-ACCESS  	read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD H:M:S
						
						Example: 2017-10-31 15:20:44
						---------------------------"
						
  		::= { omtp11PlusConfigurationEntry 11 }
  		
  	omtp11PlusSystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { omtp11PlusConfigurationEntry 12 }

	omtp11PlusTrafficConfiguration OBJECT-TYPE
		SYNTAX INTEGER
		MAX-ACCESS read-write
		STATUS current
		DESCRIPTION
			"Set or get the traffic configuration for the
			requested port
			-----------------------------
			omtp11PlusInterfaceNumber:
			1 - CLIENT-1
			2 - LINE-1
			-----------------------------
			Values: 
			00 - Un-configure
			01 - STM64
			02 - WAN10G
			04 - LAN10G
			06 - OTU2
			-----------------------------"
		::= { omtp11PlusConfigurationEntry 41 }
		
	omtp11PlusLoopbackState OBJECT-TYPE
		SYNTAX INTEGER
		MAX-ACCESS read-write
		STATUS current
		DESCRIPTION
			"Set or get the loopback state for the
			requested port
			-----------------------------
			omtp11PlusInterfaceNumber:
			1 - CLIENT-1
			2 - LINE-1
			-----------------------------
			Values: 
			00 - No Loopback   
			01 - Near End Loopback
			02 - Far End Loopback
			-----------------------------"
		::= { omtp11PlusConfigurationEntry 42 }
		
	omtp11PlusPortSignalMonitorState OBJECT-TYPE
		SYNTAX INTEGER
		MAX-ACCESS read-write
		STATUS current
		DESCRIPTION
			"This property sets or gets the port's signal
			monitoring state. Disabling port signal monitoring 
			will not provide any signal alarms and performances
			information to the user.
			-----------------------------
			omtp11PlusInterfaceNumber:
			1 - CLIENT-1
			2 - LINE-1
			-----------------------------
			Values:
			1 - Port Signal Monitoring is enabled
			0 - Port Signal Monitoring is disabled
			-----------------------------"

		::= { omtp11PlusConfigurationEntry 43 }
		
	omtp11PlusPortOpticalMonitorState OBJECT-TYPE
		SYNTAX INTEGER
		MAX-ACCESS read-write
		STATUS current
		DESCRIPTION
			"This property sets or gets the port's optical
			monitoring state. Disabling port optical monitoring 
			will not provide any optical alarms and performances
			information to the user.
			-----------------------------
			omtp11PlusInterfaceNumber:
			1 - CLIENT-1
			2 - LINE-1
			-----------------------------
			Values:
			1 - Port Optical Monitoring is enabled
			0 - Port Optical Monitoring is disabled
			-----------------------------"
		::= { omtp11PlusConfigurationEntry 44 }

	omtp11PlusClearSignalPerformance OBJECT-TYPE
		SYNTAX INTEGER
		MAX-ACCESS read-write
		STATUS current
		DESCRIPTION
			"Valid only as a SET command.
			Clears signal performance for the requested port
			-----------------------------
			omtp11PlusInterfaceNumber:
			1 - CLIENT-1
			2 - LINE-1
			-----------------------------
			Values:
			Dont care, any value
			eg: 0
			-----------------------------"
		::= { omtp11PlusConfigurationEntry 45 }
		
	omtp11PlusAlsState OBJECT-TYPE
		SYNTAX INTEGER
		MAX-ACCESS read-write
		STATUS current
		DESCRIPTION
			"Set the Automatic Laser Switching(ALS) mode for
			for requested port. Based on the RX LOS state of the
			port, the transmit LASER state will be controlled
			according to the algorithm defined for ALS in
			ITUT 664 Standard
			-----------------------------
			omtp11PlusInterfaceNumber:
			1 - CLIENT-1
			2 - LINE-1
			-----------------------------
			Values: 
			1 - Enable ALS state
			0 - Disable ALS state
			-----------------------------" 
		::= { omtp11PlusConfigurationEntry 46 }
		
	omtp11PlusAlsPulseRepetitionTime OBJECT-TYPE
		SYNTAX INTEGER
		MAX-ACCESS read-write
		STATUS current
		DESCRIPTION
			"Pulse repetition time is the time for automatic 
			restart of XFP LASER once the ALS algorithm starts.
			-----------------------------
			omtp11PlusInterfaceNumber:
			1 - CLIENT-1
			2 - LINE-1
			-----------------------------
			Values: 
			100 seconds to 300 seconds
			-----------------------------" 
		::= { omtp11PlusConfigurationEntry 47 }
		
	omtp11PlusOtuFecConfiguration OBJECT-TYPE
		SYNTAX INTEGER
		MAX-ACCESS read-write
		STATUS current
		DESCRIPTION
			"Set or Get FEC type for requested port configured with
			 OTU2 traffic.
			-----------------------------
			omtp11PlusInterfaceNumber:
			1 - CLIENT-1
			2 - LINE-1
			-----------------------------
			Values: 
			00 - UFEC (I.7 FEC)
			13 - Reed-Solomon GFEC
			14 - Zero FEC 
			-----------------------------" 
		::= { omtp11PlusConfigurationEntry 61 }

	omtp11PlusOtuSignalFailThreshold OBJECT-TYPE
		SYNTAX INTEGER
		MAX-ACCESS read-write
		STATUS current
		DESCRIPTION
			"Set or Get SM Signal Failure 
			Threshold value for the requested port configured with 
			OTU2 traffic.
			-----------------------------
			omtp11PlusInterfaceNumber:
			1 - CLIENT-1
			2 - LINE-1
			-----------------------------
			Values: 
			03 - 1.E -03
			04 - 1.E -04
			05 - 1.E -05
			-----------------------------" 
		::= { omtp11PlusConfigurationEntry 62 }
		
	omtp11PlusOtuSignalDegradeThreshold OBJECT-TYPE
		SYNTAX INTEGER
		MAX-ACCESS read-write
		STATUS current
		DESCRIPTION
			"Set or Get SM Signal Degrade 
			Threshold value for the requested port configured with 
			OTU2 traffic.
			-----------------------------
			omtp11PlusInterfaceNumber:
			1 - CLIENT-1
			2 - LINE-1
			-----------------------------
			Values:
			05 - 1.E -05
			06 - 1.E -06
			07 - 1.E -07
			08 - 1.E -08
			09 - 1.E -09
			10 - 1.E -10
			-----------------------------" 
		::= { omtp11PlusConfigurationEntry 63 }
		
	omtp11PlusOtuAlarmIndicationSignalAlarmInsertion OBJECT-TYPE
		SYNTAX INTEGER
		MAX-ACCESS read-write
		STATUS current
		DESCRIPTION
			"Inserts OTU-AIS maitainance signal for the requested
			port configured with OTU2 traffic.
			-----------------------------
			omtp11PlusInterfaceNumber:
			1 - CLIENT-1
			2 - LINE-1
			-----------------------------
			Values: 
			0 - Disable Insertion  
			1 - Enable Insertion
			-----------------------------" 
		::= { omtp11PlusConfigurationEntry 64 }
		
	omtp11PlusOtuSapiTransmitTraceMessage OBJECT-TYPE
		SYNTAX DisplayString
		MAX-ACCESS read-write
		STATUS current
		DESCRIPTION
			"Set or get the 15 characters SAPI Transmit TTI message
			which is put into the outgoing OTU2 frame. 
			-----------------------------
			omtp11PlusInterfaceNumber:
			1 - CLIENT-1
			2 - LINE-1
			-----------------------------
			Values:
			eg: 123451234512345
			-----------------------------" 
		::= { omtp11PlusConfigurationEntry 65 }

	omtp11PlusOtuDapiTransmitTraceMessage OBJECT-TYPE
		SYNTAX DisplayString
		MAX-ACCESS read-write
		STATUS current
		DESCRIPTION
			"Set or get the 15 characters DAPI Transmit TTI message
			which is put into the outgoing OTU2 frame. 
			-----------------------------
			omtp11PlusInterfaceNumber:
			1 - CLIENT-1
			2 - LINE-1
			-----------------------------
			Values:
			eg: 123451234512345
			-----------------------------" 
		::= { omtp11PlusConfigurationEntry 66 }
		
	omtp11PlusOtuOperatorSpecificTransmitTraceMessage OBJECT-TYPE
		SYNTAX DisplayString
		MAX-ACCESS read-write
		STATUS current
		DESCRIPTION
			"Set or get the 32 characters Operator Specific Transmit
			TTI message which is put into the outgoing OTU2 frame. 
			-----------------------------
			omtp11PlusInterfaceNumber:
			1 - CLIENT-1
			2 - LINE-1
			-----------------------------
			Values:
			eg: 12345123451234512345123451234500
			-----------------------------" 
		::= { omtp11PlusConfigurationEntry 67 }
		
	omtp11PlusOtuSapiExpectedTraceMessage OBJECT-TYPE
		SYNTAX DisplayString
		MAX-ACCESS read-write
		STATUS current
		DESCRIPTION
			"15 characters SM SAPI Expected TTI message - Message
			set here is used for comparison with the message present
			in SM SAPI field of the incoming OTU2 frames.
			-----------------------------
			omtp11PlusInterfaceNumber:
			1 - CLIENT-1
			2 - LINE-1
			-----------------------------
			Values:
			eg: 123451234512345
			-----------------------------" 
		::= { omtp11PlusConfigurationEntry 68 }
		
	omtp11PlusOtuDapiExpectedTraceMessage OBJECT-TYPE
		SYNTAX DisplayString
		MAX-ACCESS read-write
		STATUS current
		DESCRIPTION
			"15 characters SM DAPI Expected TTI message - Message
			set here is used for comparison with the message present
			in SM DAPI field of the incoming OTU2 frames.
			-----------------------------
			omtp11PlusInterfaceNumber:
			1 - CLIENT-1
			2 - LINE-1
			-----------------------------
			Values:
			eg: 123451234512345
			-----------------------------" 
		::= { omtp11PlusConfigurationEntry 69 }

	omtp11PlusOtuOperatorSpecificExpectedTraceMessage OBJECT-TYPE
		SYNTAX DisplayString
		MAX-ACCESS read-write
		STATUS current
		DESCRIPTION
			"32 characters SM Operator Specific Expected TTI 
			message - Message set here is used for comparison with 
			the message present in SM Operator Specific field of 
			the incoming OTU2 frames.
			-----------------------------
			omtp11PlusInterfaceNumber:
			1 - CLIENT-1
			2 - LINE-1
			-----------------------------
			Values:
			eg: 12345123451234512345123451234500
			-----------------------------" 
		::= { omtp11PlusConfigurationEntry 70 }
		
	omtp11PlusOtuSapiReceivedTraceMessage OBJECT-TYPE
		SYNTAX DisplayString
		MAX-ACCESS read-only
		STATUS current
		DESCRIPTION
			"Gets the 15 characters SAPI TTI message
			which is extracted from the incoming OTU2
			data stream.
			-----------------------------
			omtp11PlusInterfaceNumber:
			1 - CLIENT-1
			2 - LINE-1
			-----------------------------
			Values:
			eg: 123451234512345
			-----------------------------" 
		::= { omtp11PlusConfigurationEntry 71 }

	omtp11PlusOtuDapiReceivedTraceMessage OBJECT-TYPE
		SYNTAX DisplayString
		MAX-ACCESS read-only
		STATUS current
		DESCRIPTION
			"Gets the 15 characters DAPI TTI message
			which is extracted from the incoming OTU2 data
			stream.
			-----------------------------
			omtp11PlusInterfaceNumber:
			1 - CLIENT-1
			2 - LINE-1
			-----------------------------
			Values:
			eg: 123451234512345
			-----------------------------" 
		::= { omtp11PlusConfigurationEntry 72 }
		
	omtp11PlusOtuOperatorSpecificReceivedTraceMessage OBJECT-TYPE
		SYNTAX DisplayString
		MAX-ACCESS read-only
		STATUS current
		DESCRIPTION
			"Gets the 32 characters DAPI TTI message
			which is extracted from the incoming OTU2 data
			stream. 
			-----------------------------
			omtp11PlusInterfaceNumber:
			1 - CLIENT-1
			2 - LINE-1
			-----------------------------
			Values:
			eg: 12345123451234512345123451234500
			-----------------------------" 
		::= { omtp11PlusConfigurationEntry 73 }

	omtp11PlusOduSignalFailThreshold OBJECT-TYPE
		SYNTAX INTEGER
		MAX-ACCESS read-write
		STATUS current
		DESCRIPTION
			"Set or Get PM Signal Failure 
			Threshold value for the requested port configured with 
			OTU2 traffic.
			-----------------------------
			omtp11PlusInterfaceNumber:
			1 - CLIENT-1
			2 - LINE-1
			-----------------------------
			Values: 
			03 - 1.E -03
			04 - 1.E -04
			05 - 1.E -05
			-----------------------------" 
		::= { omtp11PlusConfigurationEntry 81 }
		
	omtp11PlusOduSignalDegradeThreshold OBJECT-TYPE
		SYNTAX INTEGER
		MAX-ACCESS read-write
		STATUS current
		DESCRIPTION
			"Set or Get PM Signal Degrade 
			Threshold value for the requested port configured with 
			OTU2 traffic.
			-----------------------------
			omtp11PlusInterfaceNumber:
			1 - CLIENT-1
			2 - LINE-1
			-----------------------------
			Values:
			05 - 1.E -05
			06 - 1.E -06
			07 - 1.E -07
			08 - 1.E -08
			09 - 1.E -09
			10 - 1.E -10
			-----------------------------" 
		::= { omtp11PlusConfigurationEntry 82 }
		
	omtp11PlusOduAlarmIndicationSignalAlarmInsertion OBJECT-TYPE
		SYNTAX INTEGER
		MAX-ACCESS read-write
		STATUS current
		DESCRIPTION
			"Inserts ODU-AIS maintenance signal for the requested 
			port configured with OTU2 traffic.
			-----------------------------
			omtp11PlusInterfaceNumber:
			1 - CLIENT-1
			2 - LINE-1
			-----------------------------
			Values: 
			1 - Enable Insertion
			0 - Disable Insertion  
			-----------------------------"
		::= { omtp11PlusConfigurationEntry 83 }

	omtp11PlusOduLockedDefectAlarmInsertion OBJECT-TYPE
		SYNTAX INTEGER
		MAX-ACCESS read-write
		STATUS current
		DESCRIPTION
			"Inserts ODU-LCK maintenance signal for the requested 
			port configured with OTU2 traffic.
			-----------------------------
			omtp11PlusInterfaceNumber:
			1 - CLIENT-1
			2 - LINE-1
			-----------------------------
			Values: 
			1 - Enable Insertion
			0 - Disable Insertion  
			-----------------------------"
		::= { omtp11PlusConfigurationEntry 84 }
		
	omtp11PlusOduOpenConnectionIndicationAlarmInsertion OBJECT-TYPE
		SYNTAX INTEGER
		MAX-ACCESS read-write
		STATUS current
		DESCRIPTION
			"Inserts ODU-OCI maintenance signal for the requested 
			port configured with OTU2 traffic.
			-----------------------------
			omtp11PlusInterfaceNumber:
			1 - CLIENT-1
			2 - LINE-1
			-----------------------------
			Values: 
			1 - Enable Insertion
			0 - Disable Insertion  
			-----------------------------"
		::= { omtp11PlusConfigurationEntry 85 }
		
	omtp11PlusOduSapiTransmitTraceMessage OBJECT-TYPE
		SYNTAX DisplayString
		MAX-ACCESS read-write
		STATUS current
		DESCRIPTION
			"Set or get the 15 characters SAPI Transmit TTI message
			which is put into the outgoing OTU2 frame at the PM level. 
			-----------------------------
			omtp11PlusInterfaceNumber:
			1 - CLIENT-1
			2 - LINE-1
			-----------------------------
			Values:
			eg: 123451234512345
			-----------------------------" 
		::= { omtp11PlusConfigurationEntry 86 }
		
	omtp11PlusOduDapiTransmitTraceMessage OBJECT-TYPE
		SYNTAX DisplayString
		MAX-ACCESS read-write
		STATUS current
		DESCRIPTION
			"Set or get the 15 characters DAPI Transmit TTI message
			which is put into the outgoing OTU2 frame at the PM level. 
			-----------------------------
			omtp11PlusInterfaceNumber:
			1 - CLIENT-1
			2 - LINE-1
			-----------------------------
			Values:
			eg: 123451234512345
			-----------------------------" 
		::= { omtp11PlusConfigurationEntry 87 }
		
	omtp11PlusOduOperatorSpecificTransmitTraceMessage OBJECT-TYPE
		SYNTAX DisplayString
		MAX-ACCESS read-write
		STATUS current
		DESCRIPTION
			"Set or get the 32 characters Operator Specific Transmit
			TTI message which is put into the outgoing OTU2 frame at
			the PM level. 
			-----------------------------
			omtp11PlusInterfaceNumber:
			1 - CLIENT-1
			2 - LINE-1
			-----------------------------
			Values:
			eg: 12345123451234512345123451234500
			-----------------------------" 
		::= { omtp11PlusConfigurationEntry 88 }
		
	omtp11PlusOduSapiExpectedTraceMessage OBJECT-TYPE
		SYNTAX DisplayString
		MAX-ACCESS read-write
		STATUS current
		DESCRIPTION
			"15 characters PM SAPI Expected TTI message - Message
			set here is used for comparison with the message present
			in PM SAPI field of the incoming OTU2 frames.
			-----------------------------
			omtp11PlusInterfaceNumber:
			1 - CLIENT-1
			2 - LINE-1
			-----------------------------
			Values:
			eg: 123451234512345
			-----------------------------" 
		::= { omtp11PlusConfigurationEntry 89 }

	omtp11PlusOduDapiExpectedTraceMessage OBJECT-TYPE
		SYNTAX DisplayString
		MAX-ACCESS read-write
		STATUS current
		DESCRIPTION
			"15 characters PM DAPI Expected TTI message - Message
			set here is used for comparison with the message present
			in PM DAPI field of the incoming OTU2 frames.
			-----------------------------
			omtp11PlusInterfaceNumber:
			1 - CLIENT-1
			2 - LINE-1
			-----------------------------
			Values:
			eg: 123451234512345
			-----------------------------" 
		::= { omtp11PlusConfigurationEntry 90 }
		
	omtp11PlusOduOperatorSpecificExpectedTraceMessage OBJECT-TYPE
		SYNTAX DisplayString
		MAX-ACCESS read-write
		STATUS current
		DESCRIPTION
			"32 characters PM Operator Specific Expected TTI 
			message - Message set here is used for comparison with 
			the message present in PM DAPI field of the incoming
			OTU2 frames.
			-----------------------------
			omtp11PlusInterfaceNumber:
			1 - CLIENT-1
			2 - LINE-1
			-----------------------------
			Values:
			eg: 12345123451234512345123451234500
			-----------------------------" 
		::= { omtp11PlusConfigurationEntry 91 }

	omtp11PlusOduSapiReceivedTraceMessage OBJECT-TYPE
		SYNTAX DisplayString
		MAX-ACCESS read-only
		STATUS current
		DESCRIPTION
			"Gets the 15 characters SAPI TTI message
			which is extracted from the incoming OTU2 data
			stream.
			-----------------------------
			omtp11PlusInterfaceNumber:
			1 - CLIENT-1
			2 - LINE-1
			-----------------------------
			Values:
			eg: 123451234512345
			-----------------------------" 
		::= { omtp11PlusConfigurationEntry 92 }

	omtp11PlusOduDapiReceivedTraceMessage OBJECT-TYPE
		SYNTAX DisplayString
		MAX-ACCESS read-only
		STATUS current
		DESCRIPTION
			"Gets the 15 characters DAPI TTI message
			which is extracted from the incoming OTU2
			data stream.
			-----------------------------
			omtp11PlusInterfaceNumber:
			1 - CLIENT-1
			2 - LINE-1
			-----------------------------
			Values:
			eg: 123451234512345
			-----------------------------" 
		::= {omtp11PlusConfigurationEntry 93 }
		
	omtp11PlusOduOperatorSpecificReceivedTraceMessage OBJECT-TYPE
		SYNTAX DisplayString
		MAX-ACCESS read-only
		STATUS current
		DESCRIPTION
			"Gets the 32 characters DAPI TTI message
			which is extracted from the incoming OTU2
			data stream.
			-----------------------------
			omtp11PlusInterfaceNumber:
			1 - CLIENT-1
			2 - LINE-1
			-----------------------------
			Values:
			eg: 12345123451234512345123451234500
			-----------------------------" 
		::= { omtp11PlusConfigurationEntry 94 }

	omtp11PlusOpuTransmitPayloadType OBJECT-TYPE
		SYNTAX INTEGER
		MAX-ACCESS read-only
		STATUS current
		DESCRIPTION
			"A one-byte payload type signal is defined in the PSI[0]
			byte of the payload structure identifier to indicate the
			composition of the OPUk signal. Gets the payload type
			that is put into the outgoing OTU2 datastream.
			-----------------------------
			omtp11PlusInterfaceNumber:
			1 - CLIENT-1
			2 - LINE-1
			-----------------------------
			Values:
			eg: 20
			-----------------------------" 
		::= { omtp11PlusConfigurationEntry 95 }
		
	omtp11PlusOpuReceivedPayloadType OBJECT-TYPE
		SYNTAX INTEGER
		MAX-ACCESS read-only
		STATUS current
		DESCRIPTION
			"Gives Payload Type present in Opu overhead that tells
			about the mapping informations.
			-----------------------------
			omtp11PlusInterfaceNumber:
			1 - CLIENT-1
			2 - LINE-1
			-----------------------------
			Values:
			eg: 21
			-----------------------------" 
		::= { omtp11PlusConfigurationEntry 96 }
		
	omtp11PlusSdhMsB2ExcessiveErrorThreshold OBJECT-TYPE
		SYNTAX INTEGER
		MAX-ACCESS read-write
		STATUS current
		DESCRIPTION
			"Set or Get B2 Signal Failure Threshold value for the 
			requested port configured with SDH traffic.
			-----------------------------
			omtp11PlusInterfaceNumber:
			1 - CLIENT-1
			-----------------------------
			Values:
			03 - 1.E -03
			04 - 1.E -04
			05 - 1.E -05
			-----------------------------" 
		::= { omtp11PlusConfigurationEntry 101 }

	omtp11PlusSdhMsB2SignalDegradeThreshold OBJECT-TYPE
		SYNTAX INTEGER
		MAX-ACCESS read-write
		STATUS current
		DESCRIPTION
			"Set or Get B2 Signal Degrade Threshold value for the 
			requested port configured with SDH traffic.
			-----------------------------
			omtp11PlusInterfaceNumber:
			1 - CLIENT-1
			-----------------------------
			Values:
			06 - 1.E -06
			07 - 1.E -07
			08 - 1.E -08
			09 - 1.E -09
			10 - 1.E -10
			-----------------------------" 
		::= { omtp11PlusConfigurationEntry 102 }
		
	omtp11PlusWan10gMsB2ExcessiveErrorThreshold OBJECT-TYPE
		SYNTAX INTEGER
		MAX-ACCESS read-write
		STATUS current
		DESCRIPTION
			"Set or Get B2 Signal Failure Threshold value for the 
			requested port configured with WAN traffic.
			-----------------------------
			omtp11PlusInterfaceNumber:
			1 - CLIENT-1
			-----------------------------
			Values:
			03 - 1.E -03
			04 - 1.E -04
			05 - 1.E -05
			-----------------------------" 

		::= { omtp11PlusConfigurationEntry 111 }
		
	omtp11PlusWan10gMsB2SignalDegradeThreshold OBJECT-TYPE
		SYNTAX INTEGER
		MAX-ACCESS read-write
		STATUS current
		DESCRIPTION
			"Set or Get B2 Signal Degrade Threshold value for the 
			requested port configured with WAN traffic.
			-----------------------------
			omtp11PlusInterfaceNumber:
			1 - CLIENT-1
			-----------------------------
			Values:
			06 - 1.E -06
			07 - 1.E -07
			08 - 1.E -08
			09 - 1.E -09
			10 - 1.E -10
			-----------------------------" 
		::= { omtp11PlusConfigurationEntry 112 }
				
	omtp11PlusTunableXfpLaserWavelength OBJECT-TYPE
		SYNTAX INTEGER
		MAX-ACCESS read-write
		STATUS current
		DESCRIPTION
			"Set or Get the XFP wavelength for the requested port
			-----------------------------
			omtp11PlusInterfaceNumber:
			1 - CLIENT-1
			2 - LINE-1
			-----------------------------
			Values:
			eg: 1529.944
			-----------------------------" 
		::= { omtp11PlusConfigurationEntry 113 }
		
	omtp11PlusTunableXfpLaserChannelNumber OBJECT-TYPE
		SYNTAX INTEGER
		MAX-ACCESS read-write
		STATUS current
		DESCRIPTION
			"Set or Get the XFP Channel Number for the the requested
			port
			-----------------------------
			omtp11PlusInterfaceNumber:
			1 - CLIENT-1
			2 - LINE-1
			-----------------------------
			Values:
			eg: 10
			-----------------------------" 
		::= { omtp11PlusConfigurationEntry 114 }

	omtp11PlusXfpLaserState OBJECT-TYPE
		SYNTAX INTEGER
		MAX-ACCESS read-write
		STATUS current
		DESCRIPTION
			"Set or Get the XFP LASER state for the the requested
			port
			-----------------------------
			omtp11PlusInterfaceNumber:
			1 - CLIENT-1
			2 - LINE-1
			-----------------------------
			Values: 
			00 - Laser OFF
			01 - Laser ON
			-----------------------------" 
		::= { omtp11PlusConfigurationEntry 115 }
		
	omtp11PlusXfpReset OBJECT-TYPE
		SYNTAX INTEGER
		MAX-ACCESS read-write
		STATUS current
		DESCRIPTION
			"Valid only as a SET command.
			Resets the XFP.
			-----------------------------
			omtp11PlusInterfaceNumber:
			1 - CLIENT-1
			2 - LINE-1
			-----------------------------
			Values: 
			Dont care, any value
			eg: 0
			-----------------------------" 
		::= { omtp11PlusConfigurationEntry 116 }
		
	omtp11PlusXfpPowerDownMode OBJECT-TYPE
		SYNTAX INTEGER
		MAX-ACCESS read-write
		STATUS current
		DESCRIPTION
			"Valid only as a SET command.
			Sets the XFP in the Power Down mode i.e. low power 
			consumption mode.
			-----------------------------
			omtp11PlusInterfaceNumber:
			1 - CLIENT-1
			2 - LINE-1
			-----------------------------
			Values: 
			01 - power down XFP
			-----------------------------" 
		::= { omtp11PlusConfigurationEntry 117 }
		
	omtp11PlusXfpLineLoopback OBJECT-TYPE
		SYNTAX INTEGER
		MAX-ACCESS read-write
		STATUS current
		DESCRIPTION
			"Set or Get line loopback in XFP			
			-----------------------------
			omtp11PlusInterfaceNumber:
			1 - CLIENT-1
			2 - LINE-1
			-----------------------------
			Values: 
			1 - Enable XFP Line Loopback
			0 - Disable XFP Line Loopback
			-----------------------------" 
		::= { omtp11PlusConfigurationEntry 118 }

	omtp11PlusXfpXfiLoopback OBJECT-TYPE
		SYNTAX INTEGER
		MAX-ACCESS read-write
		STATUS current
		DESCRIPTION
			"Set or Get Xfi loopback in XFP			
			-----------------------------
			omtp11PlusInterfaceNumber:
			1 - CLIENT-1
			2 - LINE-1
			-----------------------------
			Values: 
			1 - Enable XFP Xfi Loopback
			0 - Disable XFP Xfi Loopback
			-----------------------------" 
		::= { omtp11PlusConfigurationEntry 119 }
		
	omtp11PlusXfpAmplitudeThresholdOfReceiverForFecControl OBJECT-TYPE
		SYNTAX INTEGER
		MAX-ACCESS read-write
		STATUS current
		DESCRIPTION
			" Set or Get amplitude threshold of receiver for FEC control			
			-----------------------------
			omtp11PlusInterfaceNumber:
			1 - CLIENT-1
			2 - LINE-1
			-----------------------------
			Values: 
			eg: Reserved
			-----------------------------" 
		::= { omtp11PlusConfigurationEntry 120 }
		
	omtp11PlusXfpPhaseInEyeDiagramForFecControl OBJECT-TYPE
		SYNTAX INTEGER
		MAX-ACCESS read-write
		STATUS current
		DESCRIPTION
			" Set or Get XFP phase in eye diagram for FEC control			
			-----------------------------
			omtp11PlusInterfaceNumber:
			1 - CLIENT-1
			2 - LINE-1
			-----------------------------
			Values: 
			eg: Reserved
			-----------------------------" 
		::= { omtp11PlusConfigurationEntry 121 }
		
	omtp11PlusXfpSystemReportingBer OBJECT-TYPE
		SYNTAX INTEGER
		MAX-ACCESS read-write
		STATUS current
		DESCRIPTION
			" Set or Get XFP system reporting BER			
			-----------------------------
			omtp11PlusInterfaceNumber:
			1 - CLIENT-1
			2 - LINE-1
			-----------------------------
			Values: 
			eg: Reserved
			-----------------------------" 
		::= { omtp11PlusConfigurationEntry 122 }

	omtp11PlusXfpHighTemperatureAlarmThreshold OBJECT-TYPE
		SYNTAX DisplayString
		MAX-ACCESS read-write
		STATUS current
		DESCRIPTION
			"Set or Get High Temperature Alarm Threshold
			(in degree celsius) for the requested port
			-----------------------------
			omtp11PlusInterfaceNumber:
			1 - CLIENT-1
			2 - LINE-1
			-----------------------------
			Values: 
			eg: 65 
			-----------------------------" 
		::= { omtp11PlusConfigurationEntry 131 }
		
	omtp11PlusXfpLowTemperatureAlarmThreshold OBJECT-TYPE
		SYNTAX DisplayString
		MAX-ACCESS read-write
		STATUS current
		DESCRIPTION
			"Set or Get Low Temperature Alarm Threshold
			(in degree celsius) for the requested port
			-----------------------------
			omtp11PlusInterfaceNumber:
			1 - CLIENT-1
			2 - LINE-1
			-----------------------------
			Values: 
			eg: 5 
			-----------------------------" 
		::= { omtp11PlusConfigurationEntry 132 }
		
	omtp11PlusXfpHighTemperatureWarningThreshold OBJECT-TYPE
		SYNTAX DisplayString
		MAX-ACCESS read-write
		STATUS current
		DESCRIPTION
			"Set or Get High Temperature Warning Threshold
			(in degree celsius) for the requested port
			-----------------------------
			omtp11PlusInterfaceNumber:
			1 - CLIENT-1
			2 - LINE-1
			-----------------------------
			Values: 
			eg: 60 
			-----------------------------"
		::= { omtp11PlusConfigurationEntry 133 }
		
	omtp11PlusXfpLowTemperatureWarningThreshold OBJECT-TYPE
		SYNTAX DisplayString
		MAX-ACCESS read-write
		STATUS current
		DESCRIPTION
			"Set or Get Low Temperature Warning Threshold
			(in degree celsius) for the requested port
			-----------------------------
			omtp11PlusInterfaceNumber:
			1 - CLIENT-1
			2 - LINE-1
			-----------------------------
			Values: 
			eg: 10 
			-----------------------------"
		::= { omtp11PlusConfigurationEntry 134 }

	omtp11PlusXfpHighBiasCurrentAlarmThreshold OBJECT-TYPE
		SYNTAX DisplayString
		MAX-ACCESS read-write
		STATUS current
		DESCRIPTION
			"Set or Get High Bias Current Alarm Threshold
			(in milli ampere) for the requested port
			-----------------------------
			omtp11PlusInterfaceNumber:
			1 - CLIENT-1
			2 - LINE-1
			-----------------------------
			Values:
			eg: 35.6
			-----------------------------"			
		::= { omtp11PlusConfigurationEntry 135 }
		
	omtp11PlusXfpLowBiasCurrentAlarmThreshold OBJECT-TYPE
		SYNTAX DisplayString
		MAX-ACCESS read-write
		STATUS current
		DESCRIPTION
			"Set or Get Low Bias Current Alarm Threshold
			(in milli ampere) for the requested port
			-----------------------------
			omtp11PlusInterfaceNumber:
			1 - CLIENT-1
			2 - LINE-1
			-----------------------------
			Values:
			eg: 31.1
			-----------------------------"
		::= { omtp11PlusConfigurationEntry 136 }
		
	omtp11PlusXfpHighBiasCurrentWarningThreshold OBJECT-TYPE
		SYNTAX DisplayString
		MAX-ACCESS read-write
		STATUS current
		DESCRIPTION
			"Set or Get High Bias Current Warning Threshold
			(in milli ampere) for the requested port
			-----------------------------
			omtp11PlusInterfaceNumber:
			1 - CLIENT-1
			2 - LINE-1
			-----------------------------
			Values:
			eg: 34.5
			-----------------------------"
		::= { omtp11PlusConfigurationEntry 137 }
		
	omtp11PlusXfpLowBiasCurrentWarningThreshold OBJECT-TYPE
		SYNTAX DisplayString
		MAX-ACCESS read-write
		STATUS current
		DESCRIPTION
			"Set or Get Low Bias Current Warning Threshold
			(in milli ampere) for the requested port
			-----------------------------
			omtp11PlusInterfaceNumber:
			1 - CLIENT-1
			2 - LINE-1
			-----------------------------
			Values:
			eg: 32.8
			-----------------------------"
		::= { omtp11PlusConfigurationEntry 138 }
		
	omtp11PlusXfpInputHighPowerAlarmThreshold OBJECT-TYPE
		SYNTAX DisplayString
		MAX-ACCESS read-write
		STATUS current
		DESCRIPTION
			"Set or Get Input High Power Alarm Threshold
			(in dbm) for the requested port
			-----------------------------
			omtp11PlusInterfaceNumber:
			1 - CLIENT-1
			2 - LINE-1
			-----------------------------
			Values:
			eg: -9.1
			-----------------------------"
		::= { omtp11PlusConfigurationEntry 139 }

	omtp11PlusXfpInputLowPowerAlarmThreshold OBJECT-TYPE
		SYNTAX DisplayString
		MAX-ACCESS read-write
		STATUS current
		DESCRIPTION
			"Set or Get Input Low Power Alarm Threshold
			(in dbm) for the requested port
			-----------------------------
			omtp11PlusInterfaceNumber:
			1 - CLIENT-1
			2 - LINE-1
			-----------------------------
			Values:
			eg: -35.6
			-----------------------------"
		::= { omtp11PlusConfigurationEntry 140 }
		
	omtp11PlusXfpInputHighPowerWarningThreshold OBJECT-TYPE
		SYNTAX DisplayString
		MAX-ACCESS read-write
		STATUS current
		DESCRIPTION
			"Set or Get Input High Power Warning Threshold
			(in dbm) for the requested port
			-----------------------------
			omtp11PlusInterfaceNumber:
			1 - CLIENT-1
			2 - LINE-1
			-----------------------------
			Values:
			eg: -11.2
			-----------------------------"
		::= { omtp11PlusConfigurationEntry 141 }
		
	omtp11PlusXfpInputLowPowerWarningThreshold OBJECT-TYPE
		SYNTAX DisplayString
		MAX-ACCESS read-write
		STATUS current
		DESCRIPTION
			"Set or Get Input Low Power Warning Threshold
			(in dbm) for the requested port
			-----------------------------
			omtp11PlusInterfaceNumber:
			1 - CLIENT-1
			2 - LINE-1
			-----------------------------
			Values:
			eg: -31.3
			-----------------------------"
		::= { omtp11PlusConfigurationEntry 142 }
		
	omtp11PlusXfpOutputHighPowerAlarmThreshold OBJECT-TYPE
		SYNTAX DisplayString
		MAX-ACCESS read-write
		STATUS current
		DESCRIPTION
			"Set or Get Output High Power Alarm Threshold
			(in dbm) for the requested port
			-----------------------------
			omtp11PlusInterfaceNumber:
			1 - CLIENT-1
			2 - LINE-1
			-----------------------------
			Values:
			eg: +2.0
			-----------------------------"
		::= { omtp11PlusConfigurationEntry 143 }

	omtp11PlusXfpOutputLowPowerAlarmThreshold OBJECT-TYPE
		SYNTAX DisplayString
		MAX-ACCESS read-write
		STATUS current
		DESCRIPTION
			"Set or Get Output Low Power Alarm Threshold
			(in dbm) for the requested port
			-----------------------------
			omtp11PlusInterfaceNumber:
			1 - CLIENT-1
			2 - LINE-1
			-----------------------------
			Values:
			eg: -3.5
			-----------------------------"
		::= { omtp11PlusConfigurationEntry 144 }
		
	omtp11PlusXfpOutputHighPowerWarningThreshold OBJECT-TYPE
		SYNTAX DisplayString
		MAX-ACCESS read-write
		STATUS current
		DESCRIPTION
			"Set or Get Output High Power Warning Threshold
			(in dbm) for the requested port
			-----------------------------
			omtp11PlusInterfaceNumber:
			1 - CLIENT-1
			2 - LINE-1
			-----------------------------
			Values:
			eg: +1.3
			-----------------------------"
		::= { omtp11PlusConfigurationEntry 145 }
		
	omtp11PlusXfpOutputLowPowerWarningThreshold OBJECT-TYPE
		SYNTAX DisplayString
		MAX-ACCESS read-write
		STATUS current
		DESCRIPTION
			"Set or Get Output Low Power Warning Threshold
			(in dbm) for the requested port
			-----------------------------
			omtp11PlusInterfaceNumber:
			1 - CLIENT-1
			2 - LINE-1
			-----------------------------
			Values:
			eg: -2.5
			-----------------------------"
		::= { omtp11PlusConfigurationEntry 146 }
		
	omtp11PlusXfpHighSupplyVoltageAlarmThreshold OBJECT-TYPE
		SYNTAX DisplayString
		MAX-ACCESS read-write
		STATUS current
		DESCRIPTION
			"Set or Get High Supply Voltage Alarm Threshold
			(in volts) for the requested port
			-----------------------------
			omtp11PlusInterfaceNumber:
			1 - CLIENT-1
			2 - LINE-1
			-----------------------------
			Values:
			eg: +3.3
			-----------------------------"
		::= { omtp11PlusConfigurationEntry 147 }

	omtp11PlusXfpLowSupplyVoltageAlarmThreshold OBJECT-TYPE
		SYNTAX DisplayString
		MAX-ACCESS read-write
		STATUS current
		DESCRIPTION
			"Set or Get Low Supply Voltage Alarm Threshold
			(in volts) for the requested port
			-----------------------------
			omtp11PlusInterfaceNumber:
			1 - CLIENT-1
			2 - LINE-1
			-----------------------------
			Values:
			eg: +3.0
			-----------------------------"
		::= { omtp11PlusConfigurationEntry 148 }
		
	omtp11PlusXfpHighSupplyVoltageWarningThreshold OBJECT-TYPE
		SYNTAX DisplayString
		MAX-ACCESS read-write
		STATUS current
		DESCRIPTION
			"Set or Get High Supply Voltage Warning Threshold
			(in volts) for the requested port
			-----------------------------
			omtp11PlusInterfaceNumber:
			1 - CLIENT-1
			2 - LINE-1
			-----------------------------
			Values:
			eg: +3.2
			-----------------------------"
		::= { omtp11PlusConfigurationEntry 149 }
		
	omtp11PlusXfpLowSupplyVoltageWarningThreshold OBJECT-TYPE
		SYNTAX DisplayString
		MAX-ACCESS read-write
		STATUS current
		DESCRIPTION
			"Set or Get Low Supply Voltage Warning Threshold
			(in volts) for the requested port
			-----------------------------
			omtp11PlusInterfaceNumber:
			1 - CLIENT-1
			2 - LINE-1
			-----------------------------
			Values:
			eg: +3.1
			-----------------------------"
		::= { omtp11PlusConfigurationEntry 150 }
		
	omtp11PlusXfpInputPowerFailureAlarmInhibit OBJECT-TYPE
	      SYNTAX  INTEGER
	      MAX-ACCESS  read-write
	      STATUS  current
	      DESCRIPTION
			"Inhibits OMTP11-PLUS XFP Input Power Failure Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 201 }

	omtp11PlusXfpOutputPowerFailureAlarmInhibit OBJECT-TYPE
	      SYNTAX  INTEGER
	      MAX-ACCESS  read-write
	      STATUS  current
	      DESCRIPTION
			"Inhibits OMTP11-PLUS XFP Output Power Failure Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 202 }

	omtp11PlusXfpHighTemperatureAlarmInhibit OBJECT-TYPE
	      SYNTAX  INTEGER
	      MAX-ACCESS  read-write
	      STATUS  current
	      DESCRIPTION
			"Inhibits OMTP11-PLUS XFP High Temperature Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 203 }

	omtp11PlusXfpLowTemperatureAlarmInhibit OBJECT-TYPE
	      SYNTAX  INTEGER
	      MAX-ACCESS  read-write
	      STATUS  current
	      DESCRIPTION
			"Inhibits OMTP11-PLUS XFP Low Temperature Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 204 }

	omtp11PlusXfpHighTemperatureWarningInhibit OBJECT-TYPE
	      SYNTAX  INTEGER
	      MAX-ACCESS  read-write
	      STATUS  current
	      DESCRIPTION
			"Inhibits OMTP11-PLUS XFP High Temperature Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 205 }

	omtp11PlusXfpLowTemperatureWarningInhibit OBJECT-TYPE
	      SYNTAX  INTEGER
	      MAX-ACCESS  read-write
	      STATUS  current
	      DESCRIPTION
			"Inhibits OMTP11-PLUS XFP Low Temperature Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 206 }

	omtp11PlusXfpHighBiasCurrentAlarmInhibit OBJECT-TYPE
	      SYNTAX  INTEGER
	      MAX-ACCESS  read-write
	      STATUS  current
	      DESCRIPTION
			"Inhibits OMTP11-PLUS XFP High Bias Current Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 207 }

	omtp11PlusXfpLowBiasCurrentAlarmInhibit OBJECT-TYPE
	      SYNTAX  INTEGER
	      MAX-ACCESS  read-write
	      STATUS  current
	      DESCRIPTION
			"Inhibits OMTP11-PLUS XFP Low Bias Current Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 208 }

	omtp11PlusXfpHighBiasCurrentWarningInhibit OBJECT-TYPE
	      SYNTAX  INTEGER
	      MAX-ACCESS  read-write
	      STATUS  current
	      DESCRIPTION
			"Inhibits OMTP11-PLUS XFP High Bias Current Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 209 }

	omtp11PlusXfpLowBiasCurrentWarningInhibit OBJECT-TYPE
	      SYNTAX  INTEGER
	      MAX-ACCESS  read-write
	      STATUS  current
	      DESCRIPTION
			"Inhibits OMTP11-PLUS XFP Low Bias Current Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 210 }

	omtp11PlusXfpInputHighPowerAlarmInhibit OBJECT-TYPE
	      SYNTAX  INTEGER
	      MAX-ACCESS  read-write
	      STATUS  current
	      DESCRIPTION
			"Inhibits OMTP11-PLUS XFP Input High Power Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 211 }

	omtp11PlusXfpInputLowPowerAlarmInhibit OBJECT-TYPE
	      SYNTAX  INTEGER
	      MAX-ACCESS  read-write
	      STATUS  current
	      DESCRIPTION
			"Inhibits OMTP11-PLUS XFP Input Low Power Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 212 }

	omtp11PlusXfpInputHighPowerWarningInhibit OBJECT-TYPE
	      SYNTAX  INTEGER
	      MAX-ACCESS  read-write
	      STATUS  current
	      DESCRIPTION
			"Inhibits OMTP11-PLUS XFP Input High Power Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 213 }

	omtp11PlusXfpInputLowPowerWarningInhibit OBJECT-TYPE
	      SYNTAX  INTEGER
	      MAX-ACCESS  read-write
	      STATUS  current
	      DESCRIPTION
			"Inhibits OMTP11-PLUS XFP Input Low Power Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 214 }

	omtp11PlusXfpOutputHighPowerAlarmInhibit OBJECT-TYPE
	      SYNTAX  INTEGER
	      MAX-ACCESS  read-write
	      STATUS  current
	      DESCRIPTION
			"Inhibits OMTP11-PLUS XFP Output High Power Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 215 }

	omtp11PlusXfpOutputLowPowerAlarmInhibit OBJECT-TYPE
	      SYNTAX  INTEGER
	      MAX-ACCESS  read-write
	      STATUS  current
	      DESCRIPTION
			"Inhibits OMTP11-PLUS XFP Output Low Power Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 216 }

	omtp11PlusXfpOutputHighPowerWarningInhibit OBJECT-TYPE
	      SYNTAX  INTEGER
	      MAX-ACCESS  read-write
	      STATUS  current
	      DESCRIPTION
			"Inhibits OMTP11-PLUS XFP Output High Power Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 217 }

	omtp11PlusXfpOutputLowPowerWarningInhibit OBJECT-TYPE
	      SYNTAX  INTEGER
	      MAX-ACCESS  read-write
	      STATUS  current
	      DESCRIPTION
			"Inhibits OMTP11-PLUS XFP Output Low Power Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 218 }

	omtp11PlusXfpHighSupplyVoltageAlarmInhibit OBJECT-TYPE
	      SYNTAX  INTEGER
	      MAX-ACCESS  read-write
	      STATUS  current
	      DESCRIPTION
			"Inhibits OMTP11-PLUS XFP High Supply Voltage Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 219 }

	omtp11PlusXfpLowSupplyVoltageAlarmInhibit OBJECT-TYPE
	      SYNTAX  INTEGER
	      MAX-ACCESS  read-write
	      STATUS  current
	      DESCRIPTION
			"Inhibits OMTP11-PLUS XFP Low Supply Voltage Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 220 }

	omtp11PlusXfpHighSupplyVoltageWarningInhibit OBJECT-TYPE
	      SYNTAX  INTEGER
	      MAX-ACCESS  read-write
	      STATUS  current
	      DESCRIPTION
			"Inhibits OMTP11-PLUS XFP High Supply Voltage Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 221 }

	omtp11PlusXfpLowSupplyVoltageWarningInhibit OBJECT-TYPE
	      SYNTAX  INTEGER
	      MAX-ACCESS  read-write
	      STATUS  current
	      DESCRIPTION
			"Inhibits OMTP11-PLUS XFP Low Supply Voltage Warning
			for the requested port
			-----------------------------
			omtp11PlusInterfaceNumber:
			1 - CLIENT-1
			2 - LINE-1
			-----------------------------
			Values:
			1 - Inhibit
			0 - Do Not Inhibit
			-----------------------------"
		::= { omtp11PlusConfigurationEntry 222 }

	omtp11PlusXfpPresenceAbsenceNotificationInhibit OBJECT-TYPE
	      SYNTAX  INTEGER
	      MAX-ACCESS  read-write
	      STATUS  current
	      DESCRIPTION
			"Inhibits OMTP11-PLUS XFP Presence Absence Notification
			for the requested port
			-----------------------------
			omtp11PlusInterfaceNumber:
			1 - CLIENT-1
			2 - LINE-1
			-----------------------------
			Values:
			1 - Inhibit
			0 - Do Not Inhibit
			-----------------------------"
		::= { omtp11PlusConfigurationEntry 223 }

	omtp11PlusOtuLossOfSignalAlarmInhibit OBJECT-TYPE
	      SYNTAX  INTEGER
	      MAX-ACCESS  read-write
	      STATUS  current
	      DESCRIPTION
			"Inhibits OMTP11-PLUS OTU Loss Of Signal Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 231 }

	omtp11PlusOtuLossOfFrameAlarmInhibit OBJECT-TYPE
	      SYNTAX  INTEGER
	      MAX-ACCESS  read-write
	      STATUS  current
	      DESCRIPTION
			"Inhibits OMTP11-PLUS OTU Loss Of Frame Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 232 }

	omtp11PlusOtuOutOfFrameAlarmInhibit OBJECT-TYPE
	      SYNTAX  INTEGER
	      MAX-ACCESS  read-write
	      STATUS  current
	      DESCRIPTION
			"Inhibits OMTP11-PLUS OTU Out Of Frame Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 233 }

	omtp11PlusOtuLossOfMultiFrameAlarmInhibit OBJECT-TYPE
	      SYNTAX  INTEGER
	      MAX-ACCESS  read-write
	      STATUS  current
	      DESCRIPTION
			"Inhibits OMTP11-PLUS OTU Loss Of Multi Frame Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 234 }

	omtp11PlusOtuOutOfMultiFrameAlarmInhibit OBJECT-TYPE
	      SYNTAX  INTEGER
	      MAX-ACCESS  read-write
	      STATUS  current
	      DESCRIPTION
			"Inhibits OMTP11-PLUS OTU Out Of Multi Frame Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 235 }

	omtp11PlusOtuSignalFailAlarmInhibit OBJECT-TYPE
	      SYNTAX  INTEGER
	      MAX-ACCESS  read-write
	      STATUS  current
	      DESCRIPTION
			"Inhibits OMTP11-PLUS OTU Signal Fail Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 236 }

	omtp11PlusOtuSignalDegradeAlarmInhibit OBJECT-TYPE
	      SYNTAX  INTEGER
	      MAX-ACCESS  read-write
	      STATUS  current
	      DESCRIPTION
			"Inhibits OMTP11-PLUS OTU Signal Degrade Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 237 }

	omtp11PlusOtuAlarmIndicationSignalAlarmInhibit OBJECT-TYPE
	      SYNTAX  INTEGER
	      MAX-ACCESS  read-write
	      STATUS  current
	      DESCRIPTION
			"Inhibits OMTP11-PLUS OTU Alarm Indication Signal Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 238 }

	omtp11PlusOtuIncomingAlignmentErrorAlarmInhibit OBJECT-TYPE
	      SYNTAX  INTEGER
	      MAX-ACCESS  read-write
	      STATUS  current
	      DESCRIPTION
			"Inhibits OMTP11-PLUS OTU Incoming Alignment Error Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 239 }

	omtp11PlusOtuTraceIdentifierMismatchAlarmInhibit OBJECT-TYPE
	      SYNTAX  INTEGER
	      MAX-ACCESS  read-write
	      STATUS  current
	      DESCRIPTION
			"Inhibits OMTP11-PLUS OTU Trace Identifier Mismatch Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 240 }

	omtp11PlusOtuBackwardIncomingAlignmentErrorAlarmInhibit OBJECT-TYPE
	      SYNTAX  INTEGER
	      MAX-ACCESS  read-write
	      STATUS  current
	      DESCRIPTION
			"Inhibits OMTP11-PLUS OTU Backward Incoming Alignment Error Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 241 }

	omtp11PlusOtuBackwardDefectIndicationAlarmInhibit OBJECT-TYPE
	      SYNTAX  INTEGER
	      MAX-ACCESS  read-write
	      STATUS  current
	      DESCRIPTION
			"Inhibits OMTP11-PLUS OTU Backward Defect Indication Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 242 }

	omtp11PlusOduSignalFailAlarmInhibit OBJECT-TYPE
	      SYNTAX  INTEGER
	      MAX-ACCESS  read-write
	      STATUS  current
	      DESCRIPTION
			"Inhibits OMTP11-PLUS ODU Signal Fail Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 251 }

	omtp11PlusOduSignalDegradeAlarmInhibit OBJECT-TYPE
	      SYNTAX  INTEGER
	      MAX-ACCESS  read-write
	      STATUS  current
	      DESCRIPTION
			"Inhibits OMTP11-PLUS ODU Signal Degrade Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 252 }

	omtp11PlusOduAlarmIndicationSignalAlarmInhibit OBJECT-TYPE
	      SYNTAX  INTEGER
	      MAX-ACCESS  read-write
	      STATUS  current
	      DESCRIPTION
			"Inhibits OMTP11-PLUS ODU Alarm Indication Signal Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 253 }

	omtp11PlusOduTcm1IncomingAlignmentErrorAlarmInhibit OBJECT-TYPE
	      SYNTAX  INTEGER
	      MAX-ACCESS  read-write
	      STATUS  current
	      DESCRIPTION
			"Inhibits OMTP11-PLUS ODU TCM1 Incoming Alignment Error 
			Alarm for the requested port
			-----------------------------
			omtp11PlusInterfaceNumber:
			1 - CLIENT-1
			2 - LINE-1
			-----------------------------
			Values:
			1 - Inhibit
			0 - Do Not Inhibit
			-----------------------------"
		::= { omtp11PlusConfigurationEntry 254 }

	omtp11PlusOduTcm2IncomingAlignmentErrorAlarmInhibit OBJECT-TYPE
	      SYNTAX  INTEGER
	      MAX-ACCESS  read-write
	      STATUS  current
	      DESCRIPTION
			"Inhibits OMTP11-PLUS ODU TCM2 Incoming Alignment Error 
			Alarm for the requested port
			-----------------------------
			omtp11PlusInterfaceNumber:
			1 - CLIENT-1
			2 - LINE-1
			-----------------------------
			Values:
			1 - Inhibit
			0 - Do Not Inhibit
			-----------------------------"
		::= { omtp11PlusConfigurationEntry 255 }

	omtp11PlusOduTcm3IncomingAlignmentErrorAlarmInhibit OBJECT-TYPE
	      SYNTAX  INTEGER
	      MAX-ACCESS  read-write
	      STATUS  current
	      DESCRIPTION
			"Inhibits OMTP11-PLUS ODU TCM3 Incoming Alignment Error 
			Alarm for the requested port
			-----------------------------
			omtp11PlusInterfaceNumber:
			1 - CLIENT-1
			2 - LINE-1
			-----------------------------
			Values:
			1 - Inhibit
			0 - Do Not Inhibit
			-----------------------------"
		::= { omtp11PlusConfigurationEntry 256 }

	omtp11PlusOduTcm4IncomingAlignmentErrorAlarmInhibit OBJECT-TYPE
	      SYNTAX  INTEGER
	      MAX-ACCESS  read-write
	      STATUS  current
	      DESCRIPTION
			"Inhibits OMTP11-PLUS ODU TCM4 Incoming Alignment Error 
			Alarm for the requested port
			-----------------------------
			omtp11PlusInterfaceNumber:
			1 - CLIENT-1
			2 - LINE-1
			-----------------------------
			Values:
			1 - Inhibit
			0 - Do Not Inhibit
			-----------------------------"
		::= { omtp11PlusConfigurationEntry 257 }

	omtp11PlusOduTcm5IncomingAlignmentErrorAlarmInhibit OBJECT-TYPE
	      SYNTAX  INTEGER
	      MAX-ACCESS  read-write
	      STATUS  current
	      DESCRIPTION
			"Inhibits OMTP11-PLUS ODU TCM5 Incoming Alignment Error 
			Alarm for the requested port
			-----------------------------
			omtp11PlusInterfaceNumber:
			1 - CLIENT-1
			2 - LINE-1
			-----------------------------
			Values:
			1 - Inhibit
			0 - Do Not Inhibit
			-----------------------------"
		::= { omtp11PlusConfigurationEntry 258 }

	omtp11PlusOduTcm6IncomingAlignmentErrorAlarmInhibit OBJECT-TYPE
	      SYNTAX  INTEGER
	      MAX-ACCESS  read-write
	      STATUS  current
	      DESCRIPTION
			"Inhibits OMTP11-PLUS ODU TCM6 Incoming Alignment Error 
			Alarm for the requested port
			-----------------------------
			omtp11PlusInterfaceNumber:
			1 - CLIENT-1
			2 - LINE-1
			-----------------------------
			Values:
			1 - Inhibit
			0 - Do Not Inhibit
			-----------------------------"
		::= { omtp11PlusConfigurationEntry 259 }

	omtp11PlusOduTraceIdentifierMismatchAlarmInhibit OBJECT-TYPE
	      SYNTAX  INTEGER
	      MAX-ACCESS  read-write
	      STATUS  current
	      DESCRIPTION
			"Inhibits OMTP11-PLUS ODU Trace Identifier Mismatch Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 260 }

	omtp11PlusOduLockedDefectAlarmInhibit OBJECT-TYPE
	      SYNTAX  INTEGER
	      MAX-ACCESS  read-write
	      STATUS  current
	      DESCRIPTION
			"Inhibits OMTP11-PLUS ODU Locked Defect Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 261 }

	omtp11PlusOduOpenConnectionIndicationAlarmInhibit OBJECT-TYPE
	      SYNTAX  INTEGER
	      MAX-ACCESS  read-write
	      STATUS  current
	      DESCRIPTION
			"Inhibits OMTP11-PLUS ODU Open Connection Indication Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 262 }

	omtp11PlusOduBackwardDefectIndicationAlarmInhibit OBJECT-TYPE
	      SYNTAX  INTEGER
	      MAX-ACCESS  read-write
	      STATUS  current
	      DESCRIPTION
			"Inhibits OMTP11-PLUS ODU Backward Defect Indication Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 263 }

	omtp11PlusOduTcm1BackwardIncomingAlignmentErrorAlarmInhibit OBJECT-TYPE
	      SYNTAX  INTEGER
	      MAX-ACCESS  read-write
	      STATUS  current
	      DESCRIPTION
			"Inhibits OMTP11-PLUS ODU TCM1 Backward Incoming
			Alignment Error Alarm for the requested port
			-----------------------------
			omtp11PlusInterfaceNumber:
			1 - CLIENT-1
			2 - LINE-1
			-----------------------------
			Values:
			1 - Inhibit
			0 - Do Not Inhibit
			-----------------------------"
		::= { omtp11PlusConfigurationEntry 264 }

	omtp11PlusOduTcm2BackwardIncomingAlignmentErrorAlarmInhibit OBJECT-TYPE
	      SYNTAX  INTEGER
	      MAX-ACCESS  read-write
	      STATUS  current
	      DESCRIPTION
			"Inhibits OMTP11-PLUS ODU TCM2 Backward Incoming
			Alignment Error Alarm for the requested port
			-----------------------------
			omtp11PlusInterfaceNumber:
			1 - CLIENT-1
			2 - LINE-1
			-----------------------------
			Values:
			1 - Inhibit
			0 - Do Not Inhibit
			-----------------------------"
		::= { omtp11PlusConfigurationEntry 265 }

	omtp11PlusOduTcm3BackwardIncomingAlignmentErrorAlarmInhibit OBJECT-TYPE
	      SYNTAX  INTEGER
	      MAX-ACCESS  read-write
	      STATUS  current
	      DESCRIPTION
			"Inhibits OMTP11-PLUS ODU TCM3 Backward Incoming
			Alignment Error Alarm for the requested port
			-----------------------------
			omtp11PlusInterfaceNumber:
			1 - CLIENT-1
			2 - LINE-1
			-----------------------------
			Values:
			1 - Inhibit
			0 - Do Not Inhibit
			-----------------------------"
		::= { omtp11PlusConfigurationEntry 266 }

	omtp11PlusOduTcm4BackwardIncomingAlignmentErrorAlarmInhibit OBJECT-TYPE
	      SYNTAX  INTEGER
	      MAX-ACCESS  read-write
	      STATUS  current
	      DESCRIPTION
			"Inhibits OMTP11-PLUS ODU TCM4 Backward Incoming
			Alignment Error Alarm for the requested port
			-----------------------------
			omtp11PlusInterfaceNumber:
			1 - CLIENT-1
			2 - LINE-1
			-----------------------------
			Values:
			1 - Inhibit
			0 - Do Not Inhibit
			-----------------------------"
		::= { omtp11PlusConfigurationEntry 267 }

	omtp11PlusOduTcm5BackwardIncomingAlignmentErrorAlarmInhibit OBJECT-TYPE
	      SYNTAX  INTEGER
	      MAX-ACCESS  read-write
	      STATUS  current
	      DESCRIPTION
			"Inhibits OMTP11-PLUS ODU TCM5 Backward Incoming
			Alignment Error Alarm for the requested port
			-----------------------------
			omtp11PlusInterfaceNumber:
			1 - CLIENT-1
			2 - LINE-1
			-----------------------------
			Values:
			1 - Inhibit
			0 - Do Not Inhibit
			-----------------------------"
		::= { omtp11PlusConfigurationEntry 268 }

	omtp11PlusOduTcm6BackwardIncomingAlignmentErrorAlarmInhibit OBJECT-TYPE
	      SYNTAX  INTEGER
	      MAX-ACCESS  read-write
	      STATUS  current
	      DESCRIPTION
			"Inhibits OMTP11-PLUS ODU TCM6 Backward Incoming
			Alignment Error Alarm for the requested port
			-----------------------------
			omtp11PlusInterfaceNumber:
			1 - CLIENT-1
			2 - LINE-1
			-----------------------------
			Values:
			1 - Inhibit
			0 - Do Not Inhibit
			-----------------------------"
		::= { omtp11PlusConfigurationEntry 269 }

	omtp11PlusOpuPayloadMismatchAlarmInhibit OBJECT-TYPE
	      SYNTAX  INTEGER
	      MAX-ACCESS  read-write
	      STATUS  current
	      DESCRIPTION
			"Inhibits OMTP11-PLUS Opu Payload Mismatch Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 270 }

	omtp11PlusOchLossOfPayloadAlarmInhibit OBJECT-TYPE
	      SYNTAX  INTEGER
	      MAX-ACCESS  read-write
	      STATUS  current
	      DESCRIPTION
			"Inhibits OMTP11-PLUS Och Loss Of Payload Alarm
			for the requested port
			-----------------------------
			omtp11PlusInterfaceNumber:
			1 - CLIENT-1
			2 - LINE-1
			-----------------------------
			Values:
			1 - Inhibit
			0 - Do Not Inhibit
			-----------------------------"
		::= { omtp11PlusConfigurationEntry 271 }

	omtp11PlusSdhLossOfSignalAlarmInhibit OBJECT-TYPE
	      SYNTAX  INTEGER
	      MAX-ACCESS  read-write
	      STATUS  current
	      DESCRIPTION
			"Inhibits OMTP11-PLUS SDH Loss Of Signal Alarm
			for the requested port
			-----------------------------
			omtp11PlusInterfaceNumber:
			1 - CLIENT-1
			-----------------------------
			Values:
			1 - Inhibit
			0 - Do Not Inhibit
			-----------------------------"
		::= { omtp11PlusConfigurationEntry 281 }

	omtp11PlusSdhOutOfFrameAlarmInhibit OBJECT-TYPE
	      SYNTAX  INTEGER
	      MAX-ACCESS  read-write
	      STATUS  current
	      DESCRIPTION
			"Inhibits OMTP11-PLUS SDH Out Of Frame Alarm
			for the requested port
			-----------------------------
			omtp11PlusInterfaceNumber:
			1 - CLIENT-1
			-----------------------------
			Values:
			1 - Inhibit
			0 - Do Not Inhibit
			-----------------------------"
		::= { omtp11PlusConfigurationEntry 282 }

	omtp11PlusSdhLossOfFrameAlarmInhibit OBJECT-TYPE
	      SYNTAX  INTEGER
	      MAX-ACCESS  read-write
	      STATUS  current
	      DESCRIPTION
			"Inhibits OMTP11-PLUS SDH Loss Of Frame Alarm
			for the requested port
			-----------------------------
			omtp11PlusInterfaceNumber:
			1 - CLIENT-1
			-----------------------------
			Values:
			1 - Inhibit
			0 - Do Not Inhibit
			-----------------------------"
		::= { omtp11PlusConfigurationEntry 283 }

	omtp11PlusSdhRsAlarmIndicationSignalAlarmInhibit OBJECT-TYPE
	      SYNTAX  INTEGER
	      MAX-ACCESS  read-write
	      STATUS  current
	      DESCRIPTION
			"Inhibits OMTP11-PLUS SDH RS Alarm Indication Signal Alarm
			for the requested port
			-----------------------------
			omtp11PlusInterfaceNumber:
			1 - CLIENT-1
			-----------------------------
			Values:
			1 - Inhibit
			0 - Do Not Inhibit
			-----------------------------"
		::= { omtp11PlusConfigurationEntry 284 }

	omtp11PlusSdhRsTraceIdentifierMismatchAlarmInhibit OBJECT-TYPE
	      SYNTAX  INTEGER
	      MAX-ACCESS  read-write
	      STATUS  current
	      DESCRIPTION
			"Inhibits OMTP11-PLUS SDH RS Trace Identifier Mismatch Alarm
			for the requested port
			-----------------------------
			omtp11PlusInterfaceNumber:
			1 - CLIENT-1
			-----------------------------
			Values:
			1 - Inhibit
			0 - Do Not Inhibit
			-----------------------------"
		::= { omtp11PlusConfigurationEntry 285 }

	omtp11PlusSdhAuAlarmIndicationSignalAlarmInhibit OBJECT-TYPE
	      SYNTAX  INTEGER
	      MAX-ACCESS  read-write
	      STATUS  current
	      DESCRIPTION
			"Inhibits OMTP11-PLUS SDH AU Alarm Indication Signal Alarm
			for the requested port
			-----------------------------
			omtp11PlusInterfaceNumber:
			1 - CLIENT-1
			-----------------------------
			Values:
			1 - Inhibit
			0 - Do Not Inhibit
			-----------------------------"
		::= { omtp11PlusConfigurationEntry 286 }

	omtp11PlusSdhAuLossOfPointerAlarmInhibit OBJECT-TYPE
	      SYNTAX  INTEGER
	      MAX-ACCESS  read-write
	      STATUS  current
	      DESCRIPTION
			"Inhibits OMTP11-PLUS SDH AU Loss Of Pointer Alarm
			for the requested port
			-----------------------------
			omtp11PlusInterfaceNumber:
			1 - CLIENT-1
			-----------------------------
			Values:
			1 - Inhibit
			0 - Do Not Inhibit
			-----------------------------"
		::= { omtp11PlusConfigurationEntry 287 }

	omtp11PlusSdhMsAlarmIndicationSignalAlarmInhibit OBJECT-TYPE
	      SYNTAX  INTEGER
	      MAX-ACCESS  read-write
	      STATUS  current
	      DESCRIPTION
			"Inhibits OMTP11-PLUS SDH MS Alarm Indication Signal Alarm
			for the requested port
			-----------------------------
			omtp11PlusInterfaceNumber:
			1 - CLIENT-1
			-----------------------------
			Values:
			1 - Inhibit
			0 - Do Not Inhibit
			-----------------------------"
		::= { omtp11PlusConfigurationEntry 288 }

	omtp11PlusSdhMsRemoteErrorIndicationAlarmInhibit OBJECT-TYPE
	      SYNTAX  INTEGER
	      MAX-ACCESS  read-write
	      STATUS  current
	      DESCRIPTION
			"Inhibits OMTP11-PLUS SDH MS Remote Error Indication Alarm
			for the requested port
			-----------------------------
			omtp11PlusInterfaceNumber:
			1 - CLIENT-1
			-----------------------------
			Values:
			1 - Inhibit
			0 - Do Not Inhibit
			-----------------------------"
		::= { omtp11PlusConfigurationEntry 289 }

	omtp11PlusSdhMsRemoteDefectIndicationAlarmInhibit OBJECT-TYPE
	      SYNTAX  INTEGER
	      MAX-ACCESS  read-write
	      STATUS  current
	      DESCRIPTION
			"Inhibits OMTP11-PLUS SDH MS Remote Defect Indication Alarm
			for the requested port
			-----------------------------
			omtp11PlusInterfaceNumber:
			1 - CLIENT-1
			-----------------------------
			Values:
			1 - Inhibit
			0 - Do Not Inhibit
			-----------------------------"
		::= { omtp11PlusConfigurationEntry 290 }

	omtp11PlusSdhMsRemoteFailureIndicationAlarmInhibit OBJECT-TYPE
	      SYNTAX  INTEGER
	      MAX-ACCESS  read-write
	      STATUS  current
	      DESCRIPTION
			"Inhibits OMTP11-PLUS SDH MS Remote Failure Indication Alarm
			for the requested port
			-----------------------------
			omtp11PlusInterfaceNumber:
			1 - CLIENT-1
			-----------------------------
			Values:
			1 - Inhibit
			0 - Do Not Inhibit
			-----------------------------"
		::= { omtp11PlusConfigurationEntry 291 }

	omtp11PlusSdhMsB2ExcessiveErrorAlarmInhibit OBJECT-TYPE
	      SYNTAX  INTEGER
	      MAX-ACCESS  read-write
	      STATUS  current
	      DESCRIPTION
			"Inhibits OMTP11-PLUS SDH MS B2 Signal Fail Alarm
			for the requested port
			-----------------------------
			omtp11PlusInterfaceNumber:
			1 - CLIENT-1
			-----------------------------
			Values:
			1 - Inhibit
			0 - Do Not Inhibit
			-----------------------------"
		::= { omtp11PlusConfigurationEntry 292 }

	omtp11PlusSdhMsB2SignalDegradeAlarmInhibit OBJECT-TYPE
	      SYNTAX  INTEGER
	      MAX-ACCESS  read-write
	      STATUS  current
	      DESCRIPTION
			"Inhibits OMTP11-PLUS SDH MS B2 Signal Degrade Alarm
			for the requested port
			-----------------------------
			omtp11PlusInterfaceNumber:
			1 - CLIENT-1
			-----------------------------
			Values:
			1 - Inhibit
			0 - Do Not Inhibit
			-----------------------------"
		::= { omtp11PlusConfigurationEntry 293 }

	omtp11PlusSdhLossOfSequenceSynchronisationAlarmInhibit OBJECT-TYPE
	      SYNTAX  INTEGER
	      MAX-ACCESS  read-write
	      STATUS  current
	      DESCRIPTION
			"Inhibits OMTP11-PLUS SDH Loss Of Sequence Synchronisation Alarm
			for the requested port
			-----------------------------
			omtp11PlusInterfaceNumber:
			1 - CLIENT-1
			-----------------------------
			Values:
			1 - Inhibit
			0 - Do Not Inhibit
			-----------------------------"
		::= { omtp11PlusConfigurationEntry 294 }

	omtp11PlusSdhHigherOrderPathPayloadLabelMismatchAlarmInhibit OBJECT-TYPE
	      SYNTAX  INTEGER
	      MAX-ACCESS  read-write
	      STATUS  current
	      DESCRIPTION
			"Inhibits OMTP11-PLUS SDH Higher Order Path Payload Label Mismatch Alarm
			for the requested port
			-----------------------------
			omtp11PlusInterfaceNumber:
			1 - CLIENT-1
			-----------------------------
			Values:
			1 - Inhibit
			0 - Do Not Inhibit
			-----------------------------"
		::= { omtp11PlusConfigurationEntry 295 }

	omtp11PlusSdhHigherOrderPathUnequippedAlarmInhibit OBJECT-TYPE
	      SYNTAX  INTEGER
	      MAX-ACCESS  read-write
	      STATUS  current
	      DESCRIPTION
			"Inhibits OMTP11-PLUS SDH Higher Order Path Unequipped Alarm
			for the requested port
			-----------------------------
			omtp11PlusInterfaceNumber:
			1 - CLIENT-1
			-----------------------------
			Values:
			1 - Inhibit
			0 - Do Not Inhibit
			-----------------------------"
		::= { omtp11PlusConfigurationEntry 296 }

	omtp11PlusWan10gLossOfSignalAlarmInhibit OBJECT-TYPE
	      SYNTAX  INTEGER
	      MAX-ACCESS  read-write
	      STATUS  current
	      DESCRIPTION
			"Inhibits OMTP11-PLUS WAN10G Loss Of Signal Alarm
			for the requested port
			-----------------------------
			omtp11PlusInterfaceNumber:
			1 - CLIENT-1
			-----------------------------
			Values:
			1 - Inhibit
			0 - Do Not Inhibit
			-----------------------------"
		::= { omtp11PlusConfigurationEntry 301 }

	omtp11PlusWan10gOutOfFrameAlarmInhibit OBJECT-TYPE
	      SYNTAX  INTEGER
	      MAX-ACCESS  read-write
	      STATUS  current
	      DESCRIPTION
			"Inhibits OMTP11-PLUS WAN10G Out Of Frame Alarm
			for the requested port
			-----------------------------
			omtp11PlusInterfaceNumber:
			1 - CLIENT-1
			-----------------------------
			Values:
			1 - Inhibit
			0 - Do Not Inhibit
			-----------------------------"
		::= { omtp11PlusConfigurationEntry 302 }

	omtp11PlusWan10gLossOfFrameAlarmInhibit OBJECT-TYPE
	      SYNTAX  INTEGER
	      MAX-ACCESS  read-write
	      STATUS  current
	      DESCRIPTION
			"Inhibits OMTP11-PLUS WAN10G Loss Of Frame Alarm
			for the requested port
			-----------------------------
			omtp11PlusInterfaceNumber:
			1 - CLIENT-1
			-----------------------------
			Values:
			1 - Inhibit
			0 - Do Not Inhibit
			-----------------------------"
		::= { omtp11PlusConfigurationEntry 303 }

	omtp11PlusWan10gRsAlarmIndicationSignalAlarmInhibit OBJECT-TYPE
	      SYNTAX  INTEGER
	      MAX-ACCESS  read-write
	      STATUS  current
	      DESCRIPTION
			"Inhibits OMTP11-PLUS WAN10G RS Alarm Indication Signal Alarm
			for the requested port
			-----------------------------
			omtp11PlusInterfaceNumber:
			1 - CLIENT-1
			-----------------------------
			Values:
			1 - Inhibit
			0 - Do Not Inhibit
			-----------------------------"
		::= { omtp11PlusConfigurationEntry 304 }

	omtp11PlusWan10gRsTraceIdentifierMismatchAlarmInhibit OBJECT-TYPE
	      SYNTAX  INTEGER
	      MAX-ACCESS  read-write
	      STATUS  current
	      DESCRIPTION
			"Inhibits OMTP11-PLUS WAN10G RS Trace Identifier Mismatch Alarm
			for the requested port
			-----------------------------
			omtp11PlusInterfaceNumber:
			1 - CLIENT-1
			-----------------------------
			Values:
			1 - Inhibit
			0 - Do Not Inhibit
			-----------------------------"
		::= { omtp11PlusConfigurationEntry 305 }

	omtp11PlusWan10gAuAlarmIndicationSignalAlarmInhibit OBJECT-TYPE
	      SYNTAX  INTEGER
	      MAX-ACCESS  read-write
	      STATUS  current
	      DESCRIPTION
			"Inhibits OMTP11-PLUS WAN10G AU Alarm Indication Signal Alarm
			for the requested port
			-----------------------------
			omtp11PlusInterfaceNumber:
			1 - CLIENT-1
			-----------------------------
			Values:
			1 - Inhibit
			0 - Do Not Inhibit
			-----------------------------"
		::= { omtp11PlusConfigurationEntry 306 }

	omtp11PlusWan10gAuLossOfPointerAlarmInhibit OBJECT-TYPE
	      SYNTAX  INTEGER
	      MAX-ACCESS  read-write
	      STATUS  current
	      DESCRIPTION
			"Inhibits OMTP11-PLUS WAN10G AU Loss Of Pointer Alarm
			for the requested port
			-----------------------------
			omtp11PlusInterfaceNumber:
			1 - CLIENT-1
			-----------------------------
			Values:
			1 - Inhibit
			0 - Do Not Inhibit
			-----------------------------"
		::= { omtp11PlusConfigurationEntry 307 }

	omtp11PlusWan10gMsAlarmIndicationSignalAlarmInhibit OBJECT-TYPE
	      SYNTAX  INTEGER
	      MAX-ACCESS  read-write
	      STATUS  current
	      DESCRIPTION
			"Inhibits OMTP11-PLUS WAN10G MS Alarm Indication Signal Alarm
			for the requested port
			-----------------------------
			omtp11PlusInterfaceNumber:
			1 - CLIENT-1
			-----------------------------
			Values:
			1 - Inhibit
			0 - Do Not Inhibit
			-----------------------------"
		::= { omtp11PlusConfigurationEntry 308 }

	omtp11PlusWan10gMsRemoteErrorIndicationAlarmInhibit OBJECT-TYPE
	      SYNTAX  INTEGER
	      MAX-ACCESS  read-write
	      STATUS  current
	      DESCRIPTION
			"Inhibits OMTP11-PLUS WAN10G MS Remote Error Indication Alarm
			for the requested port
			-----------------------------
			omtp11PlusInterfaceNumber:
			1 - CLIENT-1
			-----------------------------
			Values:
			1 - Inhibit
			0 - Do Not Inhibit
			-----------------------------"
		::= { omtp11PlusConfigurationEntry 309 }

	omtp11PlusWan10gMsRemoteDefectIndicationAlarmInhibit OBJECT-TYPE
	      SYNTAX  INTEGER
	      MAX-ACCESS  read-write
	      STATUS  current
	      DESCRIPTION
			"Inhibits OMTP11-PLUS WAN10G MS Remote Defect Indication Alarm
			for the requested port
			-----------------------------
			omtp11PlusInterfaceNumber:
			1 - CLIENT-1
			-----------------------------
			Values:
			1 - Inhibit
			0 - Do Not Inhibit
			-----------------------------"
		::= { omtp11PlusConfigurationEntry 310 }

	omtp11PlusWan10gMsRemoteFailureIndicationAlarmInhibit OBJECT-TYPE
	      SYNTAX  INTEGER
	      MAX-ACCESS  read-write
	      STATUS  current
	      DESCRIPTION
			"Inhibits OMTP11-PLUS WAN10G MS Remote Failure Indication Alarm
			for the requested port
			-----------------------------
			omtp11PlusInterfaceNumber:
			1 - CLIENT-1
			-----------------------------
			Values:
			1 - Inhibit
			0 - Do Not Inhibit
			-----------------------------"
		::= { omtp11PlusConfigurationEntry 311 }

	omtp11PlusWan10gMsB2ExcessiveErrorAlarmInhibit OBJECT-TYPE
	      SYNTAX  INTEGER
	      MAX-ACCESS  read-write
	      STATUS  current
	      DESCRIPTION
			"Inhibits OMTP11-PLUS WAN10G MS B2 Signal Fail Alarm
			for the requested port
			-----------------------------
			omtp11PlusInterfaceNumber:
			1 - CLIENT-1
			-----------------------------
			Values:
			1 - Inhibit
			0 - Do Not Inhibit
			-----------------------------"
		::= { omtp11PlusConfigurationEntry 312 }

	omtp11PlusWan10gMsB2SignalDegradeAlarmInhibit OBJECT-TYPE
	      SYNTAX  INTEGER
	      MAX-ACCESS  read-write
	      STATUS  current
	      DESCRIPTION
			"Inhibits OMTP11-PLUS WAN10G MS B2 Signal Degrade Alarm
			for the requested port
			-----------------------------
			omtp11PlusInterfaceNumber:
			1 - CLIENT-1
			-----------------------------
			Values:
			1 - Inhibit
			0 - Do Not Inhibit
			-----------------------------"
		::= { omtp11PlusConfigurationEntry 313 }

	omtp11PlusWan10gLossOfSequenceSynchronisationAlarmInhibit OBJECT-TYPE
	      SYNTAX  INTEGER
	      MAX-ACCESS  read-write
	      STATUS  current
	      DESCRIPTION
			"Inhibits OMTP11-PLUS WAN10G Loss Of Sequence Synchronisation Alarm
			for the requested port
			-----------------------------
			omtp11PlusInterfaceNumber:
			1 - CLIENT-1
			-----------------------------
			Values:
			1 - Inhibit
			0 - Do Not Inhibit
			-----------------------------"
		::= { omtp11PlusConfigurationEntry 314 }

	omtp11PlusWan10gHigherOrderPathPayloadLabelMismatchAlarmInhibit OBJECT-TYPE
	      SYNTAX  INTEGER
	      MAX-ACCESS  read-write
	      STATUS  current
	      DESCRIPTION
			"Inhibits OMTP11-PLUS WAN10G Higher Order Path Payload Label Mismatch Alarm
			for the requested port
			-----------------------------
			omtp11PlusInterfaceNumber:
			1 - CLIENT-1
			-----------------------------
			Values:
			1 - Inhibit
			0 - Do Not Inhibit
			-----------------------------"
		::= { omtp11PlusConfigurationEntry 315 }

	omtp11PlusWan10gHigherOrderPathUnequippedAlarmInhibit OBJECT-TYPE
	      SYNTAX  INTEGER
	      MAX-ACCESS  read-write
	      STATUS  current
	      DESCRIPTION
			"Inhibits OMTP11-PLUS WAN10G Higher Order Path Unequipped Alarm
			for the requested port
			-----------------------------
			omtp11PlusInterfaceNumber:
			1 - CLIENT-1
			-----------------------------
			Values:
			1 - Inhibit
			0 - Do Not Inhibit
			-----------------------------"
		::= { omtp11PlusConfigurationEntry 316 }

	omtp11PlusLan10gLossOfSignalAlarmInhibit OBJECT-TYPE
	      SYNTAX  INTEGER
	      MAX-ACCESS  read-write
	      STATUS  current
	      DESCRIPTION
			"Inhibits OMTP11-PLUS LAN10G Loss Of Signal Alarm
			for the requested port
			-----------------------------
			omtp11PlusInterfaceNumber:
			1 - CLIENT-1
			-----------------------------
			Values:
			1 - Inhibit
			0 - Do Not Inhibit
			-----------------------------"
		::= { omtp11PlusConfigurationEntry 331 }

	omtp11PlusLan10gLossOfSignalSyncAlarmInhibit OBJECT-TYPE
	      SYNTAX  INTEGER
	      MAX-ACCESS  read-write
	      STATUS  current
	      DESCRIPTION
			"Inhibits OMTP11-PLUS LAN10G Loss Of Signal Sync Alarm
			for the requested port
			-----------------------------
			omtp11PlusInterfaceNumber:
			1 - CLIENT-1
			-----------------------------
			Values:
			1 - Inhibit
			0 - Do Not Inhibit
			-----------------------------"
		::= { omtp11PlusConfigurationEntry 332 }

	omtp11PlusLan10gLinkFailureAlarmInhibit OBJECT-TYPE
	      SYNTAX  INTEGER
	      MAX-ACCESS  read-write
	      STATUS  current
	      DESCRIPTION
			"Inhibits OMTP11-PLUS LAN10G Link Failure Alarm
			for the requested port
			-----------------------------
			omtp11PlusInterfaceNumber:
			1 - CLIENT-1
			-----------------------------
			Values:
			1 - Inhibit
			0 - Do Not Inhibit
			-----------------------------"
		::= { omtp11PlusConfigurationEntry 333 }

	omtp11PlusLan10gFrameCheckSequenceAlarmInhibit OBJECT-TYPE
	      SYNTAX  INTEGER
	      MAX-ACCESS  read-write
	      STATUS  current
	      DESCRIPTION
			"Inhibits OMTP11-PLUS LAN10G Frame Check Sequence Alarm
			for the requested port
			-----------------------------
			omtp11PlusInterfaceNumber:
			1 - CLIENT-1
			-----------------------------
			Values:
			1 - Inhibit
			0 - Do Not Inhibit
			-----------------------------"
		::= { omtp11PlusConfigurationEntry 334 }

	omtp11PlusLan10gCarrierStatusAlarmInhibit OBJECT-TYPE
	      SYNTAX  INTEGER
	      MAX-ACCESS  read-write
	      STATUS  current
	      DESCRIPTION
			"Inhibits OMTP11-PLUS LAN10G Carrier Status Alarm
			for the requested port
			-----------------------------
			omtp11PlusInterfaceNumber:
			1 - CLIENT-1
			-----------------------------
			Values:
			1 - Inhibit
			0 - Do Not Inhibit
			-----------------------------"
		::= { omtp11PlusConfigurationEntry 335 }

	omtp11PlusLan10gHighBerAlarmInhibit OBJECT-TYPE
	      SYNTAX  INTEGER
	      MAX-ACCESS  read-write
	      STATUS  current
	      DESCRIPTION
			"Inhibits OMTP11-PLUS LAN10G High Ber Alarm
			for the requested port
			-----------------------------
			omtp11PlusInterfaceNumber:
			1 - CLIENT-1
			-----------------------------
			Values:
			1 - Inhibit
			0 - Do Not Inhibit
			-----------------------------"
		::= { omtp11PlusConfigurationEntry 336 }

	omtp11PlusLan10gLocalFaultAlarmInhibit OBJECT-TYPE
	      SYNTAX  INTEGER
	      MAX-ACCESS  read-write
	      STATUS  current
	      DESCRIPTION
			"Inhibits OMTP11-PLUS LAN10G Local Fault Alarm
			for the requested port
			-----------------------------
			omtp11PlusInterfaceNumber:
			1 - CLIENT-1
			-----------------------------
			Values:
			1 - Inhibit
			0 - Do Not Inhibit
			-----------------------------"
		::= { omtp11PlusConfigurationEntry 337 }

	omtp11PlusLan10gRemoteFaultAlarmInhibit OBJECT-TYPE
	      SYNTAX  INTEGER
	      MAX-ACCESS  read-write
	      STATUS  current
	      DESCRIPTION
			"Inhibits OMTP11-PLUS LAN10G Remote Fault Alarm
			for the requested port
			-----------------------------
			omtp11PlusInterfaceNumber:
			1 - CLIENT-1
			-----------------------------
			Values:
			1 - Inhibit
			0 - Do Not Inhibit
			-----------------------------"
		::= { omtp11PlusConfigurationEntry 338 }

	omtp11PlusFcTransmitDisparityInversionDefectAlarmInhibit OBJECT-TYPE
	      SYNTAX  INTEGER
	      MAX-ACCESS  read-write
	      STATUS  current
	      DESCRIPTION
			"Inhibits OMTP11-PLUS FC Transmit Display Invert Alarm
			for the requested port
			-----------------------------
			omtp11PlusInterfaceNumber:
			1 - CLIENT-1
			-----------------------------
			Values:
			1 - Inhibit
			0 - Do Not Inhibit
			-----------------------------"
		::= { omtp11PlusConfigurationEntry 351 }

	omtp11PlusFcTransmitDigitalLossOfLinkDefectAlarmInhibit OBJECT-TYPE
	      SYNTAX  INTEGER
	      MAX-ACCESS  read-write
	      STATUS  current
	      DESCRIPTION
			"Inhibits OMTP11-PLUS FC Transmit Dlolb Alarm
			for the requested port
			-----------------------------
			omtp11PlusInterfaceNumber:
			1 - CLIENT-1
			-----------------------------
			Values:
			1 - Inhibit
			0 - Do Not Inhibit
			-----------------------------"
		::= { omtp11PlusConfigurationEntry 352 }

	omtp11PlusFcTrasnmitLossofSynchronizationDefectAlarmInhibit OBJECT-TYPE
	      SYNTAX  INTEGER
	      MAX-ACCESS  read-write
	      STATUS  current
	      DESCRIPTION
			"Inhibits OMTP11-PLUS FC Transmit Sync Alarm
			for the requested port
			-----------------------------
			omtp11PlusInterfaceNumber:
			1 - CLIENT-1
			-----------------------------
			Values:
			1 - Inhibit
			0 - Do Not Inhibit
			-----------------------------"
		::= { omtp11PlusConfigurationEntry 353 }

	omtp11PlusFcReceiveDigitalLossofLinkDefectAlarmInhibit OBJECT-TYPE
	      SYNTAX  INTEGER
	      MAX-ACCESS  read-write
	      STATUS  current
	      DESCRIPTION
			"Inhibits OMTP11-PLUS FC Receive Dlolb Alarm
			for the requested port
			-----------------------------
			omtp11PlusInterfaceNumber:
			1 - CLIENT-1
			-----------------------------
			Values:
			1 - Inhibit
			0 - Do Not Inhibit
			-----------------------------"
		::= { omtp11PlusConfigurationEntry 354 }

	omtp11PlusFcReceiveLossofSynchronizationDefectAlarmInhibit OBJECT-TYPE
	      SYNTAX  INTEGER
	      MAX-ACCESS  read-write
	      STATUS  current
	      DESCRIPTION
			"Inhibits OMTP11-PLUS FC Receive Sync Alarm
			for the requested port
			-----------------------------
			omtp11PlusInterfaceNumber:
			1 - CLIENT-1
			-----------------------------
			Values:
			1 - Inhibit
			0 - Do Not Inhibit
			-----------------------------"
		::= { omtp11PlusConfigurationEntry 355 }

	omtp11PlusFcReceiveTransitionDetectDefectAlarmInhibit OBJECT-TYPE
	      SYNTAX  INTEGER
	      MAX-ACCESS  read-write
	      STATUS  current
	      DESCRIPTION
			"Inhibits OMTP11-PLUS FC Receive Xdet Alarm
			for the requested port
			-----------------------------
			omtp11PlusInterfaceNumber:
			1 - CLIENT-1
			-----------------------------
			Values:
			1 - Inhibit
			0 - Do Not Inhibit
			-----------------------------"
		::= { omtp11PlusConfigurationEntry 356 }

	omtp11PlusFcReceiveAnalogLossofSignalDefectAlarmInhibit OBJECT-TYPE
	      SYNTAX  INTEGER
	      MAX-ACCESS  read-write
	      STATUS  current
	      DESCRIPTION
			"Inhibits OMTP11-PLUS FC Receive Asd Alarm
			for the requested port
			-----------------------------
			omtp11PlusInterfaceNumber:
			1 - CLIENT-1
			-----------------------------
			Values:
			1 - Inhibit
			0 - Do Not Inhibit
			-----------------------------"
		::= { omtp11PlusConfigurationEntry 357 }

	omtp11PlusFcReceiveLineCodeViolationDefectAlarmInhibit OBJECT-TYPE
	      SYNTAX  INTEGER
	      MAX-ACCESS  read-write
	      STATUS  current
	      DESCRIPTION
			"Inhibits OMTP11-PLUS FC Receive Lcv Alarm
			for the requested port
			-----------------------------
			omtp11PlusInterfaceNumber:
			1 - CLIENT-1
			-----------------------------
			Values:
			1 - Inhibit
			0 - Do Not Inhibit
			-----------------------------"
		::= { omtp11PlusConfigurationEntry 358 }

	omtp11PlusGfpCsfSignalFailAlarmInhibit OBJECT-TYPE
	      SYNTAX  INTEGER
	      MAX-ACCESS  read-write
	      STATUS  current
	      DESCRIPTION
			"Inhibits OMTP11-PLUS GFP Csf Signal Failure Alarm
			for the requested port
			-----------------------------
			omtp11PlusInterfaceNumber:
			1 - CLIENT-1
			-----------------------------
			Values:
			1 - Inhibit
			0 - Do Not Inhibit
			-----------------------------"
		::= { omtp11PlusConfigurationEntry 371 }

	omtp11PlusGfpCsfLinkFailAlarmInhibit OBJECT-TYPE
	      SYNTAX  INTEGER
	      MAX-ACCESS  read-write
	      STATUS  current
	      DESCRIPTION
			"Inhibits OMTP11-PLUS GFP Csf Link Failure Alarm
			for the requested port
			-----------------------------
			omtp11PlusInterfaceNumber:
			1 - CLIENT-1
			-----------------------------
			Values:
			1 - Inhibit
			0 - Do Not Inhibit
			-----------------------------"
		::= { omtp11PlusConfigurationEntry 372 }

	omtp11PlusGfpCoreHeaderErrorAlarmInhibit OBJECT-TYPE
	      SYNTAX  INTEGER
	      MAX-ACCESS  read-write
	      STATUS  current
	      DESCRIPTION
			"Inhibits OMTP11-PLUS GFP Core Header Error Alarm
			for the requested port
			-----------------------------
			omtp11PlusInterfaceNumber:
			1 - CLIENT-1
			-----------------------------
			Values:
			1 - Inhibit
			0 - Do Not Inhibit
			-----------------------------"
		::= { omtp11PlusConfigurationEntry 373 }

	omtp11PlusGfpExtentionHeaderErrorAlarmInhibit OBJECT-TYPE
	      SYNTAX  INTEGER
	      MAX-ACCESS  read-write
	      STATUS  current
	      DESCRIPTION
			"Inhibits OMTP11-PLUS GFP Extention Header Error Alarm
			for the requested port
			-----------------------------
			omtp11PlusInterfaceNumber:
			1 - CLIENT-1
			-----------------------------
			Values:
			1 - Inhibit
			0 - Do Not Inhibit
			-----------------------------"
		::= { omtp11PlusConfigurationEntry 374 }

	omtp11PlusXfpInputPowerFailureAlarmSeverity OBJECT-TYPE
	      SYNTAX  DisplayString
	      MAX-ACCESS  read-write
	      STATUS  current
	      DESCRIPTION
			"Set or Get the alarm severity level of the
			OMTP11-PLUS XFP Input Power Failure Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 401 }

	omtp11PlusXfpOutputPowerFailureAlarmSeverity OBJECT-TYPE
	      SYNTAX  DisplayString
	      MAX-ACCESS  read-write
	      STATUS  current
	      DESCRIPTION
			"Set or Get the alarm severity level of the
			OMTP11-PLUS XFP Output Power Failure Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 402 }

	omtp11PlusXfpHighTemperatureAlarmSeverity OBJECT-TYPE
	      SYNTAX  DisplayString
	      MAX-ACCESS  read-write
	      STATUS  current
	      DESCRIPTION
			"Set or Get the alarm severity level of the
			OMTP11-PLUS XFP High Temperature Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 403 }

	omtp11PlusXfpLowTemperatureAlarmSeverity OBJECT-TYPE
	      SYNTAX  DisplayString
	      MAX-ACCESS  read-write
	      STATUS  current
	      DESCRIPTION
			"Set or Get the alarm severity level of the
			OMTP11-PLUS XFP Low Temperature Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 404 }

	omtp11PlusXfpHighTemperatureWarningSeverity OBJECT-TYPE
	      SYNTAX  DisplayString
	      MAX-ACCESS  read-write
	      STATUS  current
	      DESCRIPTION
			"Set or Get the alarm severity level of the
			OMTP11-PLUS XFP High Temperature Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 405 }

	omtp11PlusXfpLowTemperatureWarningSeverity OBJECT-TYPE
	      SYNTAX  DisplayString
	      MAX-ACCESS  read-write
	      STATUS  current
	      DESCRIPTION
			"Set or Get the alarm severity level of the
			OMTP11-PLUS XFP Low Temperature Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 406 }

	omtp11PlusXfpHighBiasCurrentAlarmSeverity OBJECT-TYPE
	      SYNTAX  DisplayString
	      MAX-ACCESS  read-write
	      STATUS  current
	      DESCRIPTION
			"Set or Get the alarm severity level of the
			OMTP11-PLUS XFP High Bias Current Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 407 }

	omtp11PlusXfpLowBiasCurrentAlarmSeverity OBJECT-TYPE
	      SYNTAX  DisplayString
	      MAX-ACCESS  read-write
	      STATUS  current
	      DESCRIPTION
			"Set or Get the alarm severity level of the
			OMTP11-PLUS XFP Low Bias Current Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 408 }

	omtp11PlusXfpHighBiasCurrentWarningSeverity OBJECT-TYPE
	      SYNTAX  DisplayString
	      MAX-ACCESS  read-write
	      STATUS  current
	      DESCRIPTION
			"Set or Get the alarm severity level of the
			OMTP11-PLUS XFP High Bias Current Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 409 }

	omtp11PlusXfpLowBiasCurrentWarningSeverity OBJECT-TYPE
	      SYNTAX  DisplayString
	      MAX-ACCESS  read-write
	      STATUS  current
	      DESCRIPTION
			"Set or Get the alarm severity level of the
			OMTP11-PLUS XFP Low Bias Current Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 410 }

	omtp11PlusXfpInputHighPowerAlarmSeverity OBJECT-TYPE
	      SYNTAX  DisplayString
	      MAX-ACCESS  read-write
	      STATUS  current
	      DESCRIPTION
			"Set or Get the alarm severity level of the
			OMTP11-PLUS XFP Input High Power Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 411 }

	omtp11PlusXfpInputLowPowerAlarmSeverity OBJECT-TYPE
	      SYNTAX  DisplayString
	      MAX-ACCESS  read-write
	      STATUS  current
	      DESCRIPTION
			"Set or Get the alarm severity level of the
			OMTP11-PLUS XFP Input Low Power Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 412 }

	omtp11PlusXfpInputHighPowerWarningSeverity OBJECT-TYPE
	      SYNTAX  DisplayString
	      MAX-ACCESS  read-write
	      STATUS  current
	      DESCRIPTION
			"Set or Get the alarm severity level of the
			OMTP11-PLUS XFP Input High Power Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 413 }

	omtp11PlusXfpInputLowPowerWarningSeverity OBJECT-TYPE
	      SYNTAX  DisplayString
	      MAX-ACCESS  read-write
	      STATUS  current
	      DESCRIPTION
			"Set or Get the alarm severity level of the
			OMTP11-PLUS XFP Input Low Power Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 414 }

	omtp11PlusXfpOutputHighPowerAlarmSeverity OBJECT-TYPE
	      SYNTAX  DisplayString
	      MAX-ACCESS  read-write
	      STATUS  current
	      DESCRIPTION
			"Set or Get the alarm severity level of the
			OMTP11-PLUS XFP Output High Power Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 415 }

	omtp11PlusXfpOutputLowPowerAlarmSeverity OBJECT-TYPE
	      SYNTAX  DisplayString
	      MAX-ACCESS  read-write
	      STATUS  current
	      DESCRIPTION
			"Set or Get the alarm severity level of the
			OMTP11-PLUS XFP Output Low Power Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 416 }

	omtp11PlusXfpOutputHighPowerWarningSeverity OBJECT-TYPE
	      SYNTAX  DisplayString
	      MAX-ACCESS  read-write
	      STATUS  current
	      DESCRIPTION
			"Set or Get the alarm severity level of the
			OMTP11-PLUS XFP Output High Power Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 417 }

	omtp11PlusXfpOutputLowPowerWarningSeverity OBJECT-TYPE
	      SYNTAX  DisplayString
	      MAX-ACCESS  read-write
	      STATUS  current
	      DESCRIPTION
			"Set or Get the alarm severity level of the
			OMTP11-PLUS XFP Output Low Power Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 418 }

	omtp11PlusXfpHighSupplyVoltageAlarmSeverity OBJECT-TYPE
	      SYNTAX  DisplayString
	      MAX-ACCESS  read-write
	      STATUS  current
	      DESCRIPTION
			"Set or Get the alarm severity level of the
			OMTP11-PLUS XFP High Supply Voltage Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 419 }

	omtp11PlusXfpLowSupplyVoltageAlarmSeverity OBJECT-TYPE
	      SYNTAX  DisplayString
	      MAX-ACCESS  read-write
	      STATUS  current
	      DESCRIPTION
			"Set or Get the alarm severity level of the
			OMTP11-PLUS XFP Low Supply Voltage Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 420 }

	omtp11PlusXfpHighSupplyVoltageWarningSeverity OBJECT-TYPE
	      SYNTAX  DisplayString
	      MAX-ACCESS  read-write
	      STATUS  current
	      DESCRIPTION
			"Set or Get the alarm severity level of the
			OMTP11-PLUS XFP High Supply Voltage Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 421 }

	omtp11PlusXfpLowSupplyVoltageWarningSeverity OBJECT-TYPE
	      SYNTAX  DisplayString
	      MAX-ACCESS  read-write
	      STATUS  current
	      DESCRIPTION
			"Set or Get the alarm severity level of the
			OMTP11-PLUS XFP Low Supply Voltage Warning   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 422 }

	omtp11PlusXfpPresenceAbsenceNotificationSeverity OBJECT-TYPE
	      SYNTAX  DisplayString
	      MAX-ACCESS  read-write
	      STATUS  current
	      DESCRIPTION
			"Set or Get the alarm severity level of the
			OMTP11-PLUS XFP Presence Absence Notification   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 423 }

	omtp11PlusOtuLossOfSignalAlarmSeverity OBJECT-TYPE
	      SYNTAX  DisplayString
	      MAX-ACCESS  read-write
	      STATUS  current
	      DESCRIPTION
			"Set or Get the alarm severity level of the
			OMTP11-PLUS OTU Loss Of Signal Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 431 }

	omtp11PlusOtuLossOfFrameAlarmSeverity OBJECT-TYPE
	      SYNTAX  DisplayString
	      MAX-ACCESS  read-write
	      STATUS  current
	      DESCRIPTION
			"Set or Get the alarm severity level of the
			OMTP11-PLUS OTU Loss Of Frame Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 432 }

	omtp11PlusOtuOutOfFrameAlarmSeverity OBJECT-TYPE
	      SYNTAX  DisplayString
	      MAX-ACCESS  read-write
	      STATUS  current
	      DESCRIPTION
			"Set or Get the alarm severity level of the
			OMTP11-PLUS OTU Out Of Frame Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 433 }

	omtp11PlusOtuLossOfMultiFrameAlarmSeverity OBJECT-TYPE
	      SYNTAX  DisplayString
	      MAX-ACCESS  read-write
	      STATUS  current
	      DESCRIPTION
			"Set or Get the alarm severity level of the
			OMTP11-PLUS OTU Loss Of Multi Frame Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 434 }

	omtp11PlusOtuOutOfMultiFrameAlarmSeverity OBJECT-TYPE
	      SYNTAX  DisplayString
	      MAX-ACCESS  read-write
	      STATUS  current
	      DESCRIPTION
			"Set or Get the alarm severity level of the
			OMTP11-PLUS OTU Out Of Multi Frame Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 435 }

	omtp11PlusOtuSignalFailAlarmSeverity OBJECT-TYPE
	      SYNTAX  DisplayString
	      MAX-ACCESS  read-write
	      STATUS  current
	      DESCRIPTION
			"Set or Get the alarm severity level of the
			OMTP11-PLUS OTU Signal Fail Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 436 }

	omtp11PlusOtuSignalDegradeAlarmSeverity OBJECT-TYPE
	      SYNTAX  DisplayString
	      MAX-ACCESS  read-write
	      STATUS  current
	      DESCRIPTION
			"Set or Get the alarm severity level of the
			OMTP11-PLUS OTU Signal Degrade Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 437 }

	omtp11PlusOtuAlarmIndicationSignalAlarmSeverity OBJECT-TYPE
	      SYNTAX  DisplayString
	      MAX-ACCESS  read-write
	      STATUS  current
	      DESCRIPTION
			"Set or Get the alarm severity level of the
			OMTP11-PLUS OTU Alarm Indication Signal Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 438 }

	omtp11PlusOtuIncomingAlignmentErrorAlarmSeverity OBJECT-TYPE
	      SYNTAX  DisplayString
	      MAX-ACCESS  read-write
	      STATUS  current
	      DESCRIPTION
			"Set or Get the alarm severity level of the
			OMTP11-PLUS OTU Incoming Alignment Error Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 439 }

	omtp11PlusOtuTraceIdentifierMismatchAlarmSeverity OBJECT-TYPE
	      SYNTAX  DisplayString
	      MAX-ACCESS  read-write
	      STATUS  current
	      DESCRIPTION
			"Set or Get the alarm severity level of the
			OMTP11-PLUS OTU Trace Identifier Mismatch Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 440 }

	omtp11PlusOtuBackwardIncomingAlignmentErrorAlarmSeverity OBJECT-TYPE
	      SYNTAX  DisplayString
	      MAX-ACCESS  read-write
	      STATUS  current
	      DESCRIPTION
			"Set or Get the alarm severity level of the
			OMTP11-PLUS OTU Backward Incoming Alignment Error Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 441 }

	omtp11PlusOtuBackwardDefectIndicationAlarmSeverity OBJECT-TYPE
	      SYNTAX  DisplayString
	      MAX-ACCESS  read-write
	      STATUS  current
	      DESCRIPTION
			"Set or Get the alarm severity level of the
			OMTP11-PLUS OTU Backward Defect Indication Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 442 }

	omtp11PlusOduSignalFailAlarmSeverity OBJECT-TYPE
	      SYNTAX  DisplayString
	      MAX-ACCESS  read-write
	      STATUS  current
	      DESCRIPTION
			"Set or Get the alarm severity level of the
			OMTP11-PLUS ODU Signal Fail Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 451 }

	omtp11PlusOduSignalDegradeAlarmSeverity OBJECT-TYPE
	      SYNTAX  DisplayString
	      MAX-ACCESS  read-write
	      STATUS  current
	      DESCRIPTION
			"Set or Get the alarm severity level of the
			OMTP11-PLUS ODU Signal Degrade Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 452 }

	omtp11PlusOduAlarmIndicationSignalAlarmSeverity OBJECT-TYPE
	      SYNTAX  DisplayString
	      MAX-ACCESS  read-write
	      STATUS  current
	      DESCRIPTION
			"Set or Get the alarm severity level of the
			OMTP11-PLUS ODU Alarm Indication Signal Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 453 }

	omtp11PlusOduTcm1IncomingAlignmentErrorAlarmSeverity OBJECT-TYPE
	      SYNTAX  DisplayString
	      MAX-ACCESS  read-write
	      STATUS  current
	      DESCRIPTION
			"Set or Get the alarm severity level of the
			OMTP11-PLUS ODU TCM1 Incoming Alignment Error Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 454 }

	omtp11PlusOduTcm2IncomingAlignmentErrorAlarmSeverity OBJECT-TYPE
	      SYNTAX  DisplayString
	      MAX-ACCESS  read-write
	      STATUS  current
	      DESCRIPTION
			"Set or Get the alarm severity level of the
			OMTP11-PLUS ODU TCM2 Incoming Alignment Error Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 455 }

	omtp11PlusOduTcm3IncomingAlignmentErrorAlarmSeverity OBJECT-TYPE
	      SYNTAX  DisplayString
	      MAX-ACCESS  read-write
	      STATUS  current
	      DESCRIPTION
			"Set or Get the alarm severity level of the
			OMTP11-PLUS ODU TCM3 Incoming Alignment Error Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 456 }

	omtp11PlusOduTcm4IncomingAlignmentErrorAlarmSeverity OBJECT-TYPE
	      SYNTAX  DisplayString
	      MAX-ACCESS  read-write
	      STATUS  current
	      DESCRIPTION
			"Set or Get the alarm severity level of the
			OMTP11-PLUS ODU TCM4 Incoming Alignment Error Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 457 }

	omtp11PlusOduTcm5IncomingAlignmentErrorAlarmSeverity OBJECT-TYPE
	      SYNTAX  DisplayString
	      MAX-ACCESS  read-write
	      STATUS  current
	      DESCRIPTION
			"Set or Get the alarm severity level of the
			OMTP11-PLUS ODU TCM5 Incoming Alignment Error Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 458 }

	omtp11PlusOduTcm6IncomingAlignmentErrorAlarmSeverity OBJECT-TYPE
	      SYNTAX  DisplayString
	      MAX-ACCESS  read-write
	      STATUS  current
	      DESCRIPTION
			"Set or Get the alarm severity level of the
			OMTP11-PLUS ODU TCM6 Incoming Alignment Error Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 459 }

	omtp11PlusOduTraceIdentifierMismatchAlarmSeverity OBJECT-TYPE
	      SYNTAX  DisplayString
	      MAX-ACCESS  read-write
	      STATUS  current
	      DESCRIPTION
			"Set or Get the alarm severity level of the
			OMTP11-PLUS ODU Trace Identifier Mismatch Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 460 }

	omtp11PlusOduLockedDefectAlarmSeverity OBJECT-TYPE
	      SYNTAX  DisplayString
	      MAX-ACCESS  read-write
	      STATUS  current
	      DESCRIPTION
			"Set or Get the alarm severity level of the
			OMTP11-PLUS ODU Locked Defect Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 461 }

	omtp11PlusOduOpenConnectionIndicationAlarmSeverity OBJECT-TYPE
	      SYNTAX  DisplayString
	      MAX-ACCESS  read-write
	      STATUS  current
	      DESCRIPTION
			"Set or Get the alarm severity level of the
			OMTP11-PLUS ODU Open Connection Indication Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 462 }

	omtp11PlusOduBackwardDefectIndicationAlarmSeverity OBJECT-TYPE
	      SYNTAX  DisplayString
	      MAX-ACCESS  read-write
	      STATUS  current
	      DESCRIPTION
			"Set or Get the alarm severity level of the
			OMTP11-PLUS ODU Backward Defect Indication Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 463 }

	omtp11PlusOduTcm1BackwardIncomingAlignmentErrorAlarmSeverity OBJECT-TYPE
	      SYNTAX  DisplayString
	      MAX-ACCESS  read-write
	      STATUS  current
	      DESCRIPTION
			"Set or Get the alarm severity level of the
			OMTP11-PLUS ODU TCM1 Backward Incoming Alignment Error
			Alarm for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 469 }

	omtp11PlusOduTcm2BackwardIncomingAlignmentErrorAlarmSeverity OBJECT-TYPE
	      SYNTAX  DisplayString
	      MAX-ACCESS  read-write
	      STATUS  current
	      DESCRIPTION
			"Set or Get the alarm severity level of the
			OMTP11-PLUS ODU TCM2 Backward Incoming Alignment Error
			Alarm for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 470 }

	omtp11PlusOduTcm3BackwardIncomingAlignmentErrorAlarmSeverity OBJECT-TYPE
	      SYNTAX  DisplayString
	      MAX-ACCESS  read-write
	      STATUS  current
	      DESCRIPTION
			"Set or Get the alarm severity level of the
			OMTP11-PLUS ODU TCM3 Backward Incoming Alignment Error
			Alarm for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 471 }

	omtp11PlusOduTcm4BackwardIncomingAlignmentErrorAlarmSeverity OBJECT-TYPE
	      SYNTAX  DisplayString
	      MAX-ACCESS  read-write
	      STATUS  current
	      DESCRIPTION
			"Set or Get the alarm severity level of the
			OMTP11-PLUS ODU TCM4 Backward Incoming Alignment Error
			Alarm for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 472 }

	omtp11PlusOduTcm5BackwardIncomingAlignmentErrorAlarmSeverity OBJECT-TYPE
	      SYNTAX  DisplayString
	      MAX-ACCESS  read-write
	      STATUS  current
	      DESCRIPTION
			"Set or Get the alarm severity level of the
			OMTP11-PLUS ODU TCM5 Backward Incoming Alignment Error
			Alarm for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 473 }

	omtp11PlusOduTcm6BackwardIncomingAlignmentErrorAlarmSeverity OBJECT-TYPE
	      SYNTAX  DisplayString
	      MAX-ACCESS  read-write
	      STATUS  current
	      DESCRIPTION
			"Set or Get the alarm severity level of the
			OMTP11-PLUS ODU TCM6 Backward Incoming Alignment Error
			Alarm for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 474 }

	omtp11PlusOpuPayloadMismatchAlarmSeverity OBJECT-TYPE
	      SYNTAX  DisplayString
	      MAX-ACCESS  read-write
	      STATUS  current
	      DESCRIPTION
			"Set or Get the alarm severity level of the
			OMTP11-PLUS Opu Payload Mismatch Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 475 }

	omtp11PlusOchLossOfPayloadAlarmSeverity OBJECT-TYPE
	      SYNTAX  DisplayString
	      MAX-ACCESS  read-write
	      STATUS  current
	      DESCRIPTION
			"Set or Get the alarm severity level of the
			OMTP11-PLUS Och Loss Of Payload Alarm   
			for requested port
 			-----------------------------
			omtp11PlusInterfaceNumber:
			1 - CLIENT-1
			2 - LINE-1
			-----------------------------
			Values:
			1 - Critical
			2 - Major
			3 - Minor
			4 - Deferred
			-----------------------------"
		::= { omtp11PlusConfigurationEntry 476 }

	omtp11PlusSdhLossOfSignalAlarmSeverity OBJECT-TYPE
	      SYNTAX  DisplayString
	      MAX-ACCESS  read-write
	      STATUS  current
	      DESCRIPTION
			"Set or Get the alarm severity level of the
			OMTP11-PLUS SDH Loss Of Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 481 }

	omtp11PlusSdhOutOfFrameAlarmSeverity OBJECT-TYPE
	      SYNTAX  DisplayString
	      MAX-ACCESS  read-write
	      STATUS  current
	      DESCRIPTION
			"Set or Get the alarm severity level of the
			OMTP11-PLUS SDH Out Of Frame Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 482 }

	omtp11PlusSdhLossOfFrameAlarmSeverity OBJECT-TYPE
	      SYNTAX  DisplayString
	      MAX-ACCESS  read-write
	      STATUS  current
	      DESCRIPTION
			"Set or Get the alarm severity level of the
			OMTP11-PLUS SDH Loss Of Frame Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 483 }

	omtp11PlusSdhRsAlarmIndicationSignalAlarmSeverity OBJECT-TYPE
	      SYNTAX  DisplayString
	      MAX-ACCESS  read-write
	      STATUS  current
	      DESCRIPTION
			"Set or Get the alarm severity level of the
			OMTP11-PLUS SDH RS Alarm Indication Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 484 }

	omtp11PlusSdhRsTraceIdentifierMismatchAlarmSeverity OBJECT-TYPE
	      SYNTAX  DisplayString
	      MAX-ACCESS  read-write
	      STATUS  current
	      DESCRIPTION
			"Set or Get the alarm severity level of the
			OMTP11-PLUS SDH RS Trace Identifier Mismatch Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 485 }

	omtp11PlusSdhAuAlarmIndicationSignalAlarmSeverity OBJECT-TYPE
	      SYNTAX  DisplayString
	      MAX-ACCESS  read-write
	      STATUS  current
	      DESCRIPTION
			"Set or Get the alarm severity level of the
			OMTP11-PLUS SDH AU Alarm Indication Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 486 }

	omtp11PlusSdhAuLossOfPointerAlarmSeverity OBJECT-TYPE
	      SYNTAX  DisplayString
	      MAX-ACCESS  read-write
	      STATUS  current
	      DESCRIPTION
			"Set or Get the alarm severity level of the
			OMTP11-PLUS SDH AU Loss Of Pointer Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 487 }

	omtp11PlusSdhMsAlarmIndicationSignalAlarmSeverity OBJECT-TYPE
	      SYNTAX  DisplayString
	      MAX-ACCESS  read-write
	      STATUS  current
	      DESCRIPTION
			"Set or Get the alarm severity level of the
			OMTP11-PLUS SDH MS Alarm Indication Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 488 }

	omtp11PlusSdhMsRemoteErrorIndicationAlarmSeverity OBJECT-TYPE
	      SYNTAX  DisplayString
	      MAX-ACCESS  read-write
	      STATUS  current
	      DESCRIPTION
			"Set or Get the alarm severity level of the
			OMTP11-PLUS SDH MS Remote Error Indication Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 489 }

	omtp11PlusSdhMsRemoteDefectIndicationAlarmSeverity OBJECT-TYPE
	      SYNTAX  DisplayString
	      MAX-ACCESS  read-write
	      STATUS  current
	      DESCRIPTION
			"Set or Get the alarm severity level of the
			OMTP11-PLUS SDH MS Remote Defect Indication Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 490 }

	omtp11PlusSdhMsRemoteFailureIndicationAlarmSeverity OBJECT-TYPE
	      SYNTAX  DisplayString
	      MAX-ACCESS  read-write
	      STATUS  current
	      DESCRIPTION
			"Set or Get the alarm severity level of the
			OMTP11-PLUS SDH MS Remote Failure Indication Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 491 }

	omtp11PlusSdhMsB2ExcessiveErrorAlarmSeverity OBJECT-TYPE
	      SYNTAX  DisplayString
	      MAX-ACCESS  read-write
	      STATUS  current
	      DESCRIPTION
			"Set or Get the alarm severity level of the
			OMTP11-PLUS SDH MS B2 Signal Fail Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 492 }

	omtp11PlusSdhMsB2SignalDegradeAlarmSeverity OBJECT-TYPE
	      SYNTAX  DisplayString
	      MAX-ACCESS  read-write
	      STATUS  current
	      DESCRIPTION
			"Set or Get the alarm severity level of the
			OMTP11-PLUS SDH MS B2 Signal Degrade Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 493 }

	omtp11PlusSdhLossOfSequenceSynchronisationAlarmSeverity OBJECT-TYPE
	      SYNTAX  DisplayString
	      MAX-ACCESS  read-write
	      STATUS  current
	      DESCRIPTION
			"Set or Get the alarm severity level of the
			OMTP11-PLUS SDH Loss Of Sequence Synchronisation Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 494 }

	omtp11PlusSdhHigherOrderPathPayloadLabelMismatchAlarmSeverity OBJECT-TYPE
	      SYNTAX  DisplayString
	      MAX-ACCESS  read-write
	      STATUS  current
	      DESCRIPTION
			"Set or Get the alarm severity level of the
			OMTP11-PLUS SDH Higher Order Path Payload Label Mismatch Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 495 }

	omtp11PlusSdhHigherOrderPathUnequippedAlarmSeverity OBJECT-TYPE
	      SYNTAX  DisplayString
	      MAX-ACCESS  read-write
	      STATUS  current
	      DESCRIPTION
			"Set or Get the alarm severity level of the
			OMTP11-PLUS SDH Higher Order Path Unequipped Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 496 }

	omtp11PlusWan10gLossOfSignalAlarmSeverity OBJECT-TYPE
	      SYNTAX  DisplayString
	      MAX-ACCESS  read-write
	      STATUS  current
	      DESCRIPTION
			"Set or Get the alarm severity level of the
			OMTP11-PLUS WAN10G Loss Of Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 501 }

	omtp11PlusWan10gOutOfFrameAlarmSeverity OBJECT-TYPE
	      SYNTAX  DisplayString
	      MAX-ACCESS  read-write
	      STATUS  current
	      DESCRIPTION
			"Set or Get the alarm severity level of the
			OMTP11-PLUS WAN10G Out Of Frame Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 502 }

	omtp11PlusWan10gLossOfFrameAlarmSeverity OBJECT-TYPE
	      SYNTAX  DisplayString
	      MAX-ACCESS  read-write
	      STATUS  current
	      DESCRIPTION
			"Set or Get the alarm severity level of the
			OMTP11-PLUS WAN10G Loss Of Frame Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 503 }

	omtp11PlusWan10gRsAlarmIndicationSignalAlarmSeverity OBJECT-TYPE
	      SYNTAX  DisplayString
	      MAX-ACCESS  read-write
	      STATUS  current
	      DESCRIPTION
			"Set or Get the alarm severity level of the
			OMTP11-PLUS WAN10G RS Alarm Indication Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 504 }

	omtp11PlusWan10gRsTraceIdentifierMismatchAlarmSeverity OBJECT-TYPE
	      SYNTAX  DisplayString
	      MAX-ACCESS  read-write
	      STATUS  current
	      DESCRIPTION
			"Set or Get the alarm severity level of the
			OMTP11-PLUS WAN10G RS Trace Identifier Mismatch Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 505 }

	omtp11PlusWan10gAuAlarmIndicationSignalAlarmSeverity OBJECT-TYPE
	      SYNTAX  DisplayString
	      MAX-ACCESS  read-write
	      STATUS  current
	      DESCRIPTION
			"Set or Get the alarm severity level of the
			OMTP11-PLUS WAN10G AU Alarm Indication Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 506 }

	omtp11PlusWan10gAuLossOfPointerAlarmSeverity OBJECT-TYPE
	      SYNTAX  DisplayString
	      MAX-ACCESS  read-write
	      STATUS  current
	      DESCRIPTION
			"Set or Get the alarm severity level of the
			OMTP11-PLUS WAN10G AU Loss Of Pointer Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 507 }

	omtp11PlusWan10gMsAlarmIndicationSignalAlarmSeverity OBJECT-TYPE
	      SYNTAX  DisplayString
	      MAX-ACCESS  read-write
	      STATUS  current
	      DESCRIPTION
			"Set or Get the alarm severity level of the
			OMTP11-PLUS WAN10G MS Alarm Indication Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 508 }

	omtp11PlusWan10gMsRemoteErrorIndicationAlarmSeverity OBJECT-TYPE
	      SYNTAX  DisplayString
	      MAX-ACCESS  read-write
	      STATUS  current
	      DESCRIPTION
			"Set or Get the alarm severity level of the
			OMTP11-PLUS WAN10G MS Remote Error Indication Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 509 }

	omtp11PlusWan10gMsRemoteDefectIndicationAlarmSeverity OBJECT-TYPE
	      SYNTAX  DisplayString
	      MAX-ACCESS  read-write
	      STATUS  current
	      DESCRIPTION
			"Set or Get the alarm severity level of the
			OMTP11-PLUS WAN10G MS Remote Defect Indication Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 510 }

	omtp11PlusWan10gMsRemoteFailureIndicationAlarmSeverity OBJECT-TYPE
	      SYNTAX  DisplayString
	      MAX-ACCESS  read-write
	      STATUS  current
	      DESCRIPTION
			"Set or Get the alarm severity level of the
			OMTP11-PLUS WAN10G MS Remote Failure Indication Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 511 }

	omtp11PlusWan10gMsB2ExcessiveErrorAlarmSeverity OBJECT-TYPE
	      SYNTAX  DisplayString
	      MAX-ACCESS  read-write
	      STATUS  current
	      DESCRIPTION
			"Set or Get the alarm severity level of the
			OMTP11-PLUS WAN10G MS B2 Signal Fail Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 512 }

	omtp11PlusWan10gMsB2SignalDegradeAlarmSeverity OBJECT-TYPE
	      SYNTAX  DisplayString
	      MAX-ACCESS  read-write
	      STATUS  current
	      DESCRIPTION
			"Set or Get the alarm severity level of the
			OMTP11-PLUS WAN10G MS B2 Signal Degrade Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 513 }

	omtp11PlusWan10gLossOfSequenceSynchronisationAlarmSeverity OBJECT-TYPE
	      SYNTAX  DisplayString
	      MAX-ACCESS  read-write
	      STATUS  current
	      DESCRIPTION
			"Set or Get the alarm severity level of the
			OMTP11-PLUS WAN10G Loss Of Sequence Synchronisation Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 514 }

	omtp11PlusWan10gHigherOrderPathPayloadLabelMismatchAlarmSeverity OBJECT-TYPE
	      SYNTAX  DisplayString
	      MAX-ACCESS  read-write
	      STATUS  current
	      DESCRIPTION
			"Set or Get the alarm severity level of the
			OMTP11-PLUS WAN10G Higher Order Path Payload Label 
			Mismatch Alarm for requested port
 			-----------------------------
			omtp11PlusInterfaceNumber:
			1 - CLIENT-1
			-----------------------------
			Values:
			1 - Critical
			2 - Major
			3 - Minor
			4 - Deferred
			-----------------------------"
		::= { omtp11PlusConfigurationEntry 515 }

	omtp11PlusWan10gHigherOrderPathUnequippedAlarmSeverity OBJECT-TYPE
	      SYNTAX  DisplayString
	      MAX-ACCESS  read-write
	      STATUS  current
	      DESCRIPTION
			"Set or Get the alarm severity level of the
			OMTP11-PLUS WAN10G Higher Order Path Unequipped Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 516 }

	omtp11PlusLan10gLossOfSignalAlarmSeverity OBJECT-TYPE
	      SYNTAX  DisplayString
	      MAX-ACCESS  read-write
	      STATUS  current
	      DESCRIPTION
			"Set or Get the alarm severity level of the
			OMTP11-PLUS LAN10G Loss Of Signal Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 531 }

	omtp11PlusLan10gLossOfSignalSyncAlarmSeverity OBJECT-TYPE
	      SYNTAX  DisplayString
	      MAX-ACCESS  read-write
	      STATUS  current
	      DESCRIPTION
			"Set or Get the alarm severity level of the
			OMTP11-PLUS LAN10G Loss Of Signal Sync Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 532 }

	omtp11PlusLan10gLinkFailureAlarmSeverity OBJECT-TYPE
	      SYNTAX  DisplayString
	      MAX-ACCESS  read-write
	      STATUS  current
	      DESCRIPTION
			"Set or Get the alarm severity level of the
			OMTP11-PLUS LAN10G Link Failure Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 533 }

	omtp11PlusLan10gFrameCheckSequenceAlarmSeverity OBJECT-TYPE
	      SYNTAX  DisplayString
	      MAX-ACCESS  read-write
	      STATUS  current
	      DESCRIPTION
			"Set or Get the alarm severity level of the
			OMTP11-PLUS LAN10G Frame Check Sequence Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 534 }

	omtp11PlusLan10gCarrierStatusAlarmSeverity OBJECT-TYPE
	      SYNTAX  DisplayString
	      MAX-ACCESS  read-write
	      STATUS  current
	      DESCRIPTION
			"Set or Get the alarm severity level of the
			OMTP11-PLUS LAN10G Carrier Status Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 535 }

	omtp11PlusLan10gHighBerAlarmSeverity OBJECT-TYPE
	      SYNTAX  DisplayString
	      MAX-ACCESS  read-write
	      STATUS  current
	      DESCRIPTION
			"Set or Get the alarm severity level of the
			OMTP11-PLUS LAN10G High Ber Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 536 }

	omtp11PlusLan10gLocalFaultAlarmSeverity OBJECT-TYPE
	      SYNTAX  DisplayString
	      MAX-ACCESS  read-write
	      STATUS  current
	      DESCRIPTION
			"Set or Get the alarm severity level of the
			OMTP11-PLUS LAN10G Local Fault Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 537 }

	omtp11PlusLan10gRemoteFaultAlarmSeverity OBJECT-TYPE
	      SYNTAX  DisplayString
	      MAX-ACCESS  read-write
	      STATUS  current
	      DESCRIPTION
			"Set or Get the alarm severity level of the
			OMTP11-PLUS LAN10G Remote Fault Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 538 }

	omtp11PlusFcTransmitDisparityInversionDefectAlarmSeverity OBJECT-TYPE
	      SYNTAX  DisplayString
	      MAX-ACCESS  read-write
	      STATUS  current
	      DESCRIPTION
			"Set or Get the alarm severity level of the
			OMTP11-PLUS FC Transmit Display Invert Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 551 }

	omtp11PlusFcTransmitDigitalLossOfLinkDefectAlarmSeverity OBJECT-TYPE
	      SYNTAX  DisplayString
	      MAX-ACCESS  read-write
	      STATUS  current
	      DESCRIPTION
			"Set or Get the alarm severity level of the
			OMTP11-PLUS FC Transmit Dlolb Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 552 }

	omtp11PlusFcTrasnmitLossofSynchronizationDefectAlarmSeverity OBJECT-TYPE
	      SYNTAX  DisplayString
	      MAX-ACCESS  read-write
	      STATUS  current
	      DESCRIPTION
			"Set or Get the alarm severity level of the
			OMTP11-PLUS FC Transmit Sync Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 553 }

	omtp11PlusFcReceiveDigitalLossofLinkDefectAlarmSeverity OBJECT-TYPE
	      SYNTAX  DisplayString
	      MAX-ACCESS  read-write
	      STATUS  current
	      DESCRIPTION
			"Set or Get the alarm severity level of the
			OMTP11-PLUS FC Receive Dlolb Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 554 }

	omtp11PlusFcReceiveLossofSynchronizationDefectAlarmSeverity OBJECT-TYPE
	      SYNTAX  DisplayString
	      MAX-ACCESS  read-write
	      STATUS  current
	      DESCRIPTION
			"Set or Get the alarm severity level of the
			OMTP11-PLUS FC Receive Sync Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 555 }

	omtp11PlusFcReceiveTransitionDetectDefectAlarmSeverity OBJECT-TYPE
	      SYNTAX  DisplayString
	      MAX-ACCESS  read-write
	      STATUS  current
	      DESCRIPTION
			"Set or Get the alarm severity level of the
			OMTP11-PLUS FC Receive Xdet Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 556 }

	omtp11PlusFcReceiveAnalogLossofSignalDefectAlarmSeverity OBJECT-TYPE
	      SYNTAX  DisplayString
	      MAX-ACCESS  read-write
	      STATUS  current
	      DESCRIPTION
			"Set or Get the alarm severity level of the
			OMTP11-PLUS FC Receive Asd Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 557 }

	omtp11PlusFcReceiveLineCodeViolationDefectAlarmSeverity OBJECT-TYPE
	      SYNTAX  DisplayString
	      MAX-ACCESS  read-write
	      STATUS  current
	      DESCRIPTION
			"Set or Get the alarm severity level of the
			OMTP11-PLUS FC Receive Lcv Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 558 }

	omtp11PlusGfpCsfSignalFailAlarmSeverity OBJECT-TYPE
	      SYNTAX  DisplayString
	      MAX-ACCESS  read-write
	      STATUS  current
	      DESCRIPTION
			"Set or Get the alarm severity level of the
			OMTP11-PLUS GFP Csf Signal Failure Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 571 }

	omtp11PlusGfpCsfLinkFailAlarmSeverity OBJECT-TYPE
	      SYNTAX  DisplayString
	      MAX-ACCESS  read-write
	      STATUS  current
	      DESCRIPTION
			"Set or Get the alarm severity level of the
			OMTP11-PLUS GFP Csf Link Failure Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 572 }

	omtp11PlusGfpCoreHeaderErrorAlarmSeverity OBJECT-TYPE
	      SYNTAX  DisplayString
	      MAX-ACCESS  read-write
	      STATUS  current
	      DESCRIPTION
			"Set or Get the alarm severity level of the
			OMTP11-PLUS GFP Core Header Error Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 573 }

	omtp11PlusGfpExtentionHeaderErrorAlarmSeverity OBJECT-TYPE
	      SYNTAX  DisplayString
	      MAX-ACCESS  read-write
	      STATUS  current
	      DESCRIPTION
			"Set or Get the alarm severity level of the
			OMTP11-PLUS GFP Extention Header Error Alarm   
			for requested port
 			-----------------------------
			omtp11PlusInterfaceNumber:
			1 - CLIENT-1
			-----------------------------
			Values:
			1 - Critical
			2 - Major
			3 - Minor
			4 - Deferred
			-----------------------------"
		::= { omtp11PlusConfigurationEntry 574 }

	omtp11PlusConfigurationTableRowStatus OBJECT-TYPE
              SYNTAX      RowStatus
              MAX-ACCESS  read-write
              STATUS      current
              DESCRIPTION
                      "	This is MIB realted property,
			NOT to be considered as a card property"
              ::= { omtp11PlusConfigurationEntry 575 }	

--*****************************************************************************
--				    ALARMS
--*****************************************************************************

	omtp11PlusAlarmQueryTable OBJECT-TYPE
		SYNTAX SEQUENCE OF Omtp11PlusAlarmQueryEntry
		MAX-ACCESS not-accessible
		STATUS current
		DESCRIPTION
			"Contains Alarm queries of the OMTP11-PLUS card"
	
		::= { omtp11PlusAlarmQuery 1 }

	omtp11PlusAlarmQueryEntry OBJECT-TYPE
		SYNTAX Omtp11PlusAlarmQueryEntry
		MAX-ACCESS not-accessible
		STATUS current
		DESCRIPTION 
			""
		
		INDEX   { node, rack , subRack , slot , omtp11PlusInterfaceNumber}
	
		::= { omtp11PlusAlarmQueryTable 1 }
		
	Omtp11PlusAlarmQueryEntry ::= 
		SEQUENCE {
				omtp11PlusXfpInputPowerFailureAlarm				DisplayString,
				omtp11PlusXfpOutputPowerFailureAlarm				DisplayString,
				omtp11PlusXfpHighTemperatureAlarm				DisplayString, 
				omtp11PlusXfpLowTemperatureAlarm				DisplayString, 
				omtp11PlusXfpHighTemperatureWarning				DisplayString, 
				omtp11PlusXfpLowTemperatureWarning				DisplayString, 
				omtp11PlusXfpHighBiasCurrentAlarm				DisplayString, 
				omtp11PlusXfpLowBiasCurrentAlarm				DisplayString, 
				omtp11PlusXfpHighBiasCurrentWarning				DisplayString, 
				omtp11PlusXfpLowBiasCurrentWarning				DisplayString, 
				omtp11PlusXfpInputHighPowerAlarm				DisplayString, 
				omtp11PlusXfpInputLowPowerAlarm					DisplayString, 
				omtp11PlusXfpInputHighPowerWarning				DisplayString, 
				omtp11PlusXfpInputLowPowerWarning				DisplayString, 
				omtp11PlusXfpOutputHighPowerAlarm				DisplayString, 
				omtp11PlusXfpOutputLowPowerAlarm				DisplayString, 
				omtp11PlusXfpOutputHighPowerWarning				DisplayString, 
				omtp11PlusXfpOutputLowPowerWarning				DisplayString, 
				omtp11PlusXfpHighSupplyVoltageAlarm				DisplayString, 
				omtp11PlusXfpLowSupplyVoltageAlarm				DisplayString, 
				omtp11PlusXfpHighSupplyVoltageWarning				DisplayString, 
				omtp11PlusXfpLowSupplyVoltageWarning				DisplayString, 
				omtp11PlusXfpPresenceAbsenceNotification			DisplayString, 
				omtp11PlusOtuLossOfSignalAlarm					DisplayString, 
				omtp11PlusOtuLossOfFrameAlarm					DisplayString, 
				omtp11PlusOtuOutOfFrameAlarm					DisplayString, 
				omtp11PlusOtuLossOfMultiFrameAlarm				DisplayString, 
				omtp11PlusOtuOutOfMultiFrameAlarm				DisplayString, 
				omtp11PlusOtuSignalFailAlarm					DisplayString, 
				omtp11PlusOtuSignalDegradeAlarm					DisplayString, 
				omtp11PlusOtuAlarmIndicationSignalAlarm				DisplayString, 
				omtp11PlusOtuIncomingAlignmentErrorAlarm			DisplayString, 
				omtp11PlusOtuTraceIdentifierMismatchAlarm			DisplayString, 
				omtp11PlusOtuBackwardIncomingAlignmentErrorAlarm		DisplayString, 
				omtp11PlusOtuBackwardDefectIndicationAlarm			DisplayString, 
				omtp11PlusOduSignalFailAlarm					DisplayString, 
				omtp11PlusOduSignalDegradeAlarm					DisplayString, 
				omtp11PlusOduAlarmIndicationSignalAlarm				DisplayString, 
				omtp11PlusOduTcm1IncomingAlignmentErrorAlarm			DisplayString,
				omtp11PlusOduTcm2IncomingAlignmentErrorAlarm			DisplayString, 
				omtp11PlusOduTcm3IncomingAlignmentErrorAlarm			DisplayString, 
				omtp11PlusOduTcm4IncomingAlignmentErrorAlarm			DisplayString, 
				omtp11PlusOduTcm5IncomingAlignmentErrorAlarm			DisplayString, 
				omtp11PlusOduTcm6IncomingAlignmentErrorAlarm			DisplayString, 
				omtp11PlusOduTraceIdentifierMismatchAlarm			DisplayString, 
				omtp11PlusOduLockedDefectAlarm					DisplayString, 
				omtp11PlusOduOpenConnectionIndicationAlarm			DisplayString, 
				omtp11PlusOduBackwardDefectIndicationAlarm			DisplayString, 
				omtp11PlusOduTcm1BackwardIncomingAlignmentErrorAlarm		DisplayString, 
				omtp11PlusOduTcm2BackwardIncomingAlignmentErrorAlarm		DisplayString, 
				omtp11PlusOduTcm3BackwardIncomingAlignmentErrorAlarm		DisplayString, 
				omtp11PlusOduTcm4BackwardIncomingAlignmentErrorAlarm		DisplayString,
				omtp11PlusOduTcm5BackwardIncomingAlignmentErrorAlarm		DisplayString, 
				omtp11PlusOduTcm6BackwardIncomingAlignmentErrorAlarm		DisplayString, 
				omtp11PlusOpuPayloadMismatchAlarm				DisplayString, 
				omtp11PlusOchLossOfPayloadAlarm					DisplayString, 
				omtp11PlusSdhLossOfSignalAlarm					DisplayString, 
				omtp11PlusSdhOutOfFrameAlarm					DisplayString, 
				omtp11PlusSdhLossOfFrameAlarm					DisplayString, 
				omtp11PlusSdhRsAlarmIndicationSignalAlarm			DisplayString, 
				omtp11PlusSdhRsTraceIdentifierMismatchAlarm			DisplayString, 
				omtp11PlusSdhAuAlarmIndicationSignalAlarm			DisplayString, 
				omtp11PlusSdhAuLossOfPointerAlarm				DisplayString, 
				omtp11PlusSdhMsAlarmIndicationSignalAlarm			DisplayString, 
				omtp11PlusSdhMsRemoteErrorIndicationAlarm			DisplayString, 
				omtp11PlusSdhMsRemoteDefectIndicationAlarm			DisplayString, 
				omtp11PlusSdhMsRemoteFailureIndicationAlarm			DisplayString, 
				omtp11PlusSdhMsB2ExcessiveErrorAlarm				DisplayString, 
				omtp11PlusSdhMsB2SignalDegradeAlarm				DisplayString, 
				omtp11PlusSdhLossOfSequenceSynchronisationAlarm			DisplayString,
				omtp11PlusSdhHigherOrderPathPayloadLabelMismatchAlarm		DisplayString,
				omtp11PlusSdhHigherOrderPathUnequippedAlarm			DisplayString,
				omtp11PlusWan10gLossOfSignalAlarm				DisplayString,
				omtp11PlusWan10gOutOfFrameAlarm					DisplayString,
				omtp11PlusWan10gLossOfFrameAlarm				DisplayString,
				omtp11PlusWan10gRsAlarmIndicationSignalAlarm			DisplayString,
				omtp11PlusWan10gRsTraceIdentifierMismatchAlarm			DisplayString,
				omtp11PlusWan10gAuAlarmIndicationSignalAlarm			DisplayString,
				omtp11PlusWan10gAuLossOfPointerAlarm				DisplayString,
				omtp11PlusWan10gMsAlarmIndicationSignalAlarm			DisplayString,
				omtp11PlusWan10gMsRemoteErrorIndicationAlarm			DisplayString,
				omtp11PlusWan10gMsRemoteDefectIndicationAlarm			DisplayString,
				omtp11PlusWan10gMsRemoteFailureIndicationAlarm			DisplayString,
				omtp11PlusWan10gMsB2ExcessiveErrorAlarm				DisplayString,
				omtp11PlusWan10gMsB2SignalDegradeAlarm				DisplayString,
				omtp11PlusWan10gLossOfSequenceSynchronisationAlarm		DisplayString,
				omtp11PlusWan10gHigherOrderPathPayloadLabelMismatchAlarm	DisplayString,
				omtp11PlusWan10gHigherOrderPathUnequippedAlarm			DisplayString,
				omtp11PlusLan10gLossOfSignalAlarm				DisplayString,
				omtp11PlusLan10gLossOfSignalSyncAlarm				DisplayString,
				omtp11PlusLan10gLinkFailureAlarm				DisplayString,
				omtp11PlusLan10gFrameCheckSequenceAlarm				DisplayString,
				omtp11PlusLan10gCarrierStatusAlarm				DisplayString,
				omtp11PlusLan10gHighBerAlarm					DisplayString,
				omtp11PlusLan10gLocalFaultAlarm					DisplayString,
				omtp11PlusLan10gRemoteFaultAlarm				DisplayString,
				omtp11PlusFcTransmitDisparityInversionDefectAlarm		DisplayString,
				omtp11PlusFcTransmitDigitalLossOfLinkDefectAlarm		DisplayString,
				omtp11PlusFcTrasnmitLossofSynchronizationDefectAlarm		DisplayString,
				omtp11PlusFcReceiveDigitalLossofLinkDefectAlarm			DisplayString,
				omtp11PlusFcReceiveLossofSynchronizationDefectAlarm		DisplayString,
				omtp11PlusFcReceiveTransitionDetectDefectAlarm			DisplayString,
				omtp11PlusFcReceiveAnalogLossofSignalDefectAlarm		DisplayString,
				omtp11PlusFcReceiveLineCodeViolationDefectAlarm			DisplayString,
				omtp11PlusGfpCsfSignalFailAlarm					DisplayString,
				omtp11PlusGfpCsfLinkFailAlarm					DisplayString,
				omtp11PlusGfpCoreHeaderErrorAlarm				DisplayString,
				omtp11PlusGfpExtentionHeaderErrorAlarm				DisplayString,
				omtp11PlusAlarmQueryTableRowStatus				RowStatus
		}


	omtp11PlusXfpInputPowerFailureAlarm OBJECT-TYPE
		SYNTAX  DisplayString
		MAX-ACCESS  read-only
		STATUS  current
		DESCRIPTION
			"If optical input power at requested interface is less than
			-20dbm, this alarm will be generated
			-----------------------------
			omtp11PlusInterfaceNumber:
			1 - CLIENT-1
			2 - LINE-1
			-----------------------------
			Values :
			If Alarm is Present - Date and Time Stamp
				eg:2017-5-18,9:47:20.0,+5:30
			If Alarm is Absent  - 0
			-----------------------------"
               ::= { omtp11PlusAlarmQueryEntry 1 }

        omtp11PlusXfpOutputPowerFailureAlarm OBJECT-TYPE
		SYNTAX  DisplayString
		MAX-ACCESS  read-only
		STATUS  current
		DESCRIPTION
			"If optical output power at requested interface is less than
			-10dbm, this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 2 }

        omtp11PlusXfpHighTemperatureAlarm OBJECT-TYPE
		SYNTAX  DisplayString
		MAX-ACCESS  read-only
		STATUS  current
		DESCRIPTION
			"If optical temperature at requested interface is greater 
			than the High Temperature Alarm Threshold, alarm will 
			be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 3 }

        omtp11PlusXfpLowTemperatureAlarm OBJECT-TYPE
		SYNTAX  DisplayString
		MAX-ACCESS  read-only
		STATUS  current
		DESCRIPTION
			"If optical temperature at requested interface is lower 
			than the Low Temperature Alarm Threshold, alarm will be 
			generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 4 }

        omtp11PlusXfpHighTemperatureWarning OBJECT-TYPE
		SYNTAX  DisplayString
		MAX-ACCESS  read-only
		STATUS  current
		DESCRIPTION
       			"If optical temperature at requested interface is greater
			than the High Temperature Warning Threshold, this alarm 
			will be generated.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 5 }

        omtp11PlusXfpLowTemperatureWarning OBJECT-TYPE
		SYNTAX  DisplayString
		MAX-ACCESS  read-only
		STATUS  current
		DESCRIPTION
       			"If optical temperature at requested interface is lesser
			than the Low Temperature Warning Threshold, this alarm 
			will be generated.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 6 }

        omtp11PlusXfpHighBiasCurrentAlarm OBJECT-TYPE
		SYNTAX  DisplayString
		MAX-ACCESS  read-only
		STATUS  current
		DESCRIPTION
       			"If optical transmit bias current at requested interface
			is greater than the High Bias Current Alarm Threshold, 
			this this alarm will be generated.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 7 }

        omtp11PlusXfpLowBiasCurrentAlarm OBJECT-TYPE
		SYNTAX  DisplayString
		MAX-ACCESS  read-only
		STATUS  current
		DESCRIPTION
			"If optical transmit bias current at requested interface
			is lesser than the Low Bias Current Alarm Threshold, 
			this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 8 }

        omtp11PlusXfpHighBiasCurrentWarning OBJECT-TYPE
		SYNTAX  DisplayString
		MAX-ACCESS  read-only
		STATUS  current
		DESCRIPTION
       			"If optical transmit bias current at requested interface
			is greater than the High Bias Current Warning Threshold,
			this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 9 }

        omtp11PlusXfpLowBiasCurrentWarning OBJECT-TYPE
		SYNTAX  DisplayString
		MAX-ACCESS  read-only
		STATUS  current
		DESCRIPTION
       			"If optical transmit bias current at requested interface
			is lesser than the Low Bias Current Warning Threshold, 
			this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 10 }

        omtp11PlusXfpInputHighPowerAlarm OBJECT-TYPE
		SYNTAX  DisplayString
		MAX-ACCESS  read-only
		STATUS  current
		DESCRIPTION
       			"If optical Input power at requested interface is 
			greater than the High Input Power Alarm Threshold, this 
			alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 11 }

        omtp11PlusXfpInputLowPowerAlarm OBJECT-TYPE
		SYNTAX  DisplayString
		MAX-ACCESS  read-only
		STATUS  current
		DESCRIPTION
       			"If optical Input power at requested interface is lesser
			than the Low Input Power Alarm Threshold, this alarm 
			will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 12 }

        omtp11PlusXfpInputHighPowerWarning OBJECT-TYPE
		SYNTAX  DisplayString
		MAX-ACCESS  read-only
		STATUS  current
		DESCRIPTION
       			"If optical Input power at requested interface is 
			greater than the High Input Power Warning Threshold, 
			this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 13 }

        omtp11PlusXfpInputLowPowerWarning OBJECT-TYPE
		SYNTAX  DisplayString
		MAX-ACCESS  read-only
		STATUS  current
		DESCRIPTION
       			"If optical Input power at requested interface is lesser
			than the Low Input Power Warning Threshold, this alarm 
			will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 14 }

        omtp11PlusXfpOutputHighPowerAlarm OBJECT-TYPE
		SYNTAX  DisplayString
		MAX-ACCESS  read-only
		STATUS  current
		DESCRIPTION
       			"If optical Output power at requested interface is 
			greater than the High Output Power Alarm Threshold, this
			alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 15 }

        omtp11PlusXfpOutputLowPowerAlarm OBJECT-TYPE
		SYNTAX  DisplayString
		MAX-ACCESS  read-only
		STATUS  current
		DESCRIPTION
       			"If optical Output power at requested interface is 
			lesser than the Low Output Power Alarm Threshold, this 
			alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 16 }

        omtp11PlusXfpOutputHighPowerWarning OBJECT-TYPE
		SYNTAX  DisplayString
		MAX-ACCESS  read-only
		STATUS  current
		DESCRIPTION
       			"If optical Output power at requested interface is 
			greater than the High Output Power Warning Threshold, 
			this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 17 }

        omtp11PlusXfpOutputLowPowerWarning OBJECT-TYPE
		SYNTAX  DisplayString
		MAX-ACCESS  read-only
		STATUS  current
		DESCRIPTION
       			"If optical Output power at requested interface is 
			lesser than the Low Output Power Warning Threshold, this
			alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 18 }

        omtp11PlusXfpHighSupplyVoltageAlarm OBJECT-TYPE
		SYNTAX  DisplayString
		MAX-ACCESS  read-only
		STATUS  current
		DESCRIPTION
       			"If optical Supply Voltage at requested interface is 
			greater than the High Supply Voltage Alarm Threshold, 
			this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 19 }

        omtp11PlusXfpLowSupplyVoltageAlarm OBJECT-TYPE
		SYNTAX  DisplayString
		MAX-ACCESS  read-only
		STATUS  current
		DESCRIPTION
       			"If optical Supply Voltage at requested interface is 
			lesser than the Low Supply Voltage Alarm Threshold, this
			alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 20 }

        omtp11PlusXfpHighSupplyVoltageWarning OBJECT-TYPE
		SYNTAX  DisplayString
		MAX-ACCESS  read-only
		STATUS  current
		DESCRIPTION
       			"If optical Supply Voltage at requested interface is 
			greater than the High Supply Voltage Warning Threshold, 
			this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 21 }

        omtp11PlusXfpLowSupplyVoltageWarning OBJECT-TYPE
		SYNTAX  DisplayString
		MAX-ACCESS  read-only
		STATUS  current
		DESCRIPTION
       			"If optical Supply Voltage at requested interface is 
			lesser than the Low Supply Voltage Warning Threshold, 
			this alarm will be generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 22 }

        omtp11PlusXfpPresenceAbsenceNotification OBJECT-TYPE
		SYNTAX  DisplayString
		MAX-ACCESS  read-only
		STATUS  current
		DESCRIPTION
			"Whenever the XFP is jacked in or jacked out, this 
			notification is generated.
			-----------------------------
			omtp11PlusInterfaceNumber:
			1 - CLIENT-1
			2 - LINE-1
			-----------------------------
			Values :
			If Alarm is Present(module absent) - Date and Time Stamp
				    eg:2017-5-18,9:47:20.0,+5:30
			If Alarm is Absent(module present) - 0
			-----------------------------"
               ::= { omtp11PlusAlarmQueryEntry 23 }

        omtp11PlusOtuLossOfSignalAlarm OBJECT-TYPE
		SYNTAX  DisplayString
		MAX-ACCESS  read-only
		STATUS  current
		DESCRIPTION
			"For port configured with OTU2 traffic,
			if there is no signal received then OTU-LOS Alarm
			is generated.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 31 }

        omtp11PlusOtuLossOfFrameAlarm OBJECT-TYPE
		SYNTAX  DisplayString
		MAX-ACCESS  read-only
		STATUS  current
		DESCRIPTION
			"For port configured with OTU2 traffic, if
			OTU2 frame received are in out-of-frame (OOF)
			state for 3 ms, then OTU-LOF Alarm is generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 32 }

        omtp11PlusOtuOutOfFrameAlarm OBJECT-TYPE
		SYNTAX  DisplayString
		MAX-ACCESS  read-only
		STATUS  current
		DESCRIPTION
			"For port configured with OTU2 traffic, if 5
			consecutive OTU2 frames are received with
			invalid framing patterns then OTU OOF Alarm is
			generated
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 33 }

        omtp11PlusOtuLossOfMultiFrameAlarm OBJECT-TYPE
		SYNTAX  DisplayString
		MAX-ACCESS  read-only
		STATUS  current
		DESCRIPTION
		        "For port configured with OTU2 traffic, if 
			OTU2 frame received are in Out-of-multiframe
			(OOM) state for 3 ms then LOM Alarm is generated.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 34 }

        omtp11PlusOtuOutOfMultiFrameAlarm OBJECT-TYPE
		SYNTAX  DisplayString
		MAX-ACCESS  read-only
		STATUS  current
		DESCRIPTION
		        "For port configured with OTU2 traffic, if the
			received MFAS does not match with the expected multi
			frame number for five consecutive frames then
			OTU OOM Alarm is generated.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 35 }

        omtp11PlusOtuSignalFailAlarm OBJECT-TYPE
		SYNTAX  DisplayString
		MAX-ACCESS  read-only
		STATUS  current
		DESCRIPTION
		       "For port configured with OTU2 traffic, 
			OTU SF alarm is generated when BIP errors evaluated by 
			SM field of OTU2 frame exceeds the 
			'omtp11PlusOtuSignalFailThreshold' threshold
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 36 }

        omtp11PlusOtuSignalDegradeAlarm OBJECT-TYPE
		SYNTAX  DisplayString
		MAX-ACCESS  read-only
		STATUS  current
		DESCRIPTION
		        "For port configured with OTU2 traffic, 
		        OTU SD alarm is generated when BIP errors evaluated by 
			SM field of OTU2 frame exceeds the 
			'omtp11PlusOtuSignalDegradeThreshold' threshold.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 37 }

        omtp11PlusOtuAlarmIndicationSignalAlarm OBJECT-TYPE
		SYNTAX  DisplayString
		MAX-ACCESS  read-only
		STATUS  current
		DESCRIPTION
		         "For port configured with OTU2 traffic, 
			OTU-AIS is generated and transmitted in forward 
			direction, when LOS has been detected at far-end port.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 38 }

        omtp11PlusOtuIncomingAlignmentErrorAlarm OBJECT-TYPE
		SYNTAX  DisplayString
		MAX-ACCESS  read-only
		STATUS  current
		DESCRIPTION
		        "For port configured with OTU2 traffic, 
			OTU-IAE alarm is generated to indicate a 
			frame alignment error 
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 39 }

        omtp11PlusOtuTraceIdentifierMismatchAlarm OBJECT-TYPE
		SYNTAX  DisplayString
		MAX-ACCESS  read-only
		STATUS  current
		DESCRIPTION
		        "For port configured with OTU2 traffic, 
			when there is a trace identifier mismatch in the data 
			stream at SM section, OTU-TIM alarm is generated 
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 40 }

        omtp11PlusOtuBackwardIncomingAlignmentErrorAlarm OBJECT-TYPE
		SYNTAX  DisplayString
		MAX-ACCESS  read-only
		STATUS  current
		DESCRIPTION
		        "For port configured with OTU2 traffic, 
			This alarm conveys that 
			incoming alignment error (IAE) condition that is 
			detected in the far end card
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 41 }

        omtp11PlusOtuBackwardDefectIndicationAlarm OBJECT-TYPE
		SYNTAX  DisplayString
		MAX-ACCESS  read-only
		STATUS  current
		DESCRIPTION
		        "For port configured with OTU2 traffic, 
			OTU-BDI is sent in backward direction, to indicate that
			a defect like LOS, LOF, OTU-TIM has been detected in the
			receive direction.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 42 }

        omtp11PlusOduSignalFailAlarm OBJECT-TYPE
		SYNTAX  DisplayString
		MAX-ACCESS  read-only
		STATUS  current
		DESCRIPTION
		        "For port configured with OTU2 traffic, 
			ODU SF alarm is generated when BIP errors evaluated by 
			PM field of OTU2 frame exceeds the 
			'omtp11PlusOduSignalFailThreshold' threshold.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 51 }

        omtp11PlusOduSignalDegradeAlarm OBJECT-TYPE
		SYNTAX  DisplayString
		MAX-ACCESS  read-only
		STATUS  current
		DESCRIPTION
			"For port configured with OTU2 traffic, 
			ODU SD alarm is generated when BIP errors evaluated by 
			PM field of OTU2 frame exceeds the 	
			'omtp11PlusOduSignalDegradeThreshold' threshold.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 52 }

        omtp11PlusOduAlarmIndicationSignalAlarm OBJECT-TYPE
		SYNTAX  DisplayString
		MAX-ACCESS  read-only
		STATUS  current
		DESCRIPTION
		        "For port configured with OTU2 traffic, 
			ODU-AIS is generated when LOS/TIM/PT mismatch has been 
			detected at far-end port.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 53 }

        omtp11PlusOduTcm1IncomingAlignmentErrorAlarm OBJECT-TYPE
		SYNTAX  DisplayString
		MAX-ACCESS  read-only
		STATUS  current
		DESCRIPTION
			"For port configured with OTU2 traffic, TCM1 IAE
			shall be declared if the accepted STAT information is
			0b010
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 54 }

        omtp11PlusOduTcm2IncomingAlignmentErrorAlarm OBJECT-TYPE
		SYNTAX  DisplayString
		MAX-ACCESS  read-only
		STATUS  current
		DESCRIPTION
			"For port configured with OTU2 traffic, TCM2 IAE
			shall be declared if the accepted STAT information is
			0b010
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 55 }

        omtp11PlusOduTcm3IncomingAlignmentErrorAlarm OBJECT-TYPE
		SYNTAX  DisplayString
		MAX-ACCESS  read-only
		STATUS  current
		DESCRIPTION
			"For port configured with OTU2 traffic, TCM3 IAE
			shall be declared if the accepted STAT information is
			0b010
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 56 }

        omtp11PlusOduTcm4IncomingAlignmentErrorAlarm OBJECT-TYPE
		SYNTAX  DisplayString
		MAX-ACCESS  read-only
		STATUS  current
		DESCRIPTION
			"For port configured with OTU2 traffic, TCM4 IAE
			shall be declared if the accepted STAT information is
			0b010
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 57 }

        omtp11PlusOduTcm5IncomingAlignmentErrorAlarm OBJECT-TYPE
		SYNTAX  DisplayString
		MAX-ACCESS  read-only
		STATUS  current
		DESCRIPTION
			"For port configured with OTU2 traffic, TCM5 IAE
			shall be declared if the accepted STAT information is
			0b010
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 58 }

        omtp11PlusOduTcm6IncomingAlignmentErrorAlarm OBJECT-TYPE
		SYNTAX  DisplayString
		MAX-ACCESS  read-only
		STATUS  current
		DESCRIPTION
			"For port configured with OTU2 traffic, TCM6 IAE
			shall be declared if the accepted STAT information is
			0b010
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 59 }

        omtp11PlusOduTraceIdentifierMismatchAlarm OBJECT-TYPE
		SYNTAX  DisplayString
		MAX-ACCESS  read-only
		STATUS  current
		DESCRIPTION
			"For port configured with OTU2 traffic, 
			when there is a trace identifier mismatch in the data 
			stream at PM section ODU-TIM alarm is generated.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 60 }

        omtp11PlusOduLockedDefectAlarm OBJECT-TYPE
		SYNTAX  DisplayString
		MAX-ACCESS  read-only
		STATUS  current
		DESCRIPTION
			"For port configured with OTU2 traffic, 
			The locked maintenance signal is generated on operator
			request in order to lock the signal from user access. It
			consists of a repeating 0b01010101 pattern in the entire
			ODUk signal, which excludes the Frame Alignment
			overhead and the OTUk overhead.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 61 }

        omtp11PlusOduOpenConnectionIndicationAlarm OBJECT-TYPE
		SYNTAX  DisplayString
		MAX-ACCESS  read-only
		STATUS  current
		DESCRIPTION
			"For port configured with OTU2 traffic, 
			An open connection indication is sent downstream when
			no signal is detected from upstream. It consists of a
			repeating 0b01100110 pattern in the entire ODUk signal,
			which excludes the Frame Alignment overhead and the
			OTUk overhead.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 62 }

        omtp11PlusOduBackwardDefectIndicationAlarm OBJECT-TYPE
		SYNTAX  DisplayString
		MAX-ACCESS  read-only
		STATUS  current
		DESCRIPTION
		        "For port configured with OTU2 traffic, 
			ODU-BDI is sent in backward direction, to indicate that
			a defect like LOS, LOF, ODU-TIM has been detected in the
			receive direction.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 63 }

        omtp11PlusOduTcm1BackwardIncomingAlignmentErrorAlarm OBJECT-TYPE
		SYNTAX  DisplayString
		MAX-ACCESS  read-only
		STATUS  current
		DESCRIPTION
			"For port configured with OTU2 traffic, 
			the presence of this alarm conveys that
			TCM1 incoming alignment error (IAE) condition is 
			detected in the far-end card.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 64 }

        omtp11PlusOduTcm2BackwardIncomingAlignmentErrorAlarm OBJECT-TYPE
		SYNTAX  DisplayString
		MAX-ACCESS  read-only
		STATUS  current
		DESCRIPTION
			"For port configured with OTU2 traffic, 
			the presence of this alarm conveys that
			TCM2 incoming alignment error (IAE) condition is 
			detected in the far-end card.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 65 }

        omtp11PlusOduTcm3BackwardIncomingAlignmentErrorAlarm OBJECT-TYPE
		SYNTAX  DisplayString
		MAX-ACCESS  read-only
		STATUS  current
		DESCRIPTION
			"For port configured with OTU2 traffic, 
			the presence of this alarm conveys that
			TCM3 incoming alignment error (IAE) condition is 
			detected in the far-end card.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 66 }

        omtp11PlusOduTcm4BackwardIncomingAlignmentErrorAlarm OBJECT-TYPE
		SYNTAX  DisplayString
		MAX-ACCESS  read-only
		STATUS  current
		DESCRIPTION
			"For port configured with OTU2 traffic, 
			the presence of this alarm conveys that
			TCM4 incoming alignment error (IAE) condition is 
			detected in the far-end card.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 67 }

        omtp11PlusOduTcm5BackwardIncomingAlignmentErrorAlarm OBJECT-TYPE
		SYNTAX  DisplayString
		MAX-ACCESS  read-only
		STATUS  current
		DESCRIPTION
			"For port configured with OTU2 traffic, 
			the presence of this alarm conveys that
			TCM5 incoming alignment error (IAE) condition is 
			detected in the far-end card.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 68 }

        omtp11PlusOduTcm6BackwardIncomingAlignmentErrorAlarm OBJECT-TYPE
		SYNTAX  DisplayString
		MAX-ACCESS  read-only
		STATUS  current
		DESCRIPTION
			"For port configured with OTU2 traffic, 
			the presence of this alarm conveys that
			TCM6 incoming alignment error (IAE) condition is 
			detected in the far-end card.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 69 }

        omtp11PlusOpuPayloadMismatchAlarm OBJECT-TYPE
		SYNTAX  DisplayString
		MAX-ACCESS  read-only
		STATUS  current
		DESCRIPTION
		        "For port configured with OTU2 traffic, 
			OPU-PLM Alarm is declared if the accepted payload type
			is not equal to the expected payload type.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 70 }

        omtp11PlusOchLossOfPayloadAlarm OBJECT-TYPE
		SYNTAX  DisplayString
		MAX-ACCESS  read-only
		STATUS  current
		DESCRIPTION
		        "If input power level at the XFP is less than 
			-21dbm this this alarm will be generated.
			-----------------------------
			omtp11PlusInterfaceNumber:
			1 - CLIENT-1
			2 - LINE-1
			-----------------------------
			Values :
			If Alarm is Present - Date and Time Stamp
				    eg:2017-5-18,9:47:20.0,+5:30
			If Alarm is Absent  - 0
			-----------------------------"
               ::= { omtp11PlusAlarmQueryEntry 71 }

        omtp11PlusSdhLossOfSignalAlarm OBJECT-TYPE
		SYNTAX  DisplayString
		MAX-ACCESS  read-only
		STATUS  current
		DESCRIPTION
			"For port configured with SDH traffic, 
			If there is No signal received at the requested Port 
			configured with STM64 traffic, then LOS Alarm is 
			generated.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 81 }

        omtp11PlusSdhOutOfFrameAlarm OBJECT-TYPE
		SYNTAX  DisplayString
		MAX-ACCESS  read-only
		STATUS  current
		DESCRIPTION
			"For port configured with SDH traffic, 
			If SDH frame received are out-of-frame (OOF) state for 
			3 ms at the Port configured with STM64 traffic, LOF 
			Alarm is generated.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 82 }

        omtp11PlusSdhLossOfFrameAlarm OBJECT-TYPE
		SYNTAX  DisplayString
		MAX-ACCESS  read-only
		STATUS  current
		DESCRIPTION
		        "For port configured with SDH traffic, 
			If SDH frame received are out-of-frame (OOF) state for 
			3 ms at the Port configured with STM64 traffic, LOF 
			Alarm is generated.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 83 }

        omtp11PlusSdhRsAlarmIndicationSignalAlarm OBJECT-TYPE
		SYNTAX  DisplayString
		MAX-ACCESS  read-only
		STATUS  current
		DESCRIPTION
		        "For port configured with SDH traffic, 
			RS-AIS alarm is indicated when there is no signal 
			received in far end port.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 84 }

        omtp11PlusSdhRsTraceIdentifierMismatchAlarm OBJECT-TYPE
		SYNTAX  DisplayString
		MAX-ACCESS  read-only
		STATUS  current
		DESCRIPTION
		        "For port configured with SDH traffic, 
			RS-TIM alarm is indicated when there is mimatch in the 
			expected traces at the requested port configured with 
			STM64 traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 85 }

        omtp11PlusSdhAuAlarmIndicationSignalAlarm OBJECT-TYPE
		SYNTAX  DisplayString
		MAX-ACCESS  read-only
		STATUS  current
		DESCRIPTION
		        "For port configured with SDH traffic, 
			AU-AIS is an alarm indication signal (AIS) is a signal 
			sent downstream as an indication that an upstream
			defect has been detected.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 86 }

        omtp11PlusSdhAuLossOfPointerAlarm OBJECT-TYPE
		SYNTAX  DisplayString
		MAX-ACCESS  read-only
		STATUS  current
		DESCRIPTION
		        "For port configured with SDH traffic, 
			LOP state occurs when N consecutive invalid pointers
			are received or N consecutive New Data Flags (NDF)
			are received where N = 8, 9, or 10. LOP state is 
			cleared when three equal valid pointers or three
			consecutive AIS indications are received.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 87 }

        omtp11PlusSdhMsAlarmIndicationSignalAlarm OBJECT-TYPE
		SYNTAX  DisplayString
		MAX-ACCESS  read-only
		STATUS  current
		DESCRIPTION
		        "For port configured with SDH traffic, 
			MS-AIS is an alarm indication signal (AIS) is a signal 
			sent downstream as an indication that an upstream
			defect has been detected.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 88 }

        omtp11PlusSdhMsRemoteErrorIndicationAlarm OBJECT-TYPE
		SYNTAX  DisplayString
		MAX-ACCESS  read-only
		STATUS  current
		DESCRIPTION
		        "For port configured with SDH traffic, 
			This alarm is an indication returned to a transmitting
			node (source) that an errored block has been detected at
			the receiving node (sink).
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 89 }

        omtp11PlusSdhMsRemoteDefectIndicationAlarm OBJECT-TYPE
		SYNTAX  DisplayString
		MAX-ACCESS  read-only
		STATUS  current
		DESCRIPTION
		        "For port configured with SDH traffic, 
			MS-RDI is a signal returned to the transmitting equipment 
			upon detecting a LOS, LOF, or MS-AIS defect
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 90 }

        omtp11PlusSdhMsRemoteFailureIndicationAlarm OBJECT-TYPE
		SYNTAX  DisplayString
		MAX-ACCESS  read-only
		STATUS  current
		DESCRIPTION
		        "For port configured with SDH traffic, 
			A failure is a defect that persists beyond the maximum
			time allocated to the transmission system protection
			mechanisms. When this situation occurs, an RFI is sent
			to the far end and will initiate a path protection
			switch if this function has been provisioned.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 91 }

        omtp11PlusSdhMsB2ExcessiveErrorAlarm OBJECT-TYPE
		SYNTAX  DisplayString
		MAX-ACCESS  read-only
		STATUS  current
		DESCRIPTION
		        "For port configured with SDH traffic, 
			B2 SF alarm is generated when Parity errors evaluated 
			by byte B2 of SDH frame exceeds the 
			'omtp11PlusSdhMsB2ExcessiveErrorThreshold' threshold.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 92 }

        omtp11PlusSdhMsB2SignalDegradeAlarm OBJECT-TYPE
		SYNTAX  DisplayString
		MAX-ACCESS  read-only
		STATUS  current
		DESCRIPTION
		        "For port configured with SDH traffic, 
			B2 SD alarm is generated when Parity errors evaluated 
			by byte B2 of SDH frame exceeds the 
			'omtp11PlusSdhMsB2SignalDegradeThreshold' threshold.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 93 }

        omtp11PlusSdhLossOfSequenceSynchronisationAlarm OBJECT-TYPE
		SYNTAX  DisplayString
		MAX-ACCESS  read-only
		STATUS  current
		DESCRIPTION
		        "For port configured with SDH traffic, 
			Sequence synchronisation shall be considered to be lost
			and re-synchronisation shall be started if:
			The bit error ratio is ≥ 0.20 during an integration
			interval of 1 second; or
			It can be unambiguously identified that the test
			sequence and the reference sequence are out of phase.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 94 }
               
        omtp11PlusSdhHigherOrderPathPayloadLabelMismatchAlarm OBJECT-TYPE
		SYNTAX  DisplayString
		MAX-ACCESS  read-only
		STATUS  current
		DESCRIPTION
		        "Reserved for future study
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 95 }
               
        omtp11PlusSdhHigherOrderPathUnequippedAlarm OBJECT-TYPE
		SYNTAX  DisplayString
		MAX-ACCESS  read-only
		STATUS  current
		DESCRIPTION
		        "For port configured with SDH traffic, 
			These signals indicate to downstream transport
			processing functions (refer to ITU-T Rec. G.803) that
			the virtual container is unoccupied,
			not connected to a path termination source function.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 96 }

        omtp11PlusWan10gLossOfSignalAlarm OBJECT-TYPE
		SYNTAX  DisplayString
		MAX-ACCESS  read-only
		STATUS  current
		DESCRIPTION
		        "For port configured with 10G WAN traffic, 
			If there is No signal received at the requested port 
			configured with WAN10G traffic then LOS Alarm is 
			generated.			
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 101 }

        omtp11PlusWan10gOutOfFrameAlarm OBJECT-TYPE
		SYNTAX  DisplayString
		MAX-ACCESS  read-only
		STATUS  current
		DESCRIPTION
		        "For port configured with 10G WAN traffic, 
			If WAN frame received are out-of-frame (OOF) state for 
			3 ms at the requested port configured with WAN10G 
			traffic, LOF Alarm is generated.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 102 }

        omtp11PlusWan10gLossOfFrameAlarm OBJECT-TYPE
                      SYNTAX  DisplayString
		MAX-ACCESS  read-only
		STATUS  current
                       DESCRIPTION
		        "For port configured with 10G WAN traffic, 
			If WAN10G frame received are out-of-frame (OOF) state 
			for 3 ms at the requested port configured with WAN10G 
			traffic, LOF Alarm is generated.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 103 }

        omtp11PlusWan10gRsAlarmIndicationSignalAlarm OBJECT-TYPE
		SYNTAX  DisplayString
		MAX-ACCESS  read-only
		STATUS  current
		DESCRIPTION
		        "For port configured with 10G WAN traffic, 
			RS-AIS alarm is indicated when there is no signal 
			received in far end port.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 104 }

        omtp11PlusWan10gRsTraceIdentifierMismatchAlarm OBJECT-TYPE
		SYNTAX  DisplayString
		MAX-ACCESS  read-only
		STATUS  current
		DESCRIPTION
		        "For port configured with 10G WAN traffic, 
			RS-TIM alarm is indicated when there is mimatch in the 
			expected traces.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 105 }

        omtp11PlusWan10gAuAlarmIndicationSignalAlarm OBJECT-TYPE
		SYNTAX  DisplayString
		MAX-ACCESS  read-only
		STATUS  current
		DESCRIPTION
		        "For port configured with 10G WAN traffic, 
			AU-AIS is an alarm indication signal (AIS) is a signal 
			sent downstream as an indication that an upstream
			defect has been detected.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 106 }

        omtp11PlusWan10gAuLossOfPointerAlarm OBJECT-TYPE
		SYNTAX  DisplayString
		MAX-ACCESS  read-only
		STATUS  current
		DESCRIPTION
		        "For port configured with 10G WAN traffic, 
			LOP state occurs when N consecutive invalid pointers
			are received or N consecutive New Data Flags (NDF)
			are received where N = 8, 9, or 10. LOP state is 
			cleared when three equal valid pointers or three
			consecutive AIS indications are received.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 107 }

        omtp11PlusWan10gMsAlarmIndicationSignalAlarm OBJECT-TYPE
		SYNTAX  DisplayString
		MAX-ACCESS  read-only
		STATUS  current
		DESCRIPTION
		        "For port configured with 10G WAN traffic, 
			MS-AIS is an alarm indication signal (AIS) is a signal 
			sent downstream as an indication that an upstream
			defect has been detected.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 108 }

        omtp11PlusWan10gMsRemoteErrorIndicationAlarm OBJECT-TYPE
		SYNTAX  DisplayString
		MAX-ACCESS  read-only
		STATUS  current
		DESCRIPTION
		        "For port configured with 10G WAN traffic, 
			This alarm is an indication returned to a transmitting
			node (source) that an errored block has been detected at
			the receiving node (sink).
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 109 }

        omtp11PlusWan10gMsRemoteDefectIndicationAlarm OBJECT-TYPE
		SYNTAX  DisplayString
		MAX-ACCESS  read-only
		STATUS  current
		DESCRIPTION
		        "For port configured with 10G WAN traffic, 
			MS-RDI is a signal returned to the transmitting 
			equipment upon detecting a LOS, LOF, or MS-AIS defect.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 110 }

        omtp11PlusWan10gMsRemoteFailureIndicationAlarm OBJECT-TYPE
		SYNTAX  DisplayString
		MAX-ACCESS  read-only
		STATUS  current
		DESCRIPTION
		        "For port configured with 10G WAN traffic, 
			A failure is a defect that persists beyond the maximum
			time allocated to the transmission system protection
			mechanisms. When this situation occurs, an RFI is sent
			to the far end and will initiate a path protection
			switch if this function has been provisioned.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 111 }

        omtp11PlusWan10gMsB2ExcessiveErrorAlarm OBJECT-TYPE
		SYNTAX  DisplayString
		MAX-ACCESS  read-only
		STATUS  current
		DESCRIPTION
		        "For port configured with 10G WAN traffic, 
			B2 SF alarm is generated when Parity errors evaluated 
			by byte B2 of Wan10g frame exceeds the 
			'omtp11PlusWan10gMsB2ExcessiveErrorThreshold' threshold
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 112 }

        omtp11PlusWan10gMsB2SignalDegradeAlarm OBJECT-TYPE
		SYNTAX  DisplayString
		MAX-ACCESS  read-only
		STATUS  current
		DESCRIPTION
		        "For port configured with 10G WAN traffic, 
			B2 SD alarm is generated when Parity errors evaluated
			by byte B2 of Wan10g frame exceeds the
			'omtp11PlusWan10gMsB2SignalDegradeThreshold' threshold
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 113 }

        omtp11PlusWan10gLossOfSequenceSynchronisationAlarm OBJECT-TYPE
		SYNTAX  DisplayString
		MAX-ACCESS  read-only
		STATUS  current
		DESCRIPTION
		        "For port configured with 10G WAN traffic, 
			Sequence synchronisation shall be considered to be lost
			and re-synchronisation shall be started if:
			The bit error ratio is ≥ 0.20 during an integration
			interval of 1 second; or
			It can be unambiguously identified that the test
			sequence and the reference sequence are out of phase.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 114 }
               
        omtp11PlusWan10gHigherOrderPathPayloadLabelMismatchAlarm OBJECT-TYPE
		SYNTAX  DisplayString
		MAX-ACCESS  read-only
		STATUS  current
		DESCRIPTION
		        "Reserved for future study
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 115 }               
               
        omtp11PlusWan10gHigherOrderPathUnequippedAlarm OBJECT-TYPE
		SYNTAX  DisplayString
		MAX-ACCESS  read-only
		STATUS  current
		DESCRIPTION
		        "For port configured with 10G WAN traffic, 
			These signals indicate to downstream transport
			processing functions (refer to ITU-T Rec. G.803) that
			the virtual container is unoccupied, not connected to a 
			path termination source function.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 116 }
               
	omtp11PlusLan10gLossOfSignalAlarm OBJECT-TYPE
		SYNTAX  DisplayString
		MAX-ACCESS  read-only
		STATUS  current
		DESCRIPTION
		        "For port configured with 10G LAN traffic, 
			If there is No signal received at the Port configured 
			with LAN10G traffic, it leads to LOS Alarm.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 121 }

        omtp11PlusLan10gLossOfSignalSyncAlarm OBJECT-TYPE
		SYNTAX  DisplayString
		MAX-ACCESS  read-only
		STATUS  current
		DESCRIPTION
		        "For port configured with 10G LAN traffic, 
			When the receive interface does not achieve PCS
		         sync it is called Loss of Sync.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 122 }

        omtp11PlusLan10gLinkFailureAlarm OBJECT-TYPE
		SYNTAX  DisplayString
		MAX-ACCESS  read-only
		STATUS  current
		DESCRIPTION
		       "For port configured with 10G LAN traffic, 
			In the case of remote fault alarm, the link failure 
			alarm is generated.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 123 }

        omtp11PlusLan10gFrameCheckSequenceAlarm OBJECT-TYPE
		SYNTAX  DisplayString
		MAX-ACCESS  read-only
		STATUS  current
		DESCRIPTION
		       "For port configured with 10G LAN traffic, 
			In the incoming ethernet frame, if the FCS value in the
			FCS byte and the FCS value calculated for the payload
			of the frame doesnt match, then number of FCS errors
			is incremented. If in one second 50 such FCS errors
			are got, then FCS this alarm will be generated. 
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 124 }

        omtp11PlusLan10gCarrierStatusAlarm OBJECT-TYPE
		SYNTAX  DisplayString
		MAX-ACCESS  read-only
		STATUS  current
		DESCRIPTION
		       "For port configured with 10G LAN traffic, 
			Whenever there is an absence of the carrier signal
			i.e. carrier sense loss occurs this alarm is generated.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 125 }

        omtp11PlusLan10gHighBerAlarm OBJECT-TYPE
		SYNTAX  DisplayString
		MAX-ACCESS  read-only
		STATUS  current
		DESCRIPTION
		       "For port configured with 10G LAN traffic, 
			High Bit Errors Alarm is indicated when signal BER is greater than 1e−4
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 126 }

        omtp11PlusLan10gLocalFaultAlarm OBJECT-TYPE
		SYNTAX  DisplayString
		MAX-ACCESS  read-only
		STATUS  current
		DESCRIPTION
			"For port configured with 10G LAN traffic, 
			If Fault is detected on the receive data path then Local
			Fault Alarm is generated
			port should be configured with LAN10G traffic.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 127 }

        omtp11PlusLan10gRemoteFaultAlarm OBJECT-TYPE
		SYNTAX  DisplayString
		MAX-ACCESS  read-only
		STATUS  current
		DESCRIPTION
		       "For port configured with 10G LAN traffic, 
			If Fault is detected on the transmit data path then 
			Remote Fault Alarm is generated
			port should be configured with LAN10G traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 128 }

        omtp11PlusFcTransmitDisparityInversionDefectAlarm OBJECT-TYPE
		SYNTAX  DisplayString
		MAX-ACCESS  read-only
		STATUS  current
		DESCRIPTION
		        "For port configured with FC 800/1200 traffic, 
			Get FC Transmit Display Invert status
			for requested port configured with FC traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 141 }

        omtp11PlusFcTransmitDigitalLossOfLinkDefectAlarm OBJECT-TYPE
		SYNTAX  DisplayString
		MAX-ACCESS  read-only
		STATUS  current
		DESCRIPTION
		        "For port configured with FC 800/1200 traffic, 
			Get FC Transmit DLOLB status 
			for requested port configured with FC traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 142 }

        omtp11PlusFcTrasnmitLossofSynchronizationDefectAlarm OBJECT-TYPE
		SYNTAX  DisplayString
		MAX-ACCESS  read-only
		STATUS  current
		DESCRIPTION
		        "For port configured with FC 800/1200 traffic, 
			Get FC Transmit Sync status 
			for requested port configured with FC traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 143 }

        omtp11PlusFcReceiveDigitalLossofLinkDefectAlarm OBJECT-TYPE
		SYNTAX  DisplayString
		MAX-ACCESS  read-only
		STATUS  current
		DESCRIPTION
		        "For port configured with FC 800/1200 traffic, 
			Get FC Receive DLOLB status 
			for requested port configured with FC traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 144 }

        omtp11PlusFcReceiveLossofSynchronizationDefectAlarm OBJECT-TYPE
		SYNTAX  DisplayString
		MAX-ACCESS  read-only
		STATUS  current
		DESCRIPTION
		        "For port configured with FC 800/1200 traffic, 
			Get FC Receive Sync alarm status 
			for requested port configured with FC traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 145 }

        omtp11PlusFcReceiveTransitionDetectDefectAlarm OBJECT-TYPE
		SYNTAX  DisplayString
		MAX-ACCESS  read-only
		STATUS  current
		DESCRIPTION
		        "For port configured with FC 800/1200 traffic, 
			Get FC Receive Xdet alarm status 
			for requested port configured with FC traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 146 }

        omtp11PlusFcReceiveAnalogLossofSignalDefectAlarm OBJECT-TYPE
		SYNTAX  DisplayString
		MAX-ACCESS  read-only
		STATUS  current
		DESCRIPTION
		        "For port configured with FC 800/1200 traffic, 
			Get FC Receive Asd alarm status 
			for requested port configured with FC traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 147 }

        omtp11PlusFcReceiveLineCodeViolationDefectAlarm OBJECT-TYPE
		SYNTAX  DisplayString
		MAX-ACCESS  read-only
		STATUS  current
		DESCRIPTION
		        "For port configured with FC 800/1200 traffic, 
			Get FC Receive Lcv alarm status 
			for requested port configured with FC traffic
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 148 }

        omtp11PlusGfpCsfSignalFailAlarm OBJECT-TYPE
		SYNTAX  DisplayString
		MAX-ACCESS  read-only
		STATUS  current
		DESCRIPTION
		        "If signal loss at the far-end occurs, then
			this alarm is detected at the near-end card.
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 161 }

        omtp11PlusGfpCsfLinkFailAlarm OBJECT-TYPE
		SYNTAX  DisplayString
		MAX-ACCESS  read-only
		STATUS  current
		DESCRIPTION
			"If there is a link failure occured at the far-end
			card, then this alarm is detected at the near-end card 
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 162 }

        omtp11PlusGfpCoreHeaderErrorAlarm OBJECT-TYPE
		SYNTAX  DisplayString
		MAX-ACCESS  read-only
		STATUS  current
		DESCRIPTION
			"This alarm is generated if the core header error
			count is found to be greater than 50 for a particular
			instance. i.e. for a particular second 
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 163 }

        omtp11PlusGfpExtentionHeaderErrorAlarm OBJECT-TYPE
		SYNTAX  DisplayString
		MAX-ACCESS  read-only
		STATUS  current
		DESCRIPTION
			"This alarm is generated if the extention header error
			count is found to be greater than 50 for a particular
			instance. i.e. for a particular second 
			-----------------------------
			omtp11PlusInterfaceNumber:
			1 - CLIENT-1
			-----------------------------
			Values :
			If Alarm is Present - Date and Time Stamp
				    eg:2017-5-18,9:47:20.0,+5:30
			If Alarm is Absent  - 0
			-----------------------------"
               ::= { omtp11PlusAlarmQueryEntry 164 }

	omtp11PlusAlarmQueryTableRowStatus OBJECT-TYPE
              SYNTAX      RowStatus
              MAX-ACCESS  read-write
              STATUS      current
              DESCRIPTION
                      "	This is MIB realted property,
			NOT to be considered as a card property"
              ::= { omtp11PlusAlarmQueryEntry 165 }	


--*****************************************************************************
--				    PERFORMANCE
--***************************************************************************** 	
	omtp11PlusPerformanceTable OBJECT-TYPE
		SYNTAX SEQUENCE OF Omtp11PlusPerformanceEntry
		MAX-ACCESS not-accessible
		STATUS current
		DESCRIPTION
			"we can get performance details of the OMTP11-PLUS Card"
	
		::= { omtp11PlusPerformance 1 }

	omtp11PlusPerformanceEntry OBJECT-TYPE
		SYNTAX Omtp11PlusPerformanceEntry
		MAX-ACCESS not-accessible
		STATUS current
		DESCRIPTION 
			""
	
		INDEX   { node, rack , subRack , slot , omtp11PlusInterfaceNumber}
	
		::= { omtp11PlusPerformanceTable 1 }

		Omtp11PlusPerformanceEntry ::= 
			SEQUENCE {
					omtp11PlusXfpInputPower                                     		DisplayString,
				        omtp11PlusXfpOutputPower                                    		DisplayString,
				        omtp11PlusXfpBiasCurrent                                    		DisplayString,
				        omtp11PlusXfpSupplyVoltage                                  		DisplayString,
				        omtp11PlusXfpTemperature                                    		DisplayString,
				        omtp11PlusOtnFecUncorrectedWords                            		DisplayString,
				        omtp11PlusOtnFecCorrectedBits                              		DisplayString,       
				        omtp11PlusOtnFecZerosCorrectedBits                          		DisplayString,
				        omtp11PlusOtnFecOnesCorrectedBits                           		DisplayString,
				        omtp11PlusOtuBitInterleavedParityErrors                     		DisplayString,
				        omtp11PlusOtuIncomingAlignmentErrorSeconds                  		DisplayString,
				        omtp11PlusOtuBackwardErrorIndicationErrorCount                  	DisplayString,
				        omtp11PlusOtuBackwardIncomingAlignmentErrorSeconds          		DisplayString,
				        omtp11PlusOtuErrorFreeSeconds						DisplayString,
				        omtp11PlusOtuErrorSeconds						DisplayString,
				        omtp11PlusOtuBackgroundBlockErrors					DisplayString,
				        omtp11PlusOtuSevereErrorSeconds						DisplayString,
				        omtp11PlusOtuUnavailableSeconds						DisplayString,
				        omtp11PlusOtuBackgroundBlockErrorRatio					DisplayString,
				        omtp11PlusOtuSevereErrorSecondsErrorRatio				DisplayString,
				        omtp11PlusOtuFarEndErrorFreeSeconds					DisplayString,
				        omtp11PlusOtuFarEndErrorSeconds						DisplayString,
				        omtp11PlusOtuFarEndBackgroundBlockErrors				DisplayString,
				        omtp11PlusOtuFarEndSevereErrorSeconds					DisplayString,
				        omtp11PlusOtuFarEndUnavailableSeconds					DisplayString,
				        omtp11PlusOtuFarEndBackgroundBlockErrorRatio				DisplayString,
				        omtp11PlusOtuFarEndSevereErrorSecondsErrorRatio				DisplayString,
					omtp11PlusOtuErrorRatio							DisplayString,
					omtp11PlusOtuBitErrorRate						DisplayString,
					omtp11PlusOtuFramesReceived						DisplayString,
				        omtp11PlusOduBitInterleavedParityErrors					DisplayString,
				        omtp11PlusOduTcm1BitInterleavedParityErrors				DisplayString,
				        omtp11PlusOduTcm2BitInterleavedParityErrors				DisplayString,
				        omtp11PlusOduTcm3BitInterleavedParityErrors				DisplayString,
				        omtp11PlusOduTcm4BitInterleavedParityErrors				DisplayString,
				        omtp11PlusOduTcm5BitInterleavedParityErrors				DisplayString,
				        omtp11PlusOduTcm6BitInterleavedParityErrors				DisplayString,
				        omtp11PlusOduTcm1IncomingAlignmentErrorSeconds				DisplayString,
				        omtp11PlusOduBackwardErrorIndicationErrorCount				DisplayString,
				        omtp11PlusOduTcm1BackwardErrorIndicationErrorCount			DisplayString,
				        omtp11PlusOduTcm2BackwardErrorIndicationErrorCount			DisplayString,
				        omtp11PlusOduTcm3BackwardErrorIndicationErrorCount			DisplayString,
				        omtp11PlusOduTcm4BackwardErrorIndicationErrorCount			DisplayString,
				        omtp11PlusOduTcm5BackwardErrorIndicationErrorCount			DisplayString,
				        omtp11PlusOduTcm6BackwardErrorIndicationErrorCount			DisplayString,
				        omtp11PlusOduTcm1BackwardIncomingAlignmentErrorSeconds			DisplayString,
				        omtp11PlusOduDelayMeasurement						DisplayString,
				        omtp11PlusOduErrorFreeSeconds						DisplayString,
				        omtp11PlusOduErrorSeconds						DisplayString,
				        omtp11PlusOduBackgroundBlockErrors					DisplayString,
				        omtp11PlusOduSevereErrorSeconds						DisplayString,
				        omtp11PlusOduUnavailableSeconds						DisplayString,
				        omtp11PlusOduBackgroundBlockErrorRatio					DisplayString,
				        omtp11PlusOduSevereErrorSecondsErrorRatio				DisplayString,
				        omtp11PlusOduFarEndErrorFreeSeconds					DisplayString,
				        omtp11PlusOduFarEndErrorSeconds						DisplayString,
				        omtp11PlusOduFarEndBackgroundBlockErrors				DisplayString,
				        omtp11PlusOduFarEndSevereErrorSeconds					DisplayString,
				        omtp11PlusOduFarEndUnavailableSeconds					DisplayString,
				        omtp11PlusOduFarEndBackgroundBlockErrorRatio				DisplayString,
				        omtp11PlusOduFarEndSevereErrorSecondsErrorRatio				DisplayString,
				        omtp11PlusSdhRsB1BitInterleavedParityErrors				DisplayString,
				        omtp11PlusSdhMsB2BitInterleavedParityErrors				DisplayString,
				        omtp11PlusSdhMsB3BitInterleavedParityErrors				DisplayString,
				        omtp11PlusSdhMsRemoteErrorIndicationErrorCount				DisplayString,
				        omtp11PlusSdhMsRemoteDefectIndicationErrorCount				DisplayString,
				        omtp11PlusSdhErrorFreeSeconds						DisplayString,
				        omtp11PlusSdhErrorSeconds						DisplayString,
				        omtp11PlusSdhBackgroundBlockErrors					DisplayString,
				        omtp11PlusSdhSevereErrorSeconds						DisplayString,
				        omtp11PlusSdhUnavailableSeconds						DisplayString,
				        omtp11PlusSdhErrorSecondsErrorRatio					DisplayString,
				        omtp11PlusSdhBackgroundBlockErrorRatio					DisplayString,
				        omtp11PlusSdhSevereErrorSecondsErrorRatio				DisplayString,
				        omtp11PlusWan10gRsB1BitInterleavedParityErrors				DisplayString,
				        omtp11PlusWan10gMsB2BitInterleavedParityErrors				DisplayString,
				        omtp11PlusWan10gMsB3BitInterleavedParityErrors				DisplayString,
				        omtp11PlusWan10gMsRemoteErrorIndicationErrorCount			DisplayString,
				        omtp11PlusWan10gMsRemoteDefectIndicationErrorCount			DisplayString,
				        omtp11PlusWan10gErrorFreeSeconds					DisplayString,
				        omtp11PlusWan10gErrorSeconds						DisplayString,
				        omtp11PlusWan10gBackgroundBlockErrors					DisplayString,
				        omtp11PlusWan10gSevereErrorSeconds					DisplayString,
				        omtp11PlusWan10gUnavailableSeconds					DisplayString,
				        omtp11PlusWan10gErrorSecondsErrorRatio					DisplayString,
				        omtp11PlusWan10gBackgroundBlockErrorRatio				DisplayString,
				        omtp11PlusWan10gSevereErrorSecondsErrorRatio				DisplayString,
				        omtp11PlusLan10gMacTerminatedFramesTransmitted				DisplayString,
				        omtp11PlusLan10gMacTerminatedFramesReceived				DisplayString,
				        omtp11PlusLan10gMacTerminatedPauseFramesTransmitted			DisplayString,
				        omtp11PlusLan10gMacTerminatedPauseFramesReceived			DisplayString,
				        omtp11PlusLan10gMacTerminatedUnicastFramesTransmitted			DisplayString,
				        omtp11PlusLan10gMacTerminatedUnicastFramesReceived			DisplayString,
				        omtp11PlusLan10gMacTerminatedMulticastFramesTransmitted			DisplayString,
				        omtp11PlusLan10gMacTerminatedMulticastFramesReceived			DisplayString,
				        omtp11PlusLan10gMacTerminatedBroadcastFramesTransmitted			DisplayString,
				        omtp11PlusLan10gMacTerminatedBroadcastFramesReceived			DisplayString,
				        omtp11PlusLan10gMacTerminatedUnderSizeFramesTransmitted			DisplayString,
				        omtp11PlusLan10gMacTerminatedUnderSizeFramesReceived			DisplayString,
				        omtp11PlusLan10gMacTerminatedOverSizeFramesTransmitted			DisplayString,
				        omtp11PlusLan10gMacTerminatedOverSizeFramesReceived			DisplayString,
				        omtp11PlusLan10gMacTerminatedVlanTaggedFramesTransmitted		DisplayString,
				        omtp11PlusLan10gMacTerminatedVlanTaggedFramesReceived			DisplayString,
				        omtp11PlusLan10gMacTerminatedFrameSymbolErrorsReceived			DisplayString,
				        omtp11PlusLan10gMacTerminatedFragmentFramesReceived			DisplayString,
				        omtp11PlusLan10gMacTerminatedFrameCheckSequenceErrorsReceived		DisplayString,
					omtp11PlusLan10gMacTerminatedFramesReceivedWithNoDefect			DisplayString,
					omtp11PlusLan10gMacTerminatedBytesTransmitted				DisplayString,
					omtp11PlusLan10gMacTerminatedBytesReceived				DisplayString,	
					omtp11PlusLan10gMacTerminatedControlFramesTransmitted			DisplayString,
					omtp11PlusLan10gMacTerminatedControlFramesReceived			DisplayString,
				        omtp11PlusLan10gTransparentTransmitLcvCount				DisplayString,
				        omtp11PlusLan10gTransparentTransmitPropagationErrorDeletionCount	DisplayString,
				        omtp11PlusLan10gTransparentTransmitIdleDeletionCount			DisplayString,
				        omtp11PlusLan10gTransparentTransmitConfDeletionCount			DisplayString,
				        omtp11PlusLan10gTransparentTransmitPropagationInsertionCount		DisplayString,
				        omtp11PlusLan10gTransparentTransmitIdleInsertionCount			DisplayString,
				        omtp11PlusLan10gTransparentTransmitConfInsertionCount			DisplayString,
				        omtp11PlusLan10gTransparentReceiveLcvCount				DisplayString,
				        omtp11PlusLan10gTransparentReceivePropagationErrorDeletionCount		DisplayString,
				        omtp11PlusLan10gTransparentReceiveIdleDeletionCount			DisplayString,
				        omtp11PlusLan10gTransparentReceiveConfDeletionCount			DisplayString,
				        omtp11PlusLan10gTransparentReceivePacketDeletionCount			DisplayString,
				        omtp11PlusGfpCoreHeaderErrorCount					DisplayString,
				        omtp11PlusGfpExtentionHeaderErrorCount					DisplayString,
				        omtp11PlusGfpFrameCountWithSingleBitError				DisplayString,
					omtp11PlusGfpTypeHeaderErrorCount					DisplayString,
					omtp11PlusGfpReceiveDropFrameCount					DisplayString,
					omtp11PlusGfpReceiveExtensionHeaderIdentifierFilterDropCount		DisplayString,
				        omtp11PlusFcTransmitWordCount						DisplayString,
				        omtp11PlusFcTransmitBadCrc						DisplayString,
				        omtp11PlusFcTransmitTotalPackets					DisplayString,
				        omtp11PlusFcTransmitLcvCount						DisplayString,
				        omtp11PlusFcReceiveWordCount						DisplayString,
				        omtp11PlusFcReceiveBadCrc						DisplayString,
				        omtp11PlusFcReceiveTotalPackets						DisplayString,
				        omtp11PlusFcReceiveLcvCount						DisplayString,
				        omtp11PlusFcTransmitFillWordInsertionCount				DisplayString,
				        omtp11PlusFcTransmitPrimitiveSequenceInsertionCount			DisplayString,
				        omtp11PlusFcTransmitFillWordDeletionCount				DisplayString,
				        omtp11PlusFcTransmitPrimitiveSequenceDeletionCount			DisplayString,
					omtp11PlusPerformanceTableRowStatus					RowStatus
			}
              
        omtp11PlusXfpInputPower OBJECT-TYPE
		SYNTAX  DisplayString
		MAX-ACCESS  read-only
		STATUS  current
		DESCRIPTION
			"Gives the current Input power(dbm) received at the port
			-----------------------------
			omtp11PlusInterfaceNumber:
			1 - CLIENT-1
			2 - LINE-1
			-----------------------------
			Values:
			eg: -9.0
			-----------------------------"
        ::= { omtp11PlusPerformanceEntry 1 }

        omtp11PlusXfpOutputPower OBJECT-TYPE
		SYNTAX  DisplayString
		MAX-ACCESS  read-only
		STATUS  current
		DESCRIPTION
			"Gives the current Output power(dbm) transmitted by the port
			-----------------------------
			omtp11PlusInterfaceNumber:
			1 - CLIENT-1
			2 - LINE-1
			-----------------------------
			Values:
			eg: -0.6
			-----------------------------"
        ::= { omtp11PlusPerformanceEntry 2 }


	omtp11PlusXfpBiasCurrent OBJECT-TYPE
		SYNTAX  DisplayString
		MAX-ACCESS  read-only
		STATUS  current
		DESCRIPTION
			"Gives the bias current(mA) thats transmitted at the port
			-----------------------------
			omtp11PlusInterfaceNumber:
			1 - CLIENT-1
			2 - LINE-1
			-----------------------------
			Values:
			eg: 55
			-----------------------------"
        ::= { omtp11PlusPerformanceEntry 3 }

	omtp11PlusXfpSupplyVoltage OBJECT-TYPE
		SYNTAX  DisplayString
		MAX-ACCESS  read-only
		STATUS  current
		DESCRIPTION
			"Gives the Supply Voltage of the port
			-----------------------------
			omtp11PlusInterfaceNumber:
			1 - CLIENT-1
			2 - LINE-1
			-----------------------------
			Values:
			eg: 3.3
			-----------------------------"
	::= { omtp11PlusPerformanceEntry 4 }

	omtp11PlusXfpTemperature OBJECT-TYPE
		SYNTAX  DisplayString
		MAX-ACCESS  read-only
		STATUS  current
		DESCRIPTION
			"Gives the temperature(degree celcius) of the transmitter at  the port
			-----------------------------
			omtp11PlusInterfaceNumber:
			1 - CLIENT-1
			2 - LINE-1
			-----------------------------
			Values:
			eg: 33.35
			-----------------------------"
        ::= { omtp11PlusPerformanceEntry 5 }

        omtp11PlusOtnFecUncorrectedWords OBJECT-TYPE
		SYNTAX  DisplayString
		MAX-ACCESS  read-only
		STATUS  current
		DESCRIPTION
			"For port configured with OTU2 traffic, 
			OTU Uncorrected Word Error Counter counts the number of
			FEC errored code words that could not be corrected.
			-----------------------------
			omtp11PlusInterfaceNumber:
			1 - CLIENT-1
			2 - LINE-1
			-----------------------------
			Values:
			eg: 1234
			-----------------------------"
        ::= { omtp11PlusPerformanceEntry 11 }

	omtp11PlusOtnFecCorrectedBits OBJECT-TYPE
		SYNTAX  DisplayString
		MAX-ACCESS  read-only
		STATUS  current
		DESCRIPTION
			"For port configured with OTU2 traffic, 
			OTU Corrected Bit Error Counter counts the number of
			FEC error bits that could be corrected(sum of ones
			corrected and zeros corrected bits).
			-----------------------------
			omtp11PlusInterfaceNumber:
			1 - CLIENT-1
			2 - LINE-1
			-----------------------------
			Values:
			eg: 1234
			-----------------------------"
        ::= { omtp11PlusPerformanceEntry 12 }

        omtp11PlusOtnFecZerosCorrectedBits OBJECT-TYPE
		SYNTAX  DisplayString
		MAX-ACCESS  read-only
		STATUS  current
		DESCRIPTION
			"For port configured with OTU2 traffic, 
			OTU Zero Corrected Bits Error Counter counts the number
			of FEC error bits that could be corrected from
			one to zero value(Expected 0 but received as 1).
			-----------------------------
			omtp11PlusInterfaceNumber:
			1 - CLIENT-1
			2 - LINE-1
			-----------------------------
			Values:
			eg: 1234
			-----------------------------"
	::= { omtp11PlusPerformanceEntry 13 }

        omtp11PlusOtnFecOnesCorrectedBits OBJECT-TYPE
		SYNTAX  DisplayString
		MAX-ACCESS  read-only
		STATUS  current
		DESCRIPTION
			"For port configured with OTU2 traffic, 
			OTU Ones Corrected Byte Error Counter counts the number
			of FEC error bytes that could be corrected from
			zero to one value(Expected 1 but received as 0).
			-----------------------------
			omtp11PlusInterfaceNumber:
			1 - CLIENT-1
			2 - LINE-1
			-----------------------------
			Values:
			eg: 1234
			-----------------------------"
		::= { omtp11PlusPerformanceEntry 14 }

        omtp11PlusOtuBitInterleavedParityErrors OBJECT-TYPE
		SYNTAX  DisplayString
		MAX-ACCESS  read-only
		STATUS  current
		DESCRIPTION
			"For port configured with OTU2 traffic, 
			OTU-BIP Counter counts the Parity errors evaluated by
			SM field of an OTU2 frame.
			-----------------------------
			omtp11PlusInterfaceNumber:
			1 - CLIENT-1
			2 - LINE-1
			-----------------------------
			Values:
			eg: 1234
			-----------------------------"
	::= { omtp11PlusPerformanceEntry 15 }

        omtp11PlusOtuIncomingAlignmentErrorSeconds OBJECT-TYPE
		SYNTAX  DisplayString
		MAX-ACCESS  read-only
		STATUS  current
		DESCRIPTION
			"For port configured with OTU2 traffic, 
			OTU Incoming Alignment Error Count increases,
			when OTU IAE Alarm is detected in that particular second
			of the incoming OTU signal
			-----------------------------
			omtp11PlusInterfaceNumber:
			1 - CLIENT-1
			2 - LINE-1
			-----------------------------
			Values:
			eg: 1234
			-----------------------------"
	::= { omtp11PlusPerformanceEntry 16 }

        omtp11PlusOtuBackwardErrorIndicationErrorCount OBJECT-TYPE
		SYNTAX  DisplayString
		MAX-ACCESS  read-only
		STATUS  current
		DESCRIPTION
			"For port configured with OTU2 traffic, 
			OTU-BEI Counter increases when SM-BEI Alarm is 
			detected in that particular second
			of the incoming OTU signal
			-----------------------------
			omtp11PlusInterfaceNumber:
			1 - CLIENT-1
			2 - LINE-1
			-----------------------------
			Values:
			eg: 1234
			-----------------------------"
	::= { omtp11PlusPerformanceEntry 17 }

        omtp11PlusOtuBackwardIncomingAlignmentErrorSeconds OBJECT-TYPE
		SYNTAX  DisplayString
		MAX-ACCESS  read-only
		STATUS  current
		DESCRIPTION
			"For port configured with OTU2 traffic, 
			OTU-BIAE Counter increases when SM-BIAE Alarm is 
			detected in that particular second
			of the incoming OTU signal
			-----------------------------
			omtp11PlusInterfaceNumber:
			1 - CLIENT-1
			2 - LINE-1
			-----------------------------
			Values:
			eg: 1234
			-----------------------------"
	::= { omtp11PlusPerformanceEntry 18 }

        omtp11PlusOtuErrorFreeSeconds OBJECT-TYPE
		SYNTAX  DisplayString
		MAX-ACCESS  read-only
		STATUS  current
		DESCRIPTION
			"For port configured with OTU2 traffic, 
			OTU Error Free Seconds increases when no BIP errors
			or defects are detected
			-----------------------------
			omtp11PlusInterfaceNumber:
			1 - CLIENT-1
			2 - LINE-1
			-----------------------------
			Values:
			eg: 1234
			-----------------------------"
	::= { omtp11PlusPerformanceEntry 19 }

        omtp11PlusOtuErrorSeconds OBJECT-TYPE
		SYNTAX  DisplayString
		MAX-ACCESS  read-only
		STATUS  current
		DESCRIPTION
			"For port configured with OTU2 traffic, 
			OTU Error Seconds increases when any defects like 
			OTU-AIS, SM-TIM etc are detected at the
			section monitoring level
			-----------------------------
			omtp11PlusInterfaceNumber:
			1 - CLIENT-1
			2 - LINE-1
			-----------------------------
			Values:
			eg: 1234
			-----------------------------"
	::= { omtp11PlusPerformanceEntry 20 }

        omtp11PlusOtuBackgroundBlockErrors OBJECT-TYPE
		SYNTAX  DisplayString
		MAX-ACCESS  read-only
		STATUS  current
		DESCRIPTION
			"For port configured with OTU2 traffic, 
			OTU Background Block Errors increases on defects 
			detected and when BIP errors are less than 15% errored
			blocks received 
			-----------------------------
			omtp11PlusInterfaceNumber:
			1 - CLIENT-1
			2 - LINE-1
			-----------------------------
			Values:
			eg: 1234
			-----------------------------"
	::= { omtp11PlusPerformanceEntry 21 }

        omtp11PlusOtuSevereErrorSeconds OBJECT-TYPE
		SYNTAX  DisplayString
		MAX-ACCESS  read-only
		STATUS  current
		DESCRIPTION
			"For port configured with OTU2 traffic, 
			OTU Severe Error Seconds increases on defects
			detected and when BIP errors are greater than or
			equal to 15% errored blocks received 
			-----------------------------
			omtp11PlusInterfaceNumber:
			1 - CLIENT-1
			2 - LINE-1
			-----------------------------
			Values:
			eg: 1234
			-----------------------------"
	::= { omtp11PlusPerformanceEntry 22 }

        omtp11PlusOtuUnavailableSeconds OBJECT-TYPE
		SYNTAX  DisplayString
		MAX-ACCESS  read-only
		STATUS  current
		DESCRIPTION
			"For port configured with OTU2 traffic, 
			OTU Unavailable Seconds increases,
			when 10 consecutive
			Severe OTU Error seconds are detected
			-----------------------------
			omtp11PlusInterfaceNumber:
			1 - CLIENT-1
			2 - LINE-1
			-----------------------------
			Values:
			eg: 1234
			-----------------------------"
	::= { omtp11PlusPerformanceEntry 23 }

        omtp11PlusOtuBackgroundBlockErrorRatio OBJECT-TYPE
		SYNTAX  DisplayString
		MAX-ACCESS  read-only
		STATUS  current
		DESCRIPTION
			"For port configured with OTU2 traffic, 
			Gives OTU Background Block Error Seconds Error Ratio.
			The ratio of BBE in available time to total seconds
			in available time during a fixed measurement interval.
			-----------------------------
			omtp11PlusInterfaceNumber:
			1 - CLIENT-1
			2 - LINE-1
			-----------------------------
			Values:
			eg: 1e-3
			-----------------------------"
	::= { omtp11PlusPerformanceEntry 25 }

        omtp11PlusOtuSevereErrorSecondsErrorRatio OBJECT-TYPE
		SYNTAX  DisplayString
		MAX-ACCESS  read-only
		STATUS  current
		DESCRIPTION
			"For port configured with OTU2 traffic, 
			Gives OTU Severe Error Seconds Error Ratio.
			The ratio of SES in available time to total seconds
			in available time during a fixed measurement interval.
			-----------------------------
			omtp11PlusInterfaceNumber:
			1 - CLIENT-1
			2 - LINE-1
			-----------------------------
			Values:
			eg: 1e-3
			-----------------------------"
	::= { omtp11PlusPerformanceEntry 26 }

        omtp11PlusOtuFarEndErrorFreeSeconds OBJECT-TYPE
		SYNTAX  DisplayString
		MAX-ACCESS  read-only
		STATUS  current
		DESCRIPTION
			"For port configured with OTU2 traffic, 
			OTU Far end Error Free Seconds, increases when no
			 backward errors or defects like BDI or BEI
			are detected in the incoming OTU signal.
			-----------------------------
			omtp11PlusInterfaceNumber:
			1 - CLIENT-1
			2 - LINE-1
			-----------------------------
			Values:
			eg: 1234
			-----------------------------"
	::= { omtp11PlusPerformanceEntry 27 }

        omtp11PlusOtuFarEndErrorSeconds OBJECT-TYPE
		SYNTAX  DisplayString
		MAX-ACCESS  read-only
		STATUS  current
		DESCRIPTION
			"For port configured with OTU2 traffic, 
			OTU Far End Error Seconds increases on
			detection of defects like BDI in incoming
			OTU signal.
			-----------------------------
			omtp11PlusInterfaceNumber:
			1 - CLIENT-1
			2 - LINE-1
			-----------------------------
			Values:
			eg: 1234
			-----------------------------"
	::= { omtp11PlusPerformanceEntry 28 }

        omtp11PlusOtuFarEndBackgroundBlockErrors OBJECT-TYPE
		SYNTAX  DisplayString
		MAX-ACCESS  read-only
		STATUS  current
		DESCRIPTION
			"For port configured with OTU2 traffic, 
			OTU Far End Background Block Errors increases when BEI
			errors are less than 15% Errored Blocks in incoming
			OTU signal.
			-----------------------------
			omtp11PlusInterfaceNumber:
			1 - CLIENT-1
			2 - LINE-1
			-----------------------------
			Values:
			eg: 1234
			-----------------------------"
	::= { omtp11PlusPerformanceEntry 29 }

        omtp11PlusOtuFarEndSevereErrorSeconds OBJECT-TYPE
		SYNTAX  DisplayString
		MAX-ACCESS  read-only
		STATUS  current
		DESCRIPTION
			"For port configured with OTU2 traffic, 
			OTU Far End Severe Error Seconds increases on defects
			like BDI are detected and when BEI errors are greater
			than or equal to 15% Errored Blocks in incoming OTU 
			signal.
			-----------------------------
			omtp11PlusInterfaceNumber:
			1 - CLIENT-1
			2 - LINE-1
			-----------------------------
			Values:
			eg: 1234
			-----------------------------"
	::= { omtp11PlusPerformanceEntry 30 }

        omtp11PlusOtuFarEndUnavailableSeconds OBJECT-TYPE
		SYNTAX  DisplayString
		MAX-ACCESS  read-only
		STATUS  current
		DESCRIPTION
			"For port configured with OTU2 traffic, 
			OTU Unavailable Seconds increases, after 9 consecutive
			OTU Far End Severe Error seconds are detected
			-----------------------------
			omtp11PlusInterfaceNumber:
			1 - CLIENT-1
			2 - LINE-1
			-----------------------------
			Values:
			eg: 1234
			-----------------------------"
	::= { omtp11PlusPerformanceEntry 31 }

        omtp11PlusOtuFarEndBackgroundBlockErrorRatio OBJECT-TYPE
		SYNTAX  DisplayString
		MAX-ACCESS  read-only
		STATUS  current
		DESCRIPTION
			"For port configured with OTU2 traffic, 
			Gives Otu Far End Background Block Error Ratio.
			The ratio of BBE in available time to total seconds
			in available time during a fixed measurement interval.
			-----------------------------
			omtp11PlusInterfaceNumber:
			1 - CLIENT-1
			2 - LINE-1
			-----------------------------
			Values:
			eg: 1e-3
			-----------------------------"
	::= { omtp11PlusPerformanceEntry 33 }

        omtp11PlusOtuFarEndSevereErrorSecondsErrorRatio OBJECT-TYPE
		SYNTAX  DisplayString
		MAX-ACCESS  read-only
		STATUS  current
		DESCRIPTION
			"For port configured with OTU2 traffic, 
			Gives Otu Far End Severe Error Seconds Error Ratio.
			The ratio of SES in available time to total seconds
			in available time during a fixed measurement interval.
			-----------------------------
			omtp11PlusInterfaceNumber:
			1 - CLIENT-1
			2 - LINE-1
			-----------------------------
			Values:
			eg: 1e-3
			-----------------------------"
	::= { omtp11PlusPerformanceEntry 34 }

	omtp11PlusOtuErrorRatio   OBJECT-TYPE
              SYNTAX  DisplayString
              MAX-ACCESS  read-only
              STATUS  current
              DESCRIPTION
			"For port configured with OTU2 traffic, 
			OTU Error Ratio for requested port. The ratio of 
			number of error bits to the number of bits received in
			a particular second
			-----------------------------
			omtp11PlusInterfaceNumber:
			1 - CLIENT-1
			2 - LINE-1
			-----------------------------	
			Value:
			eg: 4.0
			-----------------------------"
	::= { omtp11PlusPerformanceEntry 35 } 

	omtp11PlusOtuBitErrorRate  OBJECT-TYPE
              SYNTAX  DisplayString
              MAX-ACCESS  read-only
              STATUS  current
              DESCRIPTION
			"For port configured with OTU2 traffic, 
			Bit error rate is the Error ratio multiplied by the
			OTU2 standard signal data-rate( 10.709225316 Gbps )
			-----------------------------
			omtp11PlusInterfaceNumber:
			1 - CLIENT-1
			2 - LINE-1
			-----------------------------	
			Value:
			eg: 4.0
			-----------------------------"
	::= { omtp11PlusPerformanceEntry 36 }

	omtp11PlusOtuFramesReceived  OBJECT-TYPE
              SYNTAX  DisplayString
              MAX-ACCESS  read-only
              STATUS  current
              DESCRIPTION
			"For port configured with OTU2 traffic, gives the 
			gives the number of OTU frames transmitted.
			-----------------------------
			omtp11PlusInterfaceNumber:
			1 - CLIENT-1
			2 - LINE-1
			-----------------------------		
			Value:
			eg: 4.0
			-----------------------------"
	::= { omtp11PlusPerformanceEntry 37 }

        omtp11PlusOduBitInterleavedParityErrors OBJECT-TYPE
		SYNTAX  DisplayString
		MAX-ACCESS  read-only
		STATUS  current
		DESCRIPTION
			"For port configured with OTU2 traffic, 
			ODU-BIP Counter counts the Parity errors evaluated by
			PM field of an OTU2 frame
			-----------------------------
			omtp11PlusInterfaceNumber:
			1 - CLIENT-1
			2 - LINE-1
			-----------------------------
			Values:
			eg: 1234
			-----------------------------"
	::= { omtp11PlusPerformanceEntry 41 }

        omtp11PlusOduTcm1BitInterleavedParityErrors OBJECT-TYPE
		SYNTAX  DisplayString
		MAX-ACCESS  read-only
		STATUS  current
		DESCRIPTION
			"For port configured with OTU2 traffic, 
			TCM1-BIP Counter counts the Parity errors evaluated by
			TCM1 field in ODU2 frame
			-----------------------------
			omtp11PlusInterfaceNumber:
			1 - CLIENT-1
			2 - LINE-1
			-----------------------------
			Values:
			eg: 1234
			-----------------------------"
	::= { omtp11PlusPerformanceEntry 42 }

        omtp11PlusOduTcm2BitInterleavedParityErrors OBJECT-TYPE
		SYNTAX  DisplayString
		MAX-ACCESS  read-only
		STATUS  current
		DESCRIPTION
			"For port configured with OTU2 traffic, 
			TCM2-BIP Counter counts the Parity errors evaluated by
			TCM2 field in ODU2 frame
			-----------------------------
			omtp11PlusInterfaceNumber:
			1 - CLIENT-1
			2 - LINE-1
			-----------------------------
			Values:
			eg: 1234
			-----------------------------"
	::= { omtp11PlusPerformanceEntry 43 }

        omtp11PlusOduTcm3BitInterleavedParityErrors OBJECT-TYPE
		SYNTAX  DisplayString
		MAX-ACCESS  read-only
		STATUS  current
		DESCRIPTION
			"For port configured with OTU2 traffic, 
			TCM3-BIP Counter counts the Parity errors evaluated by
			TCM3 field in ODU2 frame
			-----------------------------
			omtp11PlusInterfaceNumber:
			1 - CLIENT-1
			2 - LINE-1
			-----------------------------
			Values:
			eg: 1234
			-----------------------------"
	::= { omtp11PlusPerformanceEntry 44 }

        omtp11PlusOduTcm4BitInterleavedParityErrors OBJECT-TYPE
		SYNTAX  DisplayString
		MAX-ACCESS  read-only
		STATUS  current
		DESCRIPTION
			"For port configured with OTU2 traffic, 
			TCM4-BIP Counter counts the Parity errors evaluated by
			TCM4 field in ODU2 frame
			-----------------------------
			omtp11PlusInterfaceNumber:
			1 - CLIENT-1
			2 - LINE-1
			-----------------------------
			Values:
			eg: 1234
			-----------------------------"
	::= { omtp11PlusPerformanceEntry 45 }

        omtp11PlusOduTcm5BitInterleavedParityErrors OBJECT-TYPE
		SYNTAX  DisplayString
		MAX-ACCESS  read-only
		STATUS  current
		DESCRIPTION
			"For port configured with OTU2 traffic, 
			TCM5-BIP Counter counts the Parity errors evaluated by
			TCM5 field in ODU2 frame
			-----------------------------
			omtp11PlusInterfaceNumber:
			1 - CLIENT-1
			2 - LINE-1
			-----------------------------
			Values:
			eg: 1234
			-----------------------------"
	::= { omtp11PlusPerformanceEntry 46 }

        omtp11PlusOduTcm6BitInterleavedParityErrors OBJECT-TYPE
		SYNTAX  DisplayString
		MAX-ACCESS  read-only
		STATUS  current
		DESCRIPTION
			"For port configured with OTU2 traffic, 
			TCM6-BIP Counter counts the Parity errors evaluated by
			TCM6 field in ODU2 frame
			-----------------------------
			omtp11PlusInterfaceNumber:
			1 - CLIENT-1
			2 - LINE-1
			-----------------------------
			Values:
			eg: 1234
			-----------------------------"
	::= { omtp11PlusPerformanceEntry 47 }

        omtp11PlusOduTcm1IncomingAlignmentErrorSeconds OBJECT-TYPE
		SYNTAX  DisplayString
		MAX-ACCESS  read-only
		STATUS  current
		DESCRIPTION
			"For port configured with OTU2 traffic,
			ODU Incoming Alignment Error Count increases,
			when ODU-TCM1-IAE is detected in that particular second
			of the incoming OTU signal
			-----------------------------
			omtp11PlusInterfaceNumber:
			1 - CLIENT-1
			2 - LINE-1
			-----------------------------
			Values:
			eg: 1234
			-----------------------------"
	::= { omtp11PlusPerformanceEntry 48 }

        omtp11PlusOduBackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code.
			-----------------------------
			omtp11PlusInterfaceNumber:
			1 - CLIENT-1
			2 - LINE-1
			-----------------------------
			Values:
			eg: 1234
			-----------------------------"
	::= { omtp11PlusPerformanceEntry 49 }

        omtp11PlusOduTcm1BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-1 level.
			-----------------------------
			omtp11PlusInterfaceNumber:
			1 - CLIENT-1
			2 - LINE-1
			-----------------------------
			Values:
			eg: 1234
			-----------------------------"
	::= { omtp11PlusPerformanceEntry 50 }

        omtp11PlusOduTcm2BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-2 level.
			-----------------------------
			omtp11PlusInterfaceNumber:
			1 - CLIENT-1
			2 - LINE-1
			-----------------------------
			Values:
			eg: 1234
			-----------------------------"
	::= { omtp11PlusPerformanceEntry 51 }

        omtp11PlusOduTcm3BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-3 level.
			-----------------------------
			omtp11PlusInterfaceNumber:
			1 - CLIENT-1
			2 - LINE-1
			-----------------------------
			Values:
			eg: 1234
			-----------------------------"
	::= { omtp11PlusPerformanceEntry 52 }

        omtp11PlusOduTcm4BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-4 level.
			-----------------------------
			omtp11PlusInterfaceNumber:
			1 - CLIENT-1
			2 - LINE-1
			-----------------------------
			Values:
			eg: 1234
			-----------------------------"
	::= { omtp11PlusPerformanceEntry 53 }

        omtp11PlusOduTcm5BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-5 level.
			-----------------------------
			omtp11PlusInterfaceNumber:
			1 - CLIENT-1
			2 - LINE-1
			-----------------------------
			Values:
			eg: 1234
			-----------------------------"
	::= { omtp11PlusPerformanceEntry 54 }

        omtp11PlusOduTcm6BackwardErrorIndicationErrorCount OBJECT-TYPE
		SYNTAX  DisplayString
		MAX-ACCESS  read-only
		STATUS  current
		DESCRIPTION
			"For port configured with OTU2 traffic,
			this signal is used to convey in the upstream direction 
			the count of interleaved bit blocks that have 
			been detected in error using the BIP-8 code at TCM-6 level.
			-----------------------------
			omtp11PlusInterfaceNumber:
			1 - CLIENT-1
			2 - LINE-1
			-----------------------------
			Values:
			eg: 1234
			-----------------------------"
	::= { omtp11PlusPerformanceEntry 55 }

        omtp11PlusOduTcm1BackwardIncomingAlignmentErrorSeconds OBJECT-TYPE
		SYNTAX  DisplayString
		MAX-ACCESS  read-only
		STATUS  current
		DESCRIPTION
			"For port configured with OTU2 traffic,
			ODU Backward Incoming Alignment Error Count increases,
			when ODU-TCM1-BIAE is detected in that particular second
			of the incoming OTU signal
			-----------------------------
			omtp11PlusInterfaceNumber:
			1 - CLIENT-1
			2 - LINE-1
			-----------------------------
			Values:
			eg: 1234
			-----------------------------"
	::= { omtp11PlusPerformanceEntry 56 }

        omtp11PlusOduDelayMeasurement OBJECT-TYPE
		SYNTAX  DisplayString
		MAX-ACCESS  read-only
		STATUS  current
		DESCRIPTION
			"For port configured with OTU2 traffic, 
			Gives Delay measurement of OTU frame
			-----------------------------
			omtp11PlusInterfaceNumber:
			1 - CLIENT-1
			2 - LINE-1
			-----------------------------
			Values:
			eg: Reserved
			-----------------------------"
	::= { omtp11PlusPerformanceEntry 57 }

        omtp11PlusOduErrorFreeSeconds OBJECT-TYPE
		SYNTAX  DisplayString
		MAX-ACCESS  read-only
		STATUS  current
		DESCRIPTION
			"For port configured with OTU2 traffic, 
			ODU Error Free Seconds increases,
			when no BIP errors or defects are detected at the
			path monitoring level
			-----------------------------
			omtp11PlusInterfaceNumber:
			1 - CLIENT-1
			2 - LINE-1
			-----------------------------
			Values:
			eg: 1234
			-----------------------------"
	::= { omtp11PlusPerformanceEntry 58 }

        omtp11PlusOduErrorSeconds OBJECT-TYPE
		SYNTAX  DisplayString
		MAX-ACCESS  read-only
		STATUS  current
		DESCRIPTION
			"For port configured with OTU2 traffic, 
			ODU Error Seconds increases on defects detected at the
			path monitoring level
			-----------------------------
			omtp11PlusInterfaceNumber:
			1 - CLIENT-1
			2 - LINE-1
			-----------------------------
			Values:
			eg: 1234
			-----------------------------"
	::= { omtp11PlusPerformanceEntry 59 }

        omtp11PlusOduBackgroundBlockErrors OBJECT-TYPE
		SYNTAX  DisplayString
		MAX-ACCESS  read-only
		STATUS  current
		DESCRIPTION
			"For port configured with OTU2 traffic, 
			ODU Background Block Errors increases on defects 
			detected and when BIP errors are less than 15% 
			Errored Blocks in incoming OTU signal.
			-----------------------------
			omtp11PlusInterfaceNumber:
			1 - CLIENT-1
			2 - LINE-1
			-----------------------------
			Values:
			eg: 1234
			-----------------------------"
	::= { omtp11PlusPerformanceEntry 60 }

        omtp11PlusOduSevereErrorSeconds OBJECT-TYPE
		SYNTAX  DisplayString
		MAX-ACCESS  read-only
		STATUS  current
		DESCRIPTION
			"For port configured with OTU2 traffic, 
			ODU Severe Error Seconds increases on defects detected
			and when BIP errors are more than 15% Errored Blocks
			in incoming OTU signal.
			-----------------------------
			omtp11PlusInterfaceNumber:
			1 - CLIENT-1
			2 - LINE-1
			-----------------------------
			Values:
			eg: 1234
			-----------------------------"
	::= { omtp11PlusPerformanceEntry 61 }

        omtp11PlusOduUnavailableSeconds OBJECT-TYPE
		SYNTAX  DisplayString
		MAX-ACCESS  read-only
		STATUS  current
		DESCRIPTION
			"For port configured with OTU2 traffic, 
			ODU Unavailable Seconds increases, when 10 consecutive
			Severe
			ODU Error seconds are detected
			-----------------------------
			omtp11PlusInterfaceNumber:
			1 - CLIENT-1
			2 - LINE-1
			-----------------------------
			Values:
			eg: 1234
			-----------------------------"
	::= { omtp11PlusPerformanceEntry 62 }

        omtp11PlusOduBackgroundBlockErrorRatio OBJECT-TYPE
		SYNTAX  DisplayString
		MAX-ACCESS  read-only
		STATUS  current
		DESCRIPTION
			"For port configured with OTU2 traffic, 
			Gives ODU Background Block Error Ratio
			The ratio of BBE in available time to total seconds
			in available time during a fixed measurement interval.
			-----------------------------
			omtp11PlusInterfaceNumber:
			1 - CLIENT-1
			2 - LINE-1
			-----------------------------
			Values:
			eg: 1e-3
			-----------------------------"
	::= { omtp11PlusPerformanceEntry 64 }

        omtp11PlusOduSevereErrorSecondsErrorRatio OBJECT-TYPE
		SYNTAX  DisplayString
		MAX-ACCESS  read-only
		STATUS  current
		DESCRIPTION
			"For port configured with OTU2 traffic, 
			Gives ODU Severe Error Seconds Error Ratio
			The ratio of SES in available time to total seconds
			in available time during a fixed measurement interval.
			-----------------------------
			omtp11PlusInterfaceNumber:
			1 - CLIENT-1
			2 - LINE-1
			-----------------------------
			Values:
			eg: 1e-3
			-----------------------------"
	::= { omtp11PlusPerformanceEntry 65 }

        omtp11PlusOduFarEndErrorFreeSeconds OBJECT-TYPE
		SYNTAX  DisplayString
		MAX-ACCESS  read-only
		STATUS  current
		DESCRIPTION
			"For port configured with OTU2 traffic, 
			ODU Far end Error Free Seconds, increases when no
			errors or defects are detected
			-----------------------------
			omtp11PlusInterfaceNumber:
			1 - CLIENT-1
			2 - LINE-1
			-----------------------------
			Values:
			eg: 1234
			-----------------------------"
	::= { omtp11PlusPerformanceEntry 66 }

        omtp11PlusOduFarEndErrorSeconds OBJECT-TYPE
		SYNTAX  DisplayString
		MAX-ACCESS  read-only
		STATUS  current
		DESCRIPTION
			"For port configured with OTU2 traffic, 
			ODU Far End Error Seconds increases on detection of
			defects like BDI and BEI at path monitoring level
			-----------------------------
			omtp11PlusInterfaceNumber:
			1 - CLIENT-1
			2 - LINE-1
			-----------------------------
			Values:
			eg: 1234
			-----------------------------"
	::= { omtp11PlusPerformanceEntry 67 }

        omtp11PlusOduFarEndBackgroundBlockErrors OBJECT-TYPE
		SYNTAX  DisplayString
		MAX-ACCESS  read-only
		STATUS  current
		DESCRIPTION
			"For port configured with OTU2 traffic, 
			ODU Far End Background Block Errors increases when
			BEI errors are less than 15% Errored Blocks in
			incoming OTU signal.
			-----------------------------
			omtp11PlusInterfaceNumber:
			1 - CLIENT-1
			2 - LINE-1
			-----------------------------
			Values:
			eg: 1234
			-----------------------------"
	::= { omtp11PlusPerformanceEntry 68 }

        omtp11PlusOduFarEndSevereErrorSeconds OBJECT-TYPE
		SYNTAX  DisplayString
		MAX-ACCESS  read-only
		STATUS  current
		DESCRIPTION
			"For port configured with OTU2 traffic, 
			ODU Far End Severe Error Seconds increases on defects
			like BDI are detected and when BEI errors are more than
			15% Errored Blocks in incoming OTU signal.
			-----------------------------
			omtp11PlusInterfaceNumber:
			1 - CLIENT-1
			2 - LINE-1
			-----------------------------
			Values:
			eg: 1234
			-----------------------------"
	::= { omtp11PlusPerformanceEntry 69 }

        omtp11PlusOduFarEndUnavailableSeconds OBJECT-TYPE
		SYNTAX  DisplayString
		MAX-ACCESS  read-only
		STATUS  current
		DESCRIPTION
			"For port configured with OTU2 traffic, 
			ODU Far End Unavailable Seconds increases, when 10
		        consecutive OTU Far End Error seconds are detected
		       -----------------------------
			omtp11PlusInterfaceNumber:
			1 - CLIENT-1
			2 - LINE-1
			-----------------------------
			Values:
			eg: 1234
			-----------------------------"
	::= { omtp11PlusPerformanceEntry 70 }

        omtp11PlusOduFarEndBackgroundBlockErrorRatio OBJECT-TYPE
		SYNTAX  DisplayString
		MAX-ACCESS  read-only
		STATUS  current
		DESCRIPTION
			"For port configured with OTU2 traffic, 
			Gives ODU Far End Background Block Error Ratio
			The ratio of BBE in available time to total seconds
			in available time during a fixed measurement interval.
			-----------------------------
			omtp11PlusInterfaceNumber:
			1 - CLIENT-1
			2 - LINE-1
			-----------------------------
			Values:
			eg: 1e-3
			-----------------------------"
	::= { omtp11PlusPerformanceEntry 72 }

        omtp11PlusOduFarEndSevereErrorSecondsErrorRatio OBJECT-TYPE
		SYNTAX  DisplayString
		MAX-ACCESS  read-only
		STATUS  current
		DESCRIPTION
			"For port configured with OTU2 traffic, 
			Gives ODU Far End Severe Error Seconds Error Ratio
			The ratio of SES in available time to total seconds
			in available time during a fixed measurement interval.
			-----------------------------
			omtp11PlusInterfaceNumber:
			1 - CLIENT-1
			2 - LINE-1
			-----------------------------
			Values:
			eg: 1e-3
			-----------------------------"
	::= { omtp11PlusPerformanceEntry 73 }

        omtp11PlusSdhRsB1BitInterleavedParityErrors OBJECT-TYPE
		SYNTAX  DisplayString
		MAX-ACCESS  read-only
		STATUS  current
		DESCRIPTION
			"For port configured with SDH traffic, 
			SDH B1 BIP counter counts the Parity errors evaluated
			from byte B1 of the STM frame
			-----------------------------
			omtp11PlusInterfaceNumber:
			1 - CLIENT-1
			-----------------------------
			Values:
			eg: 1234
			-----------------------------"
	::= { omtp11PlusPerformanceEntry 81 }

        omtp11PlusSdhMsB2BitInterleavedParityErrors OBJECT-TYPE
		SYNTAX  DisplayString
		MAX-ACCESS  read-only
		STATUS  current
		DESCRIPTION
			"For port configured with SDH traffic, 
			SDH B2 BIP counter counts the Parity errors evaluated 
			from byte B2 of the STM frame
			-----------------------------
			omtp11PlusInterfaceNumber:
			1 - CLIENT-1
			-----------------------------
			Values:
			eg: 1234
			-----------------------------"
	::= { omtp11PlusPerformanceEntry 82 }

        omtp11PlusSdhMsB3BitInterleavedParityErrors OBJECT-TYPE
		SYNTAX  DisplayString
		MAX-ACCESS  read-only
		STATUS  current
		DESCRIPTION
			"For port configured with SDH traffic, 
			SDH B3 BIP counter counts the Parity errors evaluated 
			from byte B3 of the STM frame
			-----------------------------
			omtp11PlusInterfaceNumber:
			1 - CLIENT-1
			-----------------------------
			Values:
			eg: 1234
			-----------------------------"
	::= { omtp11PlusPerformanceEntry 83 }

        omtp11PlusSdhMsRemoteErrorIndicationErrorCount OBJECT-TYPE
		SYNTAX  DisplayString
		MAX-ACCESS  read-only
		STATUS  current
		DESCRIPTION
			"For port configured with SDH traffic, 
			SDH MS-REI error count increases when
			MS-REI is detected for that particular second
			in incoming SDH signal.
			-----------------------------
			omtp11PlusInterfaceNumber:
			1 - CLIENT-1
			-----------------------------
			Values:
			eg: 1234
			-----------------------------"
	::= { omtp11PlusPerformanceEntry 84 }

        omtp11PlusSdhMsRemoteDefectIndicationErrorCount OBJECT-TYPE
		SYNTAX  DisplayString
		MAX-ACCESS  read-only
		STATUS  current
		DESCRIPTION
			"For port configured with SDH traffic, 
			SDH MS-RDI error count increases when
			MS-RDI is detected for that particular second
			in incoming SDH signal.
			-----------------------------
			omtp11PlusInterfaceNumber:
			1 - CLIENT-1
			-----------------------------
			Values:
			eg: 1234
			-----------------------------"
	::= { omtp11PlusPerformanceEntry 85 }

        omtp11PlusSdhErrorFreeSeconds OBJECT-TYPE
		SYNTAX  DisplayString
		MAX-ACCESS  read-only
		STATUS  current
		DESCRIPTION
			"For port configured with SDH traffic, 
			SDH Error Free Seconds increases when no BIP
			errors or no defects are detected in incoming
			SDH signal.
			-----------------------------
			omtp11PlusInterfaceNumber:
			1 - CLIENT-1
			-----------------------------
			Values:
			eg: 1234
			-----------------------------"
	::= { omtp11PlusPerformanceEntry 86 }

        omtp11PlusSdhErrorSeconds OBJECT-TYPE
		SYNTAX  DisplayString
		MAX-ACCESS  read-only
		STATUS  current
		DESCRIPTION
			"For port configured with SDH traffic, 
			SDH Error Seconds increases on detection of BIP errors
			and defects like LOS, LOF, AIS etc in incoming SDH
			signal.
			-----------------------------
			omtp11PlusInterfaceNumber:
			1 - CLIENT-1
			-----------------------------
			Values:
			eg: 1234
			-----------------------------"
	::= { omtp11PlusPerformanceEntry 87 }

        omtp11PlusSdhBackgroundBlockErrors OBJECT-TYPE
		SYNTAX  DisplayString
		MAX-ACCESS  read-only
		STATUS  current
		DESCRIPTION
			"For port configured with SDH traffic, 
			SDH Background Block Errors increases on defects 
			detected and when BIP errors are less than 30%
			errored blocks in the incoming SDH signal.
			-----------------------------
			omtp11PlusInterfaceNumber:
			1 - CLIENT-1
			-----------------------------
			Values:
			eg: 1234
			-----------------------------"
	::= { omtp11PlusPerformanceEntry 88 }

        omtp11PlusSdhSevereErrorSeconds OBJECT-TYPE
		SYNTAX  DisplayString
		MAX-ACCESS  read-only
		STATUS  current
		DESCRIPTION
			"For port configured with SDH traffic, 
			SDH Severe Error Secodns increases on defects 
			detected and when BIP errors are greater than or equal
			to 30% errored blocks in the incoming SDH signal.
			-----------------------------
			omtp11PlusInterfaceNumber:
			1 - CLIENT-1
			-----------------------------
			Values:
			eg: 1234
			-----------------------------"
	::= { omtp11PlusPerformanceEntry 89 }

        omtp11PlusSdhUnavailableSeconds OBJECT-TYPE
		SYNTAX  DisplayString
		MAX-ACCESS  read-only
		STATUS  current
		DESCRIPTION
			"For port configured with SDH traffic, 
			SDH Unavailable Seconds increases, when 10 consecutive
			Severe Error seconds are detected
			-----------------------------
			omtp11PlusInterfaceNumber:
			1 - CLIENT-1
			-----------------------------
			Values:
			eg: 1234
			-----------------------------"
	::= { omtp11PlusPerformanceEntry 90 }

        omtp11PlusSdhErrorSecondsErrorRatio OBJECT-TYPE
		SYNTAX  DisplayString
		MAX-ACCESS  read-only
		STATUS  current
		DESCRIPTION
			"For port configured with SDH traffic, 
			Gives SDH Error Seconds Error Ratio.
			The ratio of ES in available time to total seconds
			in available time during a fixed measurement interval.
			-----------------------------
			omtp11PlusInterfaceNumber:
			1 - CLIENT-1
			-----------------------------
			Values:
			eg: 1234
			-----------------------------"
	::= { omtp11PlusPerformanceEntry 91 }

        omtp11PlusSdhBackgroundBlockErrorRatio OBJECT-TYPE
		SYNTAX  DisplayString
		MAX-ACCESS  read-only
		STATUS  current
		DESCRIPTION
			"For port configured with SDH traffic, 
			Gives SDH Background Block Error Ratio.
			The ratio of BBE in available time to total seconds
			in available time during a fixed measurement interval.
			-----------------------------
			omtp11PlusInterfaceNumber:
			1 - CLIENT-1
			-----------------------------
			Values:
			eg: 1234
			-----------------------------"
	::= { omtp11PlusPerformanceEntry 92 }

        omtp11PlusSdhSevereErrorSecondsErrorRatio OBJECT-TYPE
		SYNTAX  DisplayString
		MAX-ACCESS  read-only
		STATUS  current
		DESCRIPTION
			"For port configured with SDH traffic, 
			Gives SDH Severe Error Seconds Error Ratio.
			The ratio of SES in available time to total seconds
			in available time during a fixed measurement interval.
			-----------------------------
			omtp11PlusInterfaceNumber:
			1 - CLIENT-1
			-----------------------------
			Values:
			eg: 1234
			-----------------------------"
	::= { omtp11PlusPerformanceEntry 93 }

        omtp11PlusWan10gRsB1BitInterleavedParityErrors OBJECT-TYPE
		SYNTAX  DisplayString
		MAX-ACCESS  read-only
		STATUS  current
		DESCRIPTION
			"For port configured with 10G WAN traffic, 
			Wan10g B1 BIP counter counts the Parity errors evaluated
			from byte B1 of the STM frame
			-----------------------------
			omtp11PlusInterfaceNumber:
			1 - CLIENT-1
			-----------------------------
			Values:
			eg: 1234
			-----------------------------"
	::= { omtp11PlusPerformanceEntry 101 }

        omtp11PlusWan10gMsB2BitInterleavedParityErrors OBJECT-TYPE
		SYNTAX  DisplayString
		MAX-ACCESS  read-only
		STATUS  current
		DESCRIPTION
			"For port configured with 10G WAN traffic, 
			Wan10g B2 BIP counter counts the Parity errors evaluated 
			from byte B2 of the STM frame
			-----------------------------
			omtp11PlusInterfaceNumber:
			1 - CLIENT-1
			-----------------------------
			Values:
			eg: 1234
			-----------------------------"
	::= { omtp11PlusPerformanceEntry 102 }

        omtp11PlusWan10gMsB3BitInterleavedParityErrors OBJECT-TYPE
		SYNTAX  DisplayString
		MAX-ACCESS  read-only
		STATUS  current
		DESCRIPTION
			"For port configured with 10G WAN traffic, 
			Wan10g B3 BIP counter counts the Parity errors evaluated 
			from byte B3 of the STM frame
			-----------------------------
			omtp11PlusInterfaceNumber:
			1 - CLIENT-1
			-----------------------------
			Values:
			eg: 1234
			-----------------------------"
	::= { omtp11PlusPerformanceEntry 103 }

        omtp11PlusWan10gMsRemoteErrorIndicationErrorCount OBJECT-TYPE
		SYNTAX  DisplayString
		MAX-ACCESS  read-only
		STATUS  current
		DESCRIPTION
			"For port configured with 10G WAN traffic, 
			Wan10g MS-REI error count increases when
			MS-REI is detected for that particular second
			in incoming Wan10g signal.
			-----------------------------
			omtp11PlusInterfaceNumber:
			1 - CLIENT-1
			-----------------------------
			Values:
			eg: 1234
			-----------------------------"
	::= { omtp11PlusPerformanceEntry 104 }

        omtp11PlusWan10gMsRemoteDefectIndicationErrorCount OBJECT-TYPE
		SYNTAX  DisplayString
		MAX-ACCESS  read-only
		STATUS  current
		DESCRIPTION
			"For port configured with 10G WAN traffic, 
			Wan10g MS-RDI error count increases when
			MS-RDI is detected for that particular second
			in incoming Wan10g signal.
			-----------------------------
			omtp11PlusInterfaceNumber:
			1 - CLIENT-1
			-----------------------------
			Values:
			eg: 1234
			-----------------------------"
	::= { omtp11PlusPerformanceEntry 105 }

        omtp11PlusWan10gErrorFreeSeconds OBJECT-TYPE
		SYNTAX  DisplayString
		MAX-ACCESS  read-only
		STATUS  current
		DESCRIPTION
			"For port configured with 10G WAN traffic, 
			Wan10g Error Free Seconds increases when no BIP
			errors or no defects are detected in incoming
			Wan10g signal.
			-----------------------------
			omtp11PlusInterfaceNumber:
			1 - CLIENT-1
			-----------------------------
			Values:
			eg: 1234
			-----------------------------"
	::= { omtp11PlusPerformanceEntry 106 }

        omtp11PlusWan10gErrorSeconds OBJECT-TYPE
		SYNTAX  DisplayString
		MAX-ACCESS  read-only
		STATUS  current
		DESCRIPTION
			"For port configured with 10G WAN traffic, 
			Wan10g Error Seconds increases on detection of BIP errors
			and defects like LOS, LOF, AIS etc in incoming Wan10g
			signal.
			-----------------------------
			omtp11PlusInterfaceNumber:
			1 - CLIENT-1
			-----------------------------
			Values:
			eg: 1234
			-----------------------------"
	::= { omtp11PlusPerformanceEntry 107 }

        omtp11PlusWan10gBackgroundBlockErrors OBJECT-TYPE
		SYNTAX  DisplayString
		MAX-ACCESS  read-only
		STATUS  current
		DESCRIPTION
			"Wan10g Background Block Errors increases on defects 
			detected and when BIP errors are less than 30%
			errored blocks in the incoming Wan10g signal.
			-----------------------------
			omtp11PlusInterfaceNumber:
			1 - CLIENT-1
			-----------------------------
			Values:
			eg: 1234
			-----------------------------"
	::= { omtp11PlusPerformanceEntry 108 }

        omtp11PlusWan10gSevereErrorSeconds OBJECT-TYPE
		SYNTAX  DisplayString
		MAX-ACCESS  read-only
		STATUS  current
		DESCRIPTION
			"For port configured with 10G WAN traffic, 
			Wan10g Severe Error Secodns increases on defects 
			detected and when BIP errors are greater than or equal
			to 30% errored blocks in the incoming Wan10g signal.
			-----------------------------
			omtp11PlusInterfaceNumber:
			1 - CLIENT-1
			-----------------------------
			Values:
			eg: 1234
			-----------------------------"
	::= { omtp11PlusPerformanceEntry 109 }

        omtp11PlusWan10gUnavailableSeconds OBJECT-TYPE
		SYNTAX  DisplayString
		MAX-ACCESS  read-only
		STATUS  current
		DESCRIPTION
			"For port configured with 10G WAN traffic, 
			Wan10g Unavailable Seconds increases, when 10 consecutive
			Severe Error seconds are detected
			-----------------------------
			omtp11PlusInterfaceNumber:
			1 - CLIENT-1
			-----------------------------
			Values:
			eg: 1234
			-----------------------------"
	::= { omtp11PlusPerformanceEntry 110 }

        omtp11PlusWan10gErrorSecondsErrorRatio OBJECT-TYPE
		SYNTAX  DisplayString
		MAX-ACCESS  read-only
		STATUS  current
		DESCRIPTION
			"For port configured with 10G WAN traffic, 
			Gives Wan10g Error Seconds Error Ratio.
			The ratio of ES in available time to total seconds
			in available time during a fixed measurement interval.
			-----------------------------
			omtp11PlusInterfaceNumber:
			1 - CLIENT-1
			-----------------------------
			Values:
			eg: 1e-3
			-----------------------------"
	::= { omtp11PlusPerformanceEntry 111 }

        omtp11PlusWan10gBackgroundBlockErrorRatio OBJECT-TYPE
		SYNTAX  DisplayString
		MAX-ACCESS  read-only
		STATUS  current
		DESCRIPTION
			"For port configured with 10G WAN traffic, 
			Gives Wan10g Background Block Error Ratio.
			The ratio of BBE in available time to total seconds
			in available time during a fixed measurement interval.
			-----------------------------
			omtp11PlusInterfaceNumber:
			1 - CLIENT-1
			-----------------------------
			Values:
			eg: 1e-3
			-----------------------------"
	::= { omtp11PlusPerformanceEntry 112 }

        omtp11PlusWan10gSevereErrorSecondsErrorRatio OBJECT-TYPE
		SYNTAX  DisplayString
		MAX-ACCESS  read-only
		STATUS  current
		DESCRIPTION
			"For port configured with 10G WAN traffic, 
			Gives Wan10g Severe Error Seconds Error Ratio.
			The ratio of SES in available time to total seconds
			in available time during a fixed measurement interval.
			-----------------------------
			omtp11PlusInterfaceNumber:
			1 - CLIENT-1
			-----------------------------
			Values:
			eg: 1e-3
			-----------------------------"
	::= { omtp11PlusPerformanceEntry 113 }

        omtp11PlusLan10gMacTerminatedFramesTransmitted OBJECT-TYPE
		SYNTAX  DisplayString
		MAX-ACCESS  read-only
		STATUS  current
		DESCRIPTION
			"For port configured with 10G LAN traffic, 
			LAN 10G Frames transmitted counter counts the number of 
			Ethernet frame transmitted from the Client port 
			which is configured with 10G LAN traffic.
			-----------------------------
			omtp11PlusInterfaceNumber:
			1 - CLIENT-1
			-----------------------------
			Values:
			eg: 1234
			-----------------------------"
	::= { omtp11PlusPerformanceEntry 121 }

        omtp11PlusLan10gMacTerminatedFramesReceived OBJECT-TYPE
		SYNTAX  DisplayString
		MAX-ACCESS  read-only
		STATUS  current
		DESCRIPTION
			"For port configured with 10G LAN traffic, 
			LAN 10G Frames Received counter counts the number of 
			Ethernet frame received at the Client port 
			which is configured with 10G LAN traffic 
			-----------------------------
			omtp11PlusInterfaceNumber:
			1 - CLIENT-1
			-----------------------------
			Values:
			eg: 1234
			-----------------------------"
	::= { omtp11PlusPerformanceEntry 122 }

        omtp11PlusLan10gMacTerminatedPauseFramesTransmitted OBJECT-TYPE
		SYNTAX  DisplayString
		MAX-ACCESS  read-only
		STATUS  current
		DESCRIPTION
			"For port configured with 10G LAN traffic, 
			LAN 10G Pause Frames transmitted counter counts the
			number of Pause frame transmitted from port 
			which is configured with 10G LAN traffic 
			-----------------------------
			omtp11PlusInterfaceNumber:
			1 - CLIENT-1
			-----------------------------
			Values:
			eg: 1234
			-----------------------------"
	::= { omtp11PlusPerformanceEntry 123 }

        omtp11PlusLan10gMacTerminatedPauseFramesReceived OBJECT-TYPE
		SYNTAX  DisplayString
		MAX-ACCESS  read-only
		STATUS  current
		DESCRIPTION
			"For port configured with 10G LAN traffic, 
			LAN 10G Pause Frames received counter counts the
			number of Pause frame received at port 
			which is configured with 10G LAN traffic 
			-----------------------------
			omtp11PlusInterfaceNumber:
			1 - CLIENT-1
			-----------------------------
			Values:
			eg: 1234
			-----------------------------"
	::= { omtp11PlusPerformanceEntry 124 }

        omtp11PlusLan10gMacTerminatedUnicastFramesTransmitted OBJECT-TYPE
		SYNTAX  DisplayString
		MAX-ACCESS  read-only
		STATUS  current
		DESCRIPTION
			"For port configured with 10G LAN traffic, 
			Counts the number of unicast frames transmitted from port 
			which is configured with 10G LAN traffic 
			-----------------------------
			omtp11PlusInterfaceNumber:
			1 - CLIENT-1
			-----------------------------
			Values:
			eg: 1234
			-----------------------------"
	::= { omtp11PlusPerformanceEntry 125 }

        omtp11PlusLan10gMacTerminatedUnicastFramesReceived OBJECT-TYPE
		SYNTAX  DisplayString
		MAX-ACCESS  read-only
		STATUS  current
		DESCRIPTION
			"For port configured with 10G LAN traffic, 
			Counts the number of unicast frames received at port 
			which is configured with 10G LAN traffic
			-----------------------------
			omtp11PlusInterfaceNumber:
			1 - CLIENT-1
			-----------------------------
			Values:
			eg: 1234
			-----------------------------"
	::= { omtp11PlusPerformanceEntry 126 }

        omtp11PlusLan10gMacTerminatedMulticastFramesTransmitted OBJECT-TYPE
		SYNTAX  DisplayString
		MAX-ACCESS  read-only
		STATUS  current
		DESCRIPTION
			"For port configured with 10G LAN traffic, 
			Counts the number of multicast frames transmitted from port 
			which is configured with 10G LAN traffic
			-----------------------------
			omtp11PlusInterfaceNumber:
			1 - CLIENT-1
			-----------------------------
			Values:
			eg: 1234
			-----------------------------"
	::= { omtp11PlusPerformanceEntry 127 }

        omtp11PlusLan10gMacTerminatedMulticastFramesReceived OBJECT-TYPE
		SYNTAX  DisplayString
		MAX-ACCESS  read-only
		STATUS  current
		DESCRIPTION
			"For port configured with 10G LAN traffic, 
			Counts the number of multicast frames received at port 
			which is configured with 10G LAN traffic
			-----------------------------
			omtp11PlusInterfaceNumber:
			1 - CLIENT-1
			-----------------------------
			Values:
			eg: 1234
			-----------------------------"
        ::= { omtp11PlusPerformanceEntry 128 }

        omtp11PlusLan10gMacTerminatedBroadcastFramesTransmitted OBJECT-TYPE
		SYNTAX  DisplayString
		MAX-ACCESS  read-only
		STATUS  current
		DESCRIPTION
			"For port configured with 10G LAN traffic, 
			Counts the number of broadcast frames transmitted from
			port which is configured with 10G LAN traffic
			-----------------------------
			omtp11PlusInterfaceNumber:
			1 - CLIENT-1
			-----------------------------
			Values:
			eg: 1234
			-----------------------------"
	::= { omtp11PlusPerformanceEntry 129 }

        omtp11PlusLan10gMacTerminatedBroadcastFramesReceived OBJECT-TYPE
		SYNTAX  DisplayString
		MAX-ACCESS  read-only
		STATUS  current
		DESCRIPTION
			"For port configured with 10G LAN traffic, 
			Counts the number of broadcast frames received at port 
			which is configured with 10G LAN traffic
			-----------------------------
			omtp11PlusInterfaceNumber:
			1 - CLIENT-1
			-----------------------------
			Values:
			eg: 1234
			-----------------------------"
	::= { omtp11PlusPerformanceEntry 130 }

        omtp11PlusLan10gMacTerminatedUnderSizeFramesTransmitted OBJECT-TYPE
		SYNTAX  DisplayString
		MAX-ACCESS  read-only
		STATUS  current
		DESCRIPTION
			"For port configured with 10G LAN traffic, 
			LAN 10G Undersize Frames Transmitted counter counts the
			transmitted Ethernet framesize which is less than
			64 bytes from port which is configured with 10G LAN traffic
			-----------------------------
			omtp11PlusInterfaceNumber:
			1 - CLIENT-1
			-----------------------------
			Values:
			eg: 1234
			-----------------------------"
	::= { omtp11PlusPerformanceEntry 131 }

        omtp11PlusLan10gMacTerminatedUnderSizeFramesReceived OBJECT-TYPE
		SYNTAX  DisplayString
		MAX-ACCESS  read-only
		STATUS  current
		DESCRIPTION
			"For port configured with 10G LAN traffic, 
			LAN 10G Undersize Frames Received counter counts the
			Received Ethernet framesize which is less than
			64 bytes at port which is configured with 10G LAN traffic
			-----------------------------
			omtp11PlusInterfaceNumber:
			1 - CLIENT-1
			-----------------------------
			Values:
			eg: 1234
			-----------------------------"
	::= { omtp11PlusPerformanceEntry 132 }

        omtp11PlusLan10gMacTerminatedOverSizeFramesTransmitted OBJECT-TYPE
		SYNTAX  DisplayString
		MAX-ACCESS  read-only
		STATUS  current
		DESCRIPTION
			"For port configured with 10G LAN traffic, 
			LAN 10G Oversize Frames Transmitted counter counts the
			Transmitted  Ethernet framesize which is greater than 
			1518 bytes from port which is configured with 10G LAN
			traffic
			-----------------------------
			omtp11PlusInterfaceNumber:
			1 - CLIENT-1
			-----------------------------
			Values:
			eg: 1234
			-----------------------------"
        ::= { omtp11PlusPerformanceEntry 133 }

        omtp11PlusLan10gMacTerminatedOverSizeFramesReceived OBJECT-TYPE
		SYNTAX  DisplayString
		MAX-ACCESS  read-only
		STATUS  current
		DESCRIPTION
			"For port configured with 10G LAN traffic, 
			LAN 10G Oversize Frames Received counter counts the
			Received Ethernet framesize which is greater than 
			1518 bytes at port which is configured with 10G LAN 
			traffic
			-----------------------------
			omtp11PlusInterfaceNumber:
			1 - CLIENT-1
			-----------------------------
			Values:
			eg: 1234
			-----------------------------"
        ::= { omtp11PlusPerformanceEntry 134 }

        omtp11PlusLan10gMacTerminatedVlanTaggedFramesTransmitted OBJECT-TYPE
		SYNTAX  DisplayString
		MAX-ACCESS  read-only
		STATUS  current
		DESCRIPTION
			"For port configured with 10G LAN traffic, 
			Counts the Transmitted VLAN Tagged Frames
			at port which is configured with 10G LAN 
			traffic
			-----------------------------
			omtp11PlusInterfaceNumber:
			1 - CLIENT-1
			-----------------------------
			Values:
			eg: 1234
			-----------------------------"
	::= { omtp11PlusPerformanceEntry 135 }

        omtp11PlusLan10gMacTerminatedVlanTaggedFramesReceived OBJECT-TYPE
		SYNTAX  DisplayString
		MAX-ACCESS  read-only
		STATUS  current
		DESCRIPTION
			"For port configured with 10G LAN traffic, 
			Counts the Received VLAN Tagged Frames
			at port which is configured with 10G LAN 
			traffic
			-----------------------------
			omtp11PlusInterfaceNumber:
			1 - CLIENT-1
			-----------------------------
			Values:
			eg: 1234
			-----------------------------"
	::= { omtp11PlusPerformanceEntry 136 }

        omtp11PlusLan10gMacTerminatedFrameSymbolErrorsReceived OBJECT-TYPE
		SYNTAX  DisplayString
		MAX-ACCESS  read-only
		STATUS  current
		DESCRIPTION
			"For port configured with 10G LAN traffic, 
			Counts the Frame Symbol Error Received
			at port which is configured with 10G LAN 
			traffic
			-----------------------------
			omtp11PlusInterfaceNumber:
			1 - CLIENT-1
			-----------------------------
			Values:
			eg: 1234
			-----------------------------"
	::= { omtp11PlusPerformanceEntry 137 }

        omtp11PlusLan10gMacTerminatedFragmentFramesReceived OBJECT-TYPE
		SYNTAX  DisplayString
		MAX-ACCESS  read-only
		STATUS  current
		DESCRIPTION
			"Counts the Fragment Frames Received
			at port which is configured with 10G LAN 
			traffic
			-----------------------------
			omtp11PlusInterfaceNumber:
			1 - CLIENT-1
			-----------------------------
			Values:
			eg: 1234
			-----------------------------"
	::= { omtp11PlusPerformanceEntry 138 }

        omtp11PlusLan10gMacTerminatedFrameCheckSequenceErrorsReceived OBJECT-TYPE
		SYNTAX  DisplayString
		MAX-ACCESS  read-only
		STATUS  current
		DESCRIPTION
			"For port configured with 10G LAN traffic, 
			Gives Mac Terminated Frame Check Sequence Errors Received
			at port which is configured with 10G LAN 
			traffic
			-----------------------------
			omtp11PlusInterfaceNumber:
			1 - CLIENT-1
			-----------------------------
			Values:
			eg: 1234
			-----------------------------"
	::= { omtp11PlusPerformanceEntry 139 }

	omtp11PlusLan10gMacTerminatedFramesReceivedWithNoDefect OBJECT-TYPE
		SYNTAX  DisplayString
		MAX-ACCESS  read-only
		STATUS  current
		DESCRIPTION
			"For port configured with 10G LAN traffic, 
			Gives count of number of Mac Terminated frames
			received with no defects such as undersized frames, FCS
			errors etc, for port confgiured with 10G LAN traffic 
			-----------------------------
			omtp11PlusInterfaceNumber:
			1 - CLIENT-1
			-----------------------------
			Values:
			eg: 1234
			-----------------------------"
	::= { omtp11PlusPerformanceEntry 140 }
	
	omtp11PlusLan10gMacTerminatedBytesTransmitted OBJECT-TYPE
		SYNTAX  DisplayString
		MAX-ACCESS  read-only
		STATUS  current
		DESCRIPTION
			"For port configured with 10G LAN traffic, 
			10G Bytes transmitted counter counts the number of 
			Ethernet bytes transmitted from the Client port 
			which is configured with 10G LAN traffic
			-----------------------------
			omtp11PlusInterfaceNumber:
			1 - CLIENT-1
			-----------------------------
			Values:
			eg: 1234
			-----------------------------"
	::= { omtp11PlusPerformanceEntry 141 }

	omtp11PlusLan10gMacTerminatedBytesReceived OBJECT-TYPE
		SYNTAX  DisplayString
		MAX-ACCESS  read-only
		STATUS  current
		DESCRIPTION
			"For port configured with 10G LAN traffic, 
			10G Bytes Received counter counts the number of 
			Ethernet bytes received at the Client port 
			which is configured with 10G LAN traffic
			-----------------------------
			omtp11PlusInterfaceNumber:
			1 - CLIENT-1
			-----------------------------
			Values:
			eg: 1234
			-----------------------------"
	::= { omtp11PlusPerformanceEntry 142 }

	omtp11PlusLan10gMacTerminatedControlFramesTransmitted OBJECT-TYPE
		SYNTAX  DisplayString
		MAX-ACCESS  read-only
		STATUS  current
		DESCRIPTION
			"For port configured with GE-GFP-F/FE-GFP-F traffic,
			gives the count of the Ethernet control frames
			transmitted.
			-----------------------------
			omtp11PlusInterfaceNumber:
			1 - CLIENT-1
			-----------------------------
			Values:
			eg: 1234
			-----------------------------"
	::= { omtp11PlusPerformanceEntry 143 }

	omtp11PlusLan10gMacTerminatedControlFramesReceived OBJECT-TYPE
		SYNTAX  DisplayString
		MAX-ACCESS  read-only
		STATUS  current
		DESCRIPTION
			"For port configured with GE-GFP-F/FE-GFP-F traffic,
			gives the count of the Ethernet control frames
			received.
			-----------------------------
			omtp11PlusInterfaceNumber:
			1 - CLIENT-1
			-----------------------------
			Values:
			eg: 1234
			-----------------------------"
	::= { omtp11PlusPerformanceEntry 144 }

        omtp11PlusLan10gTransparentTransmitLcvCount OBJECT-TYPE
		SYNTAX  DisplayString
		MAX-ACCESS  read-only
		STATUS  current
		DESCRIPTION
			"For port configured with 10G LAN traffic, 
			Gives Lan10g Transparent Transmit Lcv Count
			at port which is configured with 10G LAN 
			traffic
			-----------------------------
			omtp11PlusInterfaceNumber:
			1 - CLIENT-1
			-----------------------------
			Values:
			eg: 1234
			-----------------------------"
	::= { omtp11PlusPerformanceEntry 151 }

        omtp11PlusLan10gTransparentTransmitPropagationErrorDeletionCount OBJECT-TYPE
		SYNTAX  DisplayString
		MAX-ACCESS  read-only
		STATUS  current
		DESCRIPTION
			"For port configured with 10G LAN traffic, 
			Gives Lan10g Transparent Transmit Propagation Error Deletion Count
			at port which is configured with 10G LAN 
			traffic
			-----------------------------
			omtp11PlusInterfaceNumber:
			1 - CLIENT-1
			-----------------------------
			Values:
			eg: 1234
			-----------------------------"
        ::= { omtp11PlusPerformanceEntry 152 }

        omtp11PlusLan10gTransparentTransmitIdleDeletionCount OBJECT-TYPE
		SYNTAX  DisplayString
		MAX-ACCESS  read-only
		STATUS  current
		DESCRIPTION
			"For port configured with 10G LAN traffic, 
			Gives Lan10g Transparent Transmit Idle Deletion Count
			at port which is configured with 10G LAN 
			traffic
			-----------------------------
			omtp11PlusInterfaceNumber:
			1 - CLIENT-1
			-----------------------------
			Values:
			eg: 1234
			-----------------------------"
	::= { omtp11PlusPerformanceEntry 153 }

        omtp11PlusLan10gTransparentTransmitConfDeletionCount OBJECT-TYPE
		SYNTAX  DisplayString
		MAX-ACCESS  read-only
		STATUS  current
		DESCRIPTION
			"For port configured with 10G LAN traffic, 
			Gives Lan10g Transparent Transmit Conf Deletion Count
			at port which is configured with 10G LAN 
			traffic
			-----------------------------
			omtp11PlusInterfaceNumber:
			1 - CLIENT-1
			-----------------------------
			Values:
			eg: 1234
			-----------------------------"
        ::= { omtp11PlusPerformanceEntry 154 }

        omtp11PlusLan10gTransparentTransmitPropagationInsertionCount OBJECT-TYPE
		SYNTAX  DisplayString
		MAX-ACCESS  read-only
		STATUS  current
		DESCRIPTION
			"For port configured with 10G LAN traffic, 
			Gives Lan10g Transparent Transmit Propagation Insertion Count
			at port which is configured with 10G LAN 
			traffic
			-----------------------------
			omtp11PlusInterfaceNumber:
			1 - CLIENT-1
			-----------------------------
			Values:
			eg: 1234
			-----------------------------"
	::= { omtp11PlusPerformanceEntry 155 }

        omtp11PlusLan10gTransparentTransmitIdleInsertionCount OBJECT-TYPE
		SYNTAX  DisplayString
		MAX-ACCESS  read-only
		STATUS  current
		DESCRIPTION
			"For port configured with 10G LAN traffic, 
			Gives Lan10g Transparent Transmit Idle Insertion Count
			at port which is configured with 10G LAN 
			traffic
			-----------------------------
			omtp11PlusInterfaceNumber:
			1 - CLIENT-1
			-----------------------------
			Values:
			eg: 1234
			-----------------------------"
	::= { omtp11PlusPerformanceEntry 156 }

        omtp11PlusLan10gTransparentTransmitConfInsertionCount OBJECT-TYPE
		SYNTAX  DisplayString
		MAX-ACCESS  read-only
		STATUS  current
		DESCRIPTION
			"For port configured with 10G LAN traffic, 
			Gives Lan10g Transparent Transmit Conf Insertion Count
			at port which is configured with 10G LAN 
			traffic
			-----------------------------
			omtp11PlusInterfaceNumber:
			1 - CLIENT-1
			-----------------------------
			Values:
			eg: 1234
			-----------------------------"
	::= { omtp11PlusPerformanceEntry 157 }

        omtp11PlusLan10gTransparentReceiveLcvCount OBJECT-TYPE
		SYNTAX  DisplayString
		MAX-ACCESS  read-only
		STATUS  current
		DESCRIPTION
			"For port configured with 10G LAN traffic, 
			Gives Lan10g Transparent Receive Lcv Count
			at port which is configured with 10G LAN 
			traffic
			-----------------------------
			omtp11PlusInterfaceNumber:
			1 - CLIENT-1
			-----------------------------
			Values:
			eg: 1234
			-----------------------------"
	::= { omtp11PlusPerformanceEntry 158 }

        omtp11PlusLan10gTransparentReceivePropagationErrorDeletionCount OBJECT-TYPE
		SYNTAX  DisplayString
		MAX-ACCESS  read-only
		STATUS  current
		DESCRIPTION
			"For port configured with 10G LAN traffic, 
			Gives Lan10g Transparent Receive Propagation Error
			Deletion Count at port which is configured with 10G LAN 
			traffic
			-----------------------------
			omtp11PlusInterfaceNumber:
			1 - CLIENT-1
			-----------------------------
			Values:
			eg: 1234
			-----------------------------"
	::= { omtp11PlusPerformanceEntry 159 }

        omtp11PlusLan10gTransparentReceiveIdleDeletionCount OBJECT-TYPE
		SYNTAX  DisplayString
		MAX-ACCESS  read-only
		STATUS  current
		DESCRIPTION
			"For port configured with 10G LAN traffic, 
			Gives Lan10g Transparent Receive Idle Deletion Count
			at port which is configured with 10G LAN 
			traffic
			-----------------------------
			omtp11PlusInterfaceNumber:
			1 - CLIENT-1
			-----------------------------
			Values:
			eg: 1234
			-----------------------------"
	::= { omtp11PlusPerformanceEntry 160 }

        omtp11PlusLan10gTransparentReceiveConfDeletionCount OBJECT-TYPE
		SYNTAX  DisplayString
		MAX-ACCESS  read-only
		STATUS  current
		DESCRIPTION
			"For port configured with 10G LAN traffic, 
			Gives Lan10g Transparent Receive Conf Deletion Count
			at port which is configured with 10G LAN 
			traffic
			-----------------------------
			omtp11PlusInterfaceNumber:
			1 - CLIENT-1
			-----------------------------
			Values:
			eg: 1234
			-----------------------------" 
	::= { omtp11PlusPerformanceEntry 161 }

        omtp11PlusLan10gTransparentReceivePacketDeletionCount OBJECT-TYPE
		SYNTAX  DisplayString
		MAX-ACCESS  read-only
		STATUS  current
		DESCRIPTION
			"For port configured with 10G LAN traffic, 
			Gives Lan10g Transparent Receive Packet Deletion Count
			at port which is configured with 10G LAN 
			traffic
			-----------------------------
			omtp11PlusInterfaceNumber:
			1 - CLIENT-1
			-----------------------------
			Values:
			eg: 1234
			-----------------------------"
	::= { omtp11PlusPerformanceEntry 162 }

        omtp11PlusGfpCoreHeaderErrorCount OBJECT-TYPE
		SYNTAX  DisplayString
		MAX-ACCESS  read-only
		STATUS  current
		DESCRIPTION
			"Get GFP Core Header Error Count at port which is
			configured with 10G LAN traffic
			-----------------------------
			omtp11PlusInterfaceNumber:
			1 - CLIENT-1
			-----------------------------
			Values:
			eg: 1234
			-----------------------------"
	::= { omtp11PlusPerformanceEntry 171 }

        omtp11PlusGfpExtentionHeaderErrorCount OBJECT-TYPE
		SYNTAX  DisplayString
		MAX-ACCESS  read-only
		STATUS  current
		DESCRIPTION
			"Get GFP Extention Header Error Count at port which is
			configured with 10G LAN traffic
			-----------------------------
			omtp11PlusInterfaceNumber:
			1 - CLIENT-1
			-----------------------------
			Values:
			eg: 1234
			-----------------------------"
	::= { omtp11PlusPerformanceEntry 172 }

	omtp11PlusGfpFrameCountWithSingleBitError OBJECT-TYPE
		SYNTAX  DisplayString
		MAX-ACCESS  read-only
		STATUS  current
		DESCRIPTION
			"For port configured with
			GE-GFP-F/FE-GFP-F/GE-GFP-T/FE-GFP-T traffic,
			gives the count of GFP Frames that are received 
			with single bit error.
			-----------------------------
			omtp11PlusInterfaceNumber:
			1 - CLIENT-1
			-----------------------------
			Values:
			eg: 1234
			-----------------------------"
	::= { omtp11PlusPerformanceEntry 173 }

	omtp11PlusGfpTypeHeaderErrorCount OBJECT-TYPE
		SYNTAX  DisplayString
		MAX-ACCESS  read-only
		STATUS  current
		DESCRIPTION
			"For port configured with
			GE-GFP-F/FE-GFP-F/GE-GFP-T/FE-GFP-T traffic,
			gives the count of received GFP frames which have error
			in the type header.
			-----------------------------
			omtp11PlusInterfaceNumber:
			1 - CLIENT-1
			-----------------------------
			Values:
			eg: 1234
			-----------------------------"
	::= { omtp11PlusPerformanceEntry 174 }

	omtp11PlusGfpReceiveDropFrameCount OBJECT-TYPE
		SYNTAX  DisplayString
		MAX-ACCESS  read-only
		STATUS  current
		DESCRIPTION
			"For port configured with
			GE-GFP-F/FE-GFP-F/GE-GFP-T/FE-GFP-T traffic,
			gives the Drop Frame count of received GFP frames.
			-----------------------------
			omtp11PlusInterfaceNumber:
			1 - CLIENT-1
			-----------------------------
			Values:
			eg: 1234
			-----------------------------"
	::= { omtp11PlusPerformanceEntry 175 }

	omtp11PlusGfpReceiveExtensionHeaderIdentifierFilterDropCount OBJECT-TYPE
		SYNTAX  DisplayString
		MAX-ACCESS  read-only
		STATUS  current
		DESCRIPTION
			"For port configured with
			GE-GFP-F/FE-GFP-F/GE-GFP-T/FE-GFP-T traffic,
			gives the Extension Header Identifier Filter
			Drop count of received GFP frames.
			-----------------------------
			omtp11PlusInterfaceNumber:
			1 - CLIENT-1
			-----------------------------
			Values:
			eg: 1234
			-----------------------------"
	::= { omtp11PlusPerformanceEntry 176 }

        omtp11PlusFcTransmitWordCount OBJECT-TYPE
		SYNTAX  DisplayString
		MAX-ACCESS  read-only
		STATUS  current
		DESCRIPTION
			"For port configured with FC 800/1200 traffic, 
			Get the FC Transmit Word Count at port which
			is configured with FC traffic
			-----------------------------
			omtp11PlusInterfaceNumber:
			1 - CLIENT-1
			-----------------------------
			Values:
			eg: 1234
			-----------------------------"
        ::= { omtp11PlusPerformanceEntry 181 }

        omtp11PlusFcTransmitBadCrc OBJECT-TYPE
		SYNTAX  DisplayString
		MAX-ACCESS  read-only
		STATUS  current
		DESCRIPTION
			"For port configured with FC 800/1200 traffic, 
			Get the FC Transmit Bad Crc count at port which
			is configured with FC traffic
			-----------------------------
			omtp11PlusInterfaceNumber:
			1 - CLIENT-1
			-----------------------------
			Values:
			eg: 1234
			-----------------------------"
        ::= { omtp11PlusPerformanceEntry 182 }

        omtp11PlusFcTransmitTotalPackets OBJECT-TYPE
		SYNTAX  DisplayString
		MAX-ACCESS  read-only
		STATUS  current
		DESCRIPTION
			"For port configured with FC 800/1200 traffic, 
			Get the FC Transmit Total packet Count at port which
			is configured with FC traffic
			-----------------------------
			omtp11PlusInterfaceNumber:
			1 - CLIENT-1
			-----------------------------
			Values:
			eg: 1234
			-----------------------------"
	::= { omtp11PlusPerformanceEntry 183 }

        omtp11PlusFcTransmitLcvCount OBJECT-TYPE
		SYNTAX  DisplayString
		MAX-ACCESS  read-only
		STATUS  current
		DESCRIPTION
			"For port configured with FC 800/1200 traffic, 
			Get the FC Transmit Lcv Count at port which
			is configured with FC traffic
			-----------------------------
			omtp11PlusInterfaceNumber:
			1 - CLIENT-1
			-----------------------------
			Values:
			eg: 1234
			-----------------------------"
	::= { omtp11PlusPerformanceEntry 184 }

        omtp11PlusFcReceiveWordCount OBJECT-TYPE
		SYNTAX  DisplayString
		MAX-ACCESS  read-only
		STATUS  current
		DESCRIPTION
			"For port configured with FC 800/1200 traffic, 
			Get the FC Receive Word Count at port which
			is configured with FC traffic
			-----------------------------
			omtp11PlusInterfaceNumber:
			1 - CLIENT-1
			-----------------------------
			Values:
			eg: 1234
			-----------------------------"
	::= { omtp11PlusPerformanceEntry 185 }

        omtp11PlusFcReceiveBadCrc OBJECT-TYPE
		SYNTAX  DisplayString
		MAX-ACCESS  read-only
		STATUS  current
		DESCRIPTION
			"For port configured with FC 800/1200 traffic, 
			Get the FC Receive Bad CRC at port which
			is configured with FC traffic
			-----------------------------
			omtp11PlusInterfaceNumber:
			1 - CLIENT-1
			-----------------------------
			Values:
			eg: 1234
			-----------------------------"
        ::= { omtp11PlusPerformanceEntry 186 }

        omtp11PlusFcReceiveTotalPackets OBJECT-TYPE
		SYNTAX  DisplayString
		MAX-ACCESS  read-only
		STATUS  current
		DESCRIPTION
			"For port configured with FC 800/1200 traffic, 
			Get the FC Receive total packet Count at port which
			is configured with FC traffic
			-----------------------------
			omtp11PlusInterfaceNumber:
			1 - CLIENT-1
			-----------------------------
			Values:
			eg: 1234
			-----------------------------"
	::= { omtp11PlusPerformanceEntry 187 }

        omtp11PlusFcReceiveLcvCount OBJECT-TYPE
		SYNTAX  DisplayString
		MAX-ACCESS  read-only
		STATUS  current
		DESCRIPTION
			"For port configured with FC 800/1200 traffic, 
			Get the FC Receive Lcv Count at port which
			is configured with FC traffic
			-----------------------------
			omtp11PlusInterfaceNumber:
			1 - CLIENT-1
			-----------------------------
			Values:
			eg: 1234
			-----------------------------"
	::= { omtp11PlusPerformanceEntry 188 }

        omtp11PlusFcTransmitFillWordInsertionCount OBJECT-TYPE
		SYNTAX  DisplayString
		MAX-ACCESS  read-only
		STATUS  current
		DESCRIPTION
			"For port configured with FC 800/1200 traffic, 
			Get the FC FW Insertion Count at port which
			is configured with FC traffic
			-----------------------------
			omtp11PlusInterfaceNumber:
			1 - CLIENT-1
			-----------------------------
			Values:
			eg: 1234
			-----------------------------"
	::= { omtp11PlusPerformanceEntry 189 }

        omtp11PlusFcTransmitPrimitiveSequenceInsertionCount OBJECT-TYPE
		SYNTAX  DisplayString
		MAX-ACCESS  read-only
		STATUS  current
		DESCRIPTION
			"For port configured with FC 800/1200 traffic, 
			Get the FC Primitive Sequence Insertion Count at port
			which is configured with FC traffic
			-----------------------------
			omtp11PlusInterfaceNumber:
			1 - CLIENT-1
			-----------------------------
			Values:
			eg: 1234
			-----------------------------"
	::= { omtp11PlusPerformanceEntry 190 }

        omtp11PlusFcTransmitFillWordDeletionCount OBJECT-TYPE
		SYNTAX  DisplayString
		MAX-ACCESS  read-only
		STATUS  current
		DESCRIPTION
			"For port configured with FC 800/1200 traffic, 
			Get the FC FW Deletion Count at port which
			is configured with FC traffic
			-----------------------------
			omtp11PlusInterfaceNumber:
			1 - CLIENT-1
			-----------------------------
			Values:
			eg: 1234
			-----------------------------"
	::= { omtp11PlusPerformanceEntry 191 }

        omtp11PlusFcTransmitPrimitiveSequenceDeletionCount OBJECT-TYPE
		SYNTAX  DisplayString
		MAX-ACCESS  read-only
		STATUS  current
		DESCRIPTION
			"For port configured with FC 800/1200 traffic, 
			Get the FC Primitive Sequence Deletion Count at port
			which is configured with FC traffic
			-----------------------------
			omtp11PlusInterfaceNumber:
			1 - CLIENT-1
			-----------------------------
			Values:
			eg: 1234
			-----------------------------"
	::= { omtp11PlusPerformanceEntry 192 }

	omtp11PlusPerformanceTableRowStatus OBJECT-TYPE
              SYNTAX      RowStatus
              MAX-ACCESS  read-write
              STATUS      current
              DESCRIPTION
                      "	This is MIB realted property,
			NOT to be considered as a card property"
              ::= { omtp11PlusPerformanceEntry 193 }


--*****************************************************************************
--				    DIAGNOSTICS
--*****************************************************************************        

	omtp11PlusDiagnosticsTable OBJECT-TYPE
	      SYNTAX  SEQUENCE OF Omtp11PlusDiagnosticsEntry
              MAX-ACCESS  not-accessible
              STATUS  current
              DESCRIPTION
                      "Category contains properties that are used for debugging
                      card software"
		::= { omtp11PlusDiagnostics 1 }	

	omtp11PlusDiagnosticsEntry   OBJECT-TYPE
              SYNTAX  Omtp11PlusDiagnosticsEntry 
              MAX-ACCESS  not-accessible
              STATUS  current
              DESCRIPTION 
              	""
		INDEX   { node, rack , subRack , slot , omtp11PlusInterfaceNumber }
		::= { omtp11PlusDiagnosticsTable 1 }
	
	Omtp11PlusDiagnosticsEntry ::= 
		SEQUENCE {
				omtp11PlusAccessCortinaRegister				INTEGER,
				omtp11PlusCollectCortinaRegisterDump			INTEGER,
				omtp11PlusCollectCortinaModulebGpllRxLockStatus		DisplayString,
				omtp11PlusCollectCortinaModulebGpllTxLockStatus		DisplayString,
				omtp11PlusCollectCortinaModulebTxSerdesLockStatus	DisplayString,
				omtp11PlusCollectCortinaModulebTxSerdesVcoTunedValue	DisplayString,
				omtp11PlusCollectCortinaModulebXfiCupllLockStatus	DisplayString,
				omtp11PlusCollectCortinaModulebAllClockLockStatus	OCTET STRING,
				omtp11PlusDiagnosticTableRowStatus			RowStatus
			}
			
	omtp11PlusAccessCortinaRegister OBJECT-TYPE
		SYNTAX  INTEGER
		MAX-ACCESS  read-write
		STATUS  current
		DESCRIPTION
			"Sets/gets the value of any cortina register
			-----------------------------
			omtp11PlusInterfaceNumber: 0
			-----------------------------
			Values:
			eg:
			example of cortina register - 76071076
			value - 1
			-----------------------------"
	::= { omtp11PlusDiagnosticsEntry 1 }	

	omtp11PlusCollectCortinaRegisterDump OBJECT-TYPE
		SYNTAX  INTEGER
		MAX-ACCESS  read-only
		STATUS  current
		DESCRIPTION
			"create register dump of all cortina register
			-----------------------------
			omtp11PlusInterfaceNumber: 0
			-----------------------------
                     	This query will create registe dump in card's 
			root directory
			-----------------------------"
	::= { omtp11PlusDiagnosticsEntry 2 }	

	omtp11PlusCollectCortinaModulebGpllRxLockStatus OBJECT-TYPE
		SYNTAX  DisplayString
		MAX-ACCESS  read-only
		STATUS  current
		DESCRIPTION
			"reads GPLL Rx clock lock status for all slices
			 of module B
			 Expected value : should be 0x00049 to indicate 
			 Value is locked
			 The following register will be read:
			 0x00c59, 0x00c99, 0x00cd9, 0x00d19
			 The register that will be read is GPLLX1_SDS_COMMON_TXLOCKD0_INTSTATUS
			-----------------------------
			omtp11PlusInterfaceNumber: 0
			-----------------------------"
	::= { omtp11PlusDiagnosticsEntry 3 }	
	
	omtp11PlusCollectCortinaModulebGpllTxLockStatus OBJECT-TYPE
		SYNTAX  DisplayString
		MAX-ACCESS  read-only
		STATUS  current
		DESCRIPTION
			"reads GPLL Tx clock lock status for all slices
			 of module B
			 Expected value : should be 0x00049 to indicate 
			 Value is locked
			 The following register will be read:
			 0x00d59, 0x00d99, 0x00dd9, 0x00e19
			 The register that will be read is GPLLX1_SDS_COMMON_TXLOCKD0_INTSTATUS
			-----------------------------
			omtp11PlusInterfaceNumber: 0
			-----------------------------"
	::= { omtp11PlusDiagnosticsEntry 4 }

	omtp11PlusCollectCortinaModulebTxSerdesLockStatus OBJECT-TYPE
		SYNTAX  DisplayString
		MAX-ACCESS  read-only
		STATUS  current
		DESCRIPTION
			"reads Tx serdes clock lock status for all slices
			 of module B
			 Expected value : should be 0x00049 to indicate 
			 Value is locked
			 The following register will be read:
			 0x0303d, 0x0343d, 0x0383d, 0x03c3d
			 The register that will be read is 
			 XFI32X1_SDS_XFI32X1_SDS_COMMON_TXLOCKD0_INTSTATUS
			-----------------------------
			omtp11PlusInterfaceNumber: 0
			-----------------------------"
	::= { omtp11PlusDiagnosticsEntry 5 }	
	
	omtp11PlusCollectCortinaModulebTxSerdesVcoTunedValue OBJECT-TYPE
		SYNTAX  DisplayString
		MAX-ACCESS  read-only
		STATUS  current
		DESCRIPTION
			"reads Tx serdes VCO tuning value for all slices
			 of module B
			 Expected value : Value when correctly tuned should not 
			 be near extremes of 0x3F or 0x00
			 The following register will be read:
			 0x03031, 0x03431, 0x03831, 0x03c31
			 The register that will be read is XFI32X1_SDS_XFI32X1_SDS_COMMON_TXVCO0_STATUS
			-----------------------------
			omtp11PlusInterfaceNumber: 0
			-----------------------------"
	::= { omtp11PlusDiagnosticsEntry 6 }	

	omtp11PlusCollectCortinaModulebXfiCupllLockStatus OBJECT-TYPE
		SYNTAX  DisplayString
		MAX-ACCESS  read-only
		STATUS  current
		DESCRIPTION
			"reads XFI CUPLL Lock status for all slices
			 of module B
			 Expected value : should be 0x00049 to indicate Value is locked 
			 The following register will be read:
			 0x1b438, 0x1b478, 0x1b4b8, 0x1b4f8
			 The register that will be read is XFI_CUPLL_LOCKDET_INTSTATUS
			-----------------------------
			omtp11PlusInterfaceNumber: 0
			-----------------------------"
	::= { omtp11PlusDiagnosticsEntry 7 }	

	omtp11PlusCollectCortinaModulebAllClockLockStatus OBJECT-TYPE
		SYNTAX  OCTET STRING
		MAX-ACCESS  read-only
		STATUS  current
		DESCRIPTION
			"reads Lock status of following clocks:
			 GPLL Rx/Tx, Tx serdes, Tx Serdes VCO tuned value and XFI CUPLLfor all slices
			 of module B.
			 Expected value : should be 0x00049 to indicate Value is locked 
			 The following register will be read:
			 0x1b438, 0x1b478, 0x1b4b8, 0x1b4f8
			 The register that will be read is XFI_CUPLL_LOCKDET_INTSTATUS
			-----------------------------
			omtp11PlusInterfaceNumber: 0
			-----------------------------"
	::= { omtp11PlusDiagnosticsEntry 8 }	

	omtp11PlusDiagnosticTableRowStatus OBJECT-TYPE
              SYNTAX      RowStatus
              MAX-ACCESS  read-write
              STATUS      current
              DESCRIPTION
			"*****************************
			This is MIB realted property,
			NOT to be considered as a card property
			*****************************"
	::= { omtp11PlusDiagnosticsEntry 9 }
        
--*****************************************************************************
--				    ALARM Notification Table
--*****************************************************************************

        omtp11PlusXfpInputPowerFailureAlarmTrap NOTIFICATION-TYPE
         OBJECTS { omtp11PlusXfpInputPowerFailureAlarm }
                STATUS  current
                DESCRIPTION
                        "OMTP11-PLUS XFP input power failure alarm trap"
        ::= { omtp11PlusAlarmNotification 1 }


        omtp11PlusXfpOutputPowerFailureAlarmTrap NOTIFICATION-TYPE
         OBJECTS { omtp11PlusXfpOutputPowerFailureAlarm }
               STATUS  current
               DESCRIPTION
                        "OMTP11-PLUS XFP output power failure alarm trap"
        ::= { omtp11PlusAlarmNotification 2 }


        omtp11PlusXfpHighTemperatureAlarmTrap NOTIFICATION-TYPE
         OBJECTS { omtp11PlusXfpHighTemperatureAlarm }
               STATUS  current
               DESCRIPTION
                        "OMTP11-PLUS XFP high temperature alarm trap"
        ::= { omtp11PlusAlarmNotification 3 }

        omtp11PlusXfpLowTemperatureAlarmTrap NOTIFICATION-TYPE
         OBJECTS { omtp11PlusXfpLowTemperatureAlarm }
               STATUS  current
               DESCRIPTION
                        "OMTP11-PLUS XFP low temperature alarm trap"
        ::= { omtp11PlusAlarmNotification 4 }

        omtp11PlusXfpHighTemperatureWarningTrap NOTIFICATION-TYPE
         OBJECTS { omtp11PlusXfpHighTemperatureWarning }
               STATUS  current
               DESCRIPTION
                        "OMTP11-PLUS XFP high temperature warning trap"
        ::= { omtp11PlusAlarmNotification 5 }

        omtp11PlusXfpLowTemperatureWarningTrap NOTIFICATION-TYPE
         OBJECTS { omtp11PlusXfpLowTemperatureWarning }
               STATUS  current
               DESCRIPTION
                        "OMTP11-PLUS XFP low temperature warning trap"
        ::= { omtp11PlusAlarmNotification 6 }

        omtp11PlusXfpHighBiasCurrentAlarmTrap NOTIFICATION-TYPE
         OBJECTS { omtp11PlusXfpHighBiasCurrentAlarm }
               STATUS  current
               DESCRIPTION
                        "OMTP11-PLUS XFP high bias current alarm trap"
        ::= { omtp11PlusAlarmNotification 7 }

        omtp11PlusXfpLowBiasCurrentAlarmTrap NOTIFICATION-TYPE
         OBJECTS { omtp11PlusXfpLowBiasCurrentAlarm }
               STATUS  current
               DESCRIPTION
                        "OMTP11-PLUS XFP low bias current alarm trap"
        ::= { omtp11PlusAlarmNotification 8 }

        omtp11PlusXfpHighBiasCurrentWarningTrap NOTIFICATION-TYPE
         OBJECTS { omtp11PlusXfpHighBiasCurrentWarning }
               STATUS  current
               DESCRIPTION
                        "OMTP11-PLUS XFP high bias current warning trap"
        ::= { omtp11PlusAlarmNotification 9 }

        omtp11PlusXfpLowBiasCurrentWarningTrap NOTIFICATION-TYPE
         OBJECTS { omtp11PlusXfpLowBiasCurrentWarning }
               STATUS  current
               DESCRIPTION
                        "OMTP11-PLUS XFP low bias current warning trap"
        ::= { omtp11PlusAlarmNotification 10 }

        omtp11PlusXfpInputHighPowerAlarmTrap NOTIFICATION-TYPE
         OBJECTS { omtp11PlusXfpInputHighPowerAlarm }
               STATUS  current
               DESCRIPTION
                        "OMTP11-PLUS XFP input high power alarm trap"
        ::= { omtp11PlusAlarmNotification 11 }

        omtp11PlusXfpInputLowPowerAlarmTrap NOTIFICATION-TYPE
         OBJECTS { omtp11PlusXfpInputLowPowerAlarm }
               STATUS  current
               DESCRIPTION
                        "OMTP11-PLUS XFP input low power alarm trap"
        ::= { omtp11PlusAlarmNotification 12 }

        omtp11PlusXfpInputHighPowerWarningTrap NOTIFICATION-TYPE
         OBJECTS { omtp11PlusXfpInputHighPowerWarning }
               STATUS  current
               DESCRIPTION
                        "OMTP11-PLUS XFP input high power warning trap"
        ::= { omtp11PlusAlarmNotification 13 }

        omtp11PlusXfpInputLowPowerWarningTrap NOTIFICATION-TYPE
         OBJECTS { omtp11PlusXfpInputLowPowerWarning }
               STATUS  current
               DESCRIPTION
                        "OMTP11-PLUS XFP input low power warning trap"
        ::= { omtp11PlusAlarmNotification 14 }

        omtp11PlusXfpOutputHighPowerAlarmTrap NOTIFICATION-TYPE
         OBJECTS { omtp11PlusXfpOutputHighPowerAlarm }
               STATUS  current
               DESCRIPTION
                        "OMTP11-PLUS XFP output high power alarm trap"
        ::= { omtp11PlusAlarmNotification 15 }

        omtp11PlusXfpOutputLowPowerAlarmTrap NOTIFICATION-TYPE
         OBJECTS { omtp11PlusXfpOutputLowPowerAlarm }
               STATUS  current
               DESCRIPTION
                        "OMTP11-PLUS XFP output low power alarm trap"
        ::= { omtp11PlusAlarmNotification 16 }

        omtp11PlusXfpOutputHighPowerWarningTrap NOTIFICATION-TYPE
         OBJECTS { omtp11PlusXfpOutputHighPowerWarning }
               STATUS  current
               DESCRIPTION
                        "OMTP11-PLUS XFP output high power warning trap"
        ::= { omtp11PlusAlarmNotification 17 }

        omtp11PlusXfpOutputLowPowerWarningTrap NOTIFICATION-TYPE
         OBJECTS { omtp11PlusXfpOutputLowPowerWarning }
               STATUS  current
               DESCRIPTION
                        "OMTP11-PLUS XFP output low power warning trap"
        ::= { omtp11PlusAlarmNotification 18 }

        omtp11PlusXfpHighSupplyVoltageAlarmTrap NOTIFICATION-TYPE
         OBJECTS { omtp11PlusXfpHighSupplyVoltageAlarm }
               STATUS  current
               DESCRIPTION
                        "OMTP11-PLUS XFP high supply voltage alarm trap"
        ::= { omtp11PlusAlarmNotification 19 }

        omtp11PlusXfpLowSupplyVoltageAlarmTrap NOTIFICATION-TYPE
         OBJECTS { omtp11PlusXfpLowSupplyVoltageAlarm }
               STATUS  current
               DESCRIPTION
                        "OMTP11-PLUS XFP low supply voltage alarm trap"
        ::= { omtp11PlusAlarmNotification 20 }

        omtp11PlusXfpHighSupplyVoltageWarningTrap NOTIFICATION-TYPE
         OBJECTS { omtp11PlusXfpHighSupplyVoltageWarning }
               STATUS  current
               DESCRIPTION
                        "OMTP11-PLUS XFP high supply voltage warning trap"
        ::= { omtp11PlusAlarmNotification 21 }

        omtp11PlusXfpLowSupplyVoltageWarningTrap NOTIFICATION-TYPE
         OBJECTS { omtp11PlusXfpLowSupplyVoltageWarning }
               STATUS  current
               DESCRIPTION
                        "OMTP11-PLUS XFP low supply voltage warning trap"
        ::= { omtp11PlusAlarmNotification 22 }

        omtp11PlusXfpPresenceAbsenceNotificationTrap NOTIFICATION-TYPE
         OBJECTS { omtp11PlusXfpPresenceAbsenceNotification }
               STATUS  current
               DESCRIPTION
                        "OMTP11-PLUS XFP presence absence notification"
        ::= { omtp11PlusAlarmNotification 23 }

        omtp11PlusOtuLossOfSignalAlarmTrap NOTIFICATION-TYPE
         OBJECTS { omtp11PlusOtuLossOfSignalAlarm }
               STATUS  current
               DESCRIPTION
                        "OMTP11-PLUS OTU loss of signal alarm trap"
        ::= { omtp11PlusAlarmNotification 31 }

        omtp11PlusOtuLossOfFrameAlarmTrap NOTIFICATION-TYPE
         OBJECTS { omtp11PlusOtuLossOfFrameAlarm }
               STATUS  current
               DESCRIPTION
                        "OMTP11-PLUS OTU loss of frame alarm trap"
        ::= { omtp11PlusAlarmNotification 32 }

        omtp11PlusOtuOutOfFrameAlarmTrap NOTIFICATION-TYPE
         OBJECTS { omtp11PlusOtuOutOfFrameAlarm }
               STATUS  current
               DESCRIPTION
                        "OMTP11-PLUS OTU out of frame alarm trap"
        ::= { omtp11PlusAlarmNotification 33 }

        omtp11PlusOtuLossOfMultiFrameAlarmTrap NOTIFICATION-TYPE
         OBJECTS { omtp11PlusOtuLossOfMultiFrameAlarm }
               STATUS  current
               DESCRIPTION
                        "OMTP11-PLUS OTU loss of multi frame alarm trap"
        ::= { omtp11PlusAlarmNotification 34 }

        omtp11PlusOtuOutOfMultiFrameAlarmTrap NOTIFICATION-TYPE
         OBJECTS { omtp11PlusOtuOutOfMultiFrameAlarm }
               STATUS  current
               DESCRIPTION
                        "OMTP11-PLUS OTU out of multi frame alarm trap"
        ::= { omtp11PlusAlarmNotification 35 }

        omtp11PlusOtuSignalFailAlarmTrap NOTIFICATION-TYPE
         OBJECTS { omtp11PlusOtuSignalFailAlarm }
               STATUS  current
               DESCRIPTION
                        "OMTP11-PLUS OTU signal fail alarm trap"
        ::= { omtp11PlusAlarmNotification 36 }

        omtp11PlusOtuSignalDegradeAlarmTrap NOTIFICATION-TYPE
         OBJECTS { omtp11PlusOtuSignalDegradeAlarm }
               STATUS  current
               DESCRIPTION
                        "OMTP11-PLUS OTU signal degrade alarm trap"
        ::= { omtp11PlusAlarmNotification 37 }

        omtp11PlusOtuAlarmIndicationSignalAlarmTrap NOTIFICATION-TYPE
         OBJECTS { omtp11PlusOtuAlarmIndicationSignalAlarm }
               STATUS  current
               DESCRIPTION
                        "OMTP11-PLUS OTU alarm indication signal alarm trap"
        ::= { omtp11PlusAlarmNotification 38 }

        omtp11PlusOtuIncomingAlignmentErrorAlarmTrap NOTIFICATION-TYPE
         OBJECTS { omtp11PlusOtuIncomingAlignmentErrorAlarm }
               STATUS  current
               DESCRIPTION
                        "OMTP11-PLUS OTU incoming alignment error alarm trap"
        ::= { omtp11PlusAlarmNotification 39 }

        omtp11PlusOtuTraceIdentifierMismatchAlarmTrap NOTIFICATION-TYPE
         OBJECTS { omtp11PlusOtuTraceIdentifierMismatchAlarm }
               STATUS  current
               DESCRIPTION
                        "OMTP11-PLUS OTU trace identifier mismatch alarm trap"
        ::= { omtp11PlusAlarmNotification 40 }

        omtp11PlusOtuBackwardIncomingAlignmentErrorAlarmTrap NOTIFICATION-TYPE
         OBJECTS { omtp11PlusOtuBackwardIncomingAlignmentErrorAlarm }
               STATUS  current
               DESCRIPTION
                        "OMTP11-PLUS OTU backward incoming alignment error alarm trap"
        ::= { omtp11PlusAlarmNotification 41 }

        omtp11PlusOtuBackwardDefectIndicationAlarmTrap NOTIFICATION-TYPE
         OBJECTS { omtp11PlusOtuBackwardDefectIndicationAlarm }
               STATUS  current
               DESCRIPTION
                        "OMTP11-PLUS OTU backward defect indication alarm trap"
        ::= { omtp11PlusAlarmNotification 42 }

        omtp11PlusOduSignalFailAlarmTrap NOTIFICATION-TYPE
         OBJECTS { omtp11PlusOduSignalFailAlarm }
               STATUS  current
               DESCRIPTION
                        "OMTP11-PLUS ODU signal fail alarm trap"
        ::= { omtp11PlusAlarmNotification 51 }

        omtp11PlusOduSignalDegradeAlarmTrap NOTIFICATION-TYPE
         OBJECTS { omtp11PlusOduSignalDegradeAlarm }
               STATUS  current
               DESCRIPTION
                        "OMTP11-PLUS ODU signal degrade alarm trap"
        ::= { omtp11PlusAlarmNotification 52 }

        omtp11PlusOduAlarmIndicationSignalAlarmTrap NOTIFICATION-TYPE
         OBJECTS { omtp11PlusOduAlarmIndicationSignalAlarm }
               STATUS  current
               DESCRIPTION
                        "OMTP11-PLUS ODU alarm indication signal alarm trap"
        ::= { omtp11PlusAlarmNotification 53 }

        omtp11PlusOduTcm1IncomingAlignmentErrorAlarmTrap NOTIFICATION-TYPE
         OBJECTS { omtp11PlusOduTcm1IncomingAlignmentErrorAlarm }
               STATUS  current
               DESCRIPTION
                        "OMTP11-PLUS ODU TCM1 incoming alignment error alarm trap"
        ::= { omtp11PlusAlarmNotification 54 }

        omtp11PlusOduTcm2IncomingAlignmentErrorAlarmTrap NOTIFICATION-TYPE
         OBJECTS { omtp11PlusOduTcm2IncomingAlignmentErrorAlarm }
               STATUS  current
               DESCRIPTION
                        "OMTP11-PLUS ODU TCM2 incoming alignment error alarm trap"
        ::= { omtp11PlusAlarmNotification 55 }

        omtp11PlusOduTcm3IncomingAlignmentErrorAlarmTrap NOTIFICATION-TYPE
         OBJECTS { omtp11PlusOduTcm3IncomingAlignmentErrorAlarm }
               STATUS  current
               DESCRIPTION
                        "OMTP11-PLUS ODU TCM3 incoming alignment error alarm trap"
        ::= { omtp11PlusAlarmNotification 56 }

        omtp11PlusOduTcm4IncomingAlignmentErrorAlarmTrap NOTIFICATION-TYPE
         OBJECTS { omtp11PlusOduTcm4IncomingAlignmentErrorAlarm }
               STATUS  current
               DESCRIPTION
                        "OMTP11-PLUS ODU TCM4 incoming alignment error alarm trap"
        ::= { omtp11PlusAlarmNotification 57 }

        omtp11PlusOduTcm5IncomingAlignmentErrorAlarmTrap NOTIFICATION-TYPE
         OBJECTS { omtp11PlusOduTcm5IncomingAlignmentErrorAlarm }
               STATUS  current
               DESCRIPTION
                        "OMTP11-PLUS ODU TCM5 incoming alignment error alarm trap"
        ::= { omtp11PlusAlarmNotification 58 }

        omtp11PlusOduTcm6IncomingAlignmentErrorAlarmTrap NOTIFICATION-TYPE
         OBJECTS { omtp11PlusOduTcm6IncomingAlignmentErrorAlarm }
               STATUS  current
               DESCRIPTION
                        "OMTP11-PLUS ODU TCM6 incoming alignment error alarm trap"
        ::= { omtp11PlusAlarmNotification 59 }

        omtp11PlusOduTraceIdentifierMismatchAlarmTrap NOTIFICATION-TYPE
         OBJECTS { omtp11PlusOduTraceIdentifierMismatchAlarm }
               STATUS  current
               DESCRIPTION
                        "OMTP11-PLUS ODU trace identifier mismatch alarm trap"
        ::= { omtp11PlusAlarmNotification 60 }

        omtp11PlusOduLockedDefectAlarmTrap NOTIFICATION-TYPE
         OBJECTS { omtp11PlusOduLockedDefectAlarm }
               STATUS  current
               DESCRIPTION
                        "OMTP11-PLUS ODU locked defect alarm trap"
        ::= { omtp11PlusAlarmNotification 61 }

        omtp11PlusOduOpenConnectionIndicationAlarmTrap NOTIFICATION-TYPE
         OBJECTS { omtp11PlusOduOpenConnectionIndicationAlarm }
               STATUS  current
               DESCRIPTION
                        "OMTP11-PLUS ODU open connection indication alarm trap"
        ::= { omtp11PlusAlarmNotification 62 }

        omtp11PlusOduBackwardDefectIndicationAlarmTrap NOTIFICATION-TYPE
         OBJECTS { omtp11PlusOduBackwardDefectIndicationAlarm }
               STATUS  current
               DESCRIPTION
                        "OMTP11-PLUS ODU backward defect indication alarm trap"
        ::= { omtp11PlusAlarmNotification 63 }

        omtp11PlusOduTcm1BackwardIncomingAlignmentErrorAlarmTrap NOTIFICATION-TYPE
         OBJECTS { omtp11PlusOduTcm1BackwardIncomingAlignmentErrorAlarm }
               STATUS  current
               DESCRIPTION
                        "OMTP11-PLUS ODU TCM1 backward incoming alignment error alarm trap"
        ::= { omtp11PlusAlarmNotification 64 }

        omtp11PlusOduTcm2BackwardIncomingAlignmentErrorAlarmTrap NOTIFICATION-TYPE
         OBJECTS { omtp11PlusOduTcm2BackwardIncomingAlignmentErrorAlarm }
               STATUS  current
               DESCRIPTION
                        "OMTP11-PLUS ODU TCM2 backward incoming alignment error alarm trap"
        ::= { omtp11PlusAlarmNotification 65 }

        omtp11PlusOduTcm3BackwardIncomingAlignmentErrorAlarmTrap NOTIFICATION-TYPE
         OBJECTS { omtp11PlusOduTcm3BackwardIncomingAlignmentErrorAlarm }
               STATUS  current
               DESCRIPTION
                        "OMTP11-PLUS ODU TCM3 backward incoming alignment error alarm trap"
        ::= { omtp11PlusAlarmNotification 66 }

        omtp11PlusOduTcm4BackwardIncomingAlignmentErrorAlarmTrap NOTIFICATION-TYPE
         OBJECTS { omtp11PlusOduTcm4BackwardIncomingAlignmentErrorAlarm }
               STATUS  current
               DESCRIPTION
                        "OMTP11-PLUS ODU TCM4 backward incoming alignment error alarm trap"
        ::= { omtp11PlusAlarmNotification 67 }

        omtp11PlusOduTcm5BackwardIncomingAlignmentErrorAlarmTrap NOTIFICATION-TYPE
         OBJECTS { omtp11PlusOduTcm5BackwardIncomingAlignmentErrorAlarm }
               STATUS  current
               DESCRIPTION
                        "OMTP11-PLUS ODU TCM5 backward incoming alignment error alarm trap"
        ::= { omtp11PlusAlarmNotification 68 }

        omtp11PlusOduTcm6BackwardIncomingAlignmentErrorAlarmTrap NOTIFICATION-TYPE
         OBJECTS { omtp11PlusOduTcm6BackwardIncomingAlignmentErrorAlarm }
               STATUS  current
               DESCRIPTION
                        "OMTP11-PLUS ODU TCM6 backward incoming alignment error alarm trap"
        ::= { omtp11PlusAlarmNotification 69 }

        omtp11PlusOpuPayloadMismatchAlarmTrap NOTIFICATION-TYPE
         OBJECTS { omtp11PlusOpuPayloadMismatchAlarm }
               STATUS  current
               DESCRIPTION
                        "OMTP11-PLUS OPU payload mismatch alarm trap"
        ::= { omtp11PlusAlarmNotification 70 }
        omtp11PlusOchLossOfPayloadAlarmTrap NOTIFICATION-TYPE
         OBJECTS { omtp11PlusOchLossOfPayloadAlarm }
               STATUS  current
               DESCRIPTION
                        "OMTP11-PLUS Och loss of payload alarm trap"
        ::= { omtp11PlusAlarmNotification 71 }

        omtp11PlusSdhLossOfSignalAlarmTrap NOTIFICATION-TYPE
         OBJECTS { omtp11PlusSdhLossOfSignalAlarm }
               STATUS  current
               DESCRIPTION
                        "OMTP11-PLUS SDH loss of signal alarm trap"
        ::= { omtp11PlusAlarmNotification 81 }

        omtp11PlusSdhOutOfFrameAlarmTrap NOTIFICATION-TYPE
         OBJECTS { omtp11PlusSdhOutOfFrameAlarm }
               STATUS  current
               DESCRIPTION
                        "OMTP11-PLUS SDH out of frame alarm trap"
        ::= { omtp11PlusAlarmNotification 82 }

        omtp11PlusSdhLossOfFrameAlarmTrap NOTIFICATION-TYPE
         OBJECTS { omtp11PlusSdhLossOfFrameAlarm }
               STATUS  current
               DESCRIPTION
                        "OMTP11-PLUS SDH loss of frame alarm trap"
        ::= { omtp11PlusAlarmNotification 83 }

        omtp11PlusSdhRsAlarmIndicationSignalAlarmTrap NOTIFICATION-TYPE
         OBJECTS { omtp11PlusSdhRsAlarmIndicationSignalAlarm }
               STATUS  current
               DESCRIPTION
                        "OMTP11-PLUS SDH rs alarm indication signal alarm trap"
        ::= { omtp11PlusAlarmNotification 84 }

        omtp11PlusSdhRsTraceIdentifierMismatchAlarmTrap NOTIFICATION-TYPE
         OBJECTS { omtp11PlusSdhRsTraceIdentifierMismatchAlarm }
               STATUS  current
               DESCRIPTION
                        "OMTP11-PLUS SDH rs trace identifier mismatch alarm trap"
        ::= { omtp11PlusAlarmNotification 85 }

        omtp11PlusSdhAuAlarmIndicationSignalAlarmTrap NOTIFICATION-TYPE
         OBJECTS { omtp11PlusSdhAuAlarmIndicationSignalAlarm }
               STATUS  current
               DESCRIPTION
                        "OMTP11-PLUS SDH au alarm indication signal alarm trap"
        ::= { omtp11PlusAlarmNotification 86 }

        omtp11PlusSdhAuLossOfPointerAlarmTrap NOTIFICATION-TYPE
         OBJECTS { omtp11PlusSdhAuLossOfPointerAlarm }
               STATUS  current
               DESCRIPTION
                        "OMTP11-PLUS SDH au loss of pointer alarm trap"
        ::= { omtp11PlusAlarmNotification 87 }

        omtp11PlusSdhMsAlarmIndicationSignalAlarmTrap NOTIFICATION-TYPE
         OBJECTS { omtp11PlusSdhMsAlarmIndicationSignalAlarm }
               STATUS  current
               DESCRIPTION
                        "OMTP11-PLUS SDH ms alarm indication signal alarm trap"
        ::= { omtp11PlusAlarmNotification 88 }

        omtp11PlusSdhMsRemoteErrorIndicationAlarmTrap NOTIFICATION-TYPE
         OBJECTS { omtp11PlusSdhMsRemoteErrorIndicationAlarm }
               STATUS  current
               DESCRIPTION
                        "OMTP11-PLUS SDH ms remote error indication alarm trap"
        ::= { omtp11PlusAlarmNotification 89 }

        omtp11PlusSdhMsRemoteDefectIndicationAlarmTrap NOTIFICATION-TYPE
         OBJECTS { omtp11PlusSdhMsRemoteDefectIndicationAlarm }
               STATUS  current
               DESCRIPTION
                        "OMTP11-PLUS SDH ms remote defect indication alarm trap"
        ::= { omtp11PlusAlarmNotification 90 }

        omtp11PlusSdhMsRemoteFailureIndicationAlarmTrap NOTIFICATION-TYPE
         OBJECTS { omtp11PlusSdhMsRemoteFailureIndicationAlarm }
               STATUS  current
               DESCRIPTION
                        "OMTP11-PLUS SDH ms remote failure indication alarm trap"
        ::= { omtp11PlusAlarmNotification 91 }

        omtp11PlusSdhMsB2ExcessiveErrorAlarmTrap NOTIFICATION-TYPE
         OBJECTS { omtp11PlusSdhMsB2ExcessiveErrorAlarm }
               STATUS  current
               DESCRIPTION
                        "OMTP11-PLUS SDH ms b2 signal fail alarm trap"
        ::= { omtp11PlusAlarmNotification 92 }

        omtp11PlusSdhMsB2SignalDegradeAlarmTrap NOTIFICATION-TYPE
         OBJECTS { omtp11PlusSdhMsB2SignalDegradeAlarm }
               STATUS  current
               DESCRIPTION
                        "OMTP11-PLUS SDH ms b2 signal degrade alarm trap"
        ::= { omtp11PlusAlarmNotification 93 }

        omtp11PlusSdhLossOfSequenceSynchronisationAlarmTrap NOTIFICATION-TYPE
         OBJECTS { omtp11PlusSdhLossOfSequenceSynchronisationAlarm }
               STATUS  current
               DESCRIPTION
                        "OMTP11-PLUS SDH loss of sequence synchronisation alarm trap"
        ::= { omtp11PlusAlarmNotification 94 }

 	omtp11PlusSdhHigherOrderPathPayloadLabelMismatchAlarmTrap NOTIFICATION-TYPE
         OBJECTS { omtp11PlusSdhHigherOrderPathPayloadLabelMismatchAlarm }
               STATUS  current
               DESCRIPTION
                        "OMTP11-PLUS SDH higher order Payload Label Mismatch alarm trap"
        ::= { omtp11PlusAlarmNotification 95 }

        omtp11PlusSdhHigherOrderPathUnequippedAlarmTrap NOTIFICATION-TYPE
         OBJECTS { omtp11PlusSdhHigherOrderPathUnequippedAlarm }
               STATUS  current
               DESCRIPTION
                        "OMTP11-PLUS SDH higher order path unequipped alarm trap"
        ::= { omtp11PlusAlarmNotification 96 }

        omtp11PlusWan10gLossOfSignalAlarmTrap NOTIFICATION-TYPE
         OBJECTS { omtp11PlusWan10gLossOfSignalAlarm }
               STATUS  current
               DESCRIPTION
                        "OMTP11-PLUS WAN10G loss of signal alarm trap"
        ::= { omtp11PlusAlarmNotification 101 }

        omtp11PlusWan10gOutOfFrameAlarmTrap NOTIFICATION-TYPE
         OBJECTS { omtp11PlusWan10gOutOfFrameAlarm }
               STATUS  current
               DESCRIPTION
                        "OMTP11-PLUS WAN10G out of frame alarm trap"
        ::= { omtp11PlusAlarmNotification 102 }

        omtp11PlusWan10gLossOfFrameAlarmTrap NOTIFICATION-TYPE
         OBJECTS { omtp11PlusWan10gLossOfFrameAlarm }
               STATUS  current
               DESCRIPTION
                        "OMTP11-PLUS WAN10G loss of frame alarm trap"
        ::= { omtp11PlusAlarmNotification 97 }

        omtp11PlusWan10gRsAlarmIndicationSignalAlarmTrap NOTIFICATION-TYPE
         OBJECTS { omtp11PlusWan10gRsAlarmIndicationSignalAlarm }
               STATUS  current
               DESCRIPTION
                        "OMTP11-PLUS WAN10G rs alarm indication signal alarm trap"
        ::= { omtp11PlusAlarmNotification 103 }

        omtp11PlusWan10gRsTraceIdentifierMismatchAlarmTrap NOTIFICATION-TYPE
         OBJECTS { omtp11PlusWan10gRsTraceIdentifierMismatchAlarm }
               STATUS  current
               DESCRIPTION
                        "OMTP11-PLUS WAN10G rs trace identifier mismatch alarm trap"
        ::= { omtp11PlusAlarmNotification 104 }

        omtp11PlusWan10gAuAlarmIndicationSignalAlarmTrap NOTIFICATION-TYPE
         OBJECTS { omtp11PlusWan10gAuAlarmIndicationSignalAlarm }
               STATUS  current
               DESCRIPTION
                        "OMTP11-PLUS WAN10G au alarm indication signal alarm trap"
        ::= { omtp11PlusAlarmNotification 105 }

        omtp11PlusWan10gAuLossOfPointerAlarmTrap NOTIFICATION-TYPE
         OBJECTS { omtp11PlusWan10gAuLossOfPointerAlarm }
               STATUS  current
               DESCRIPTION
                        "OMTP11-PLUS WAN10G au loss of pointer alarm trap"
        ::= { omtp11PlusAlarmNotification 106 }

        omtp11PlusWan10gMsAlarmIndicationSignalAlarmTrap NOTIFICATION-TYPE
         OBJECTS { omtp11PlusWan10gMsAlarmIndicationSignalAlarm }
               STATUS  current
               DESCRIPTION
                        "OMTP11-PLUS WAN10G ms alarm indication signal alarm trap"
        ::= { omtp11PlusAlarmNotification 107 }

        omtp11PlusWan10gMsRemoteErrorIndicationAlarmTrap NOTIFICATION-TYPE
         OBJECTS { omtp11PlusWan10gMsRemoteErrorIndicationAlarm }
               STATUS  current
               DESCRIPTION
                        "OMTP11-PLUS WAN10G ms remote error indication alarm trap"
        ::= { omtp11PlusAlarmNotification 108 }

        omtp11PlusWan10gMsRemoteDefectIndicationAlarmTrap NOTIFICATION-TYPE
         OBJECTS { omtp11PlusWan10gMsRemoteDefectIndicationAlarm }
               STATUS  current
               DESCRIPTION
                        "OMTP11-PLUS WAN10G ms remote defect indication alarm trap"
        ::= { omtp11PlusAlarmNotification 109 }

        omtp11PlusWan10gMsRemoteFailureIndicationAlarmTrap NOTIFICATION-TYPE
         OBJECTS { omtp11PlusWan10gMsRemoteFailureIndicationAlarm }
               STATUS  current
               DESCRIPTION
                        "OMTP11-PLUS WAN10G ms remote failure indication alarm trap"
        ::= { omtp11PlusAlarmNotification 110 }

        omtp11PlusWan10gMsB2ExcessiveErrorAlarmTrap NOTIFICATION-TYPE
         OBJECTS { omtp11PlusWan10gMsB2ExcessiveErrorAlarm }
               STATUS  current
               DESCRIPTION
                        "OMTP11-PLUS WAN10G ms b2 signal fail alarm trap"
        ::= { omtp11PlusAlarmNotification 111 }

        omtp11PlusWan10gMsB2SignalDegradeAlarmTrap NOTIFICATION-TYPE
         OBJECTS { omtp11PlusWan10gMsB2SignalDegradeAlarm }
               STATUS  current
               DESCRIPTION
                        "OMTP11-PLUS WAN10G ms b2 signal degrade alarm trap"
        ::= { omtp11PlusAlarmNotification 112 }

        omtp11PlusWan10gLossOfSequenceSynchronisationAlarmTrap NOTIFICATION-TYPE
         OBJECTS { omtp11PlusWan10gLossOfSequenceSynchronisationAlarm }
               STATUS  current
               DESCRIPTION
                        "OMTP11-PLUS WAN10G loss of sequence synchronisation alarm trap"
        ::= { omtp11PlusAlarmNotification 113 }

       omtp11PlusWan10gHigherOrderPathPayloadLabelMismatchAlarmTrap NOTIFICATION-TYPE
         OBJECTS { omtp11PlusWan10gHigherOrderPathPayloadLabelMismatchAlarm }
               STATUS  current
               DESCRIPTION
                        "OMTP11-PLUS Wan10g higher order Payload Label Mismatch alarm trap"
        ::= { omtp11PlusAlarmNotification 114 }

        omtp11PlusWan10gHigherOrderPathUnequippedAlarmTrap NOTIFICATION-TYPE
         OBJECTS { omtp11PlusWan10gHigherOrderPathUnequippedAlarm }
               STATUS  current
               DESCRIPTION
                        "OMTP11-PLUS Wan10g higher order path unequipped alarm trap"
        ::= { omtp11PlusAlarmNotification 115 }

        omtp11PlusLan10gLossOfSignalAlarmTrap NOTIFICATION-TYPE
         OBJECTS { omtp11PlusLan10gLossOfSignalAlarm }
               STATUS  current
               DESCRIPTION
                        "OMTP11-PLUS LAN10g loss of signal alarm trap"
        ::= { omtp11PlusAlarmNotification 121 }

        omtp11PlusLan10gLossOfSignalSyncAlarmTrap NOTIFICATION-TYPE
         OBJECTS { omtp11PlusLan10gLossOfSignalSyncAlarm }
               STATUS  current
               DESCRIPTION
                        "OMTP11-PLUS LAN10g loss of signal sync alarm trap"
        ::= { omtp11PlusAlarmNotification 122 }

        omtp11PlusLan10gLinkFailureAlarmTrap NOTIFICATION-TYPE
         OBJECTS { omtp11PlusLan10gLinkFailureAlarm }
               STATUS  current
               DESCRIPTION
                        "OMTP11-PLUS LAN10g link failure alarm trap"
        ::= { omtp11PlusAlarmNotification 123 }

        omtp11PlusLan10gFrameCheckSequenceAlarmTrap NOTIFICATION-TYPE
         OBJECTS { omtp11PlusLan10gFrameCheckSequenceAlarm }
               STATUS  current
               DESCRIPTION
                        "OMTP11-PLUS LAN10g frame check sequence alarm trap"
        ::= { omtp11PlusAlarmNotification 124 }

        omtp11PlusLan10gCarrierStatusAlarmTrap NOTIFICATION-TYPE
         OBJECTS { omtp11PlusLan10gCarrierStatusAlarm }
               STATUS  current
               DESCRIPTION
                        "OMTP11-PLUS LAN10g carrier status alarm trap"
        ::= { omtp11PlusAlarmNotification 125 }

        omtp11PlusLan10gHighBerAlarmTrap NOTIFICATION-TYPE
         OBJECTS { omtp11PlusLan10gHighBerAlarm }
               STATUS  current
               DESCRIPTION
                        "OMTP11-PLUS LAN10g high ber Alarm trap"
        ::= { omtp11PlusAlarmNotification 126 }

        omtp11PlusLan10gLocalFaultAlarmTrap NOTIFICATION-TYPE
         OBJECTS { omtp11PlusLan10gLocalFaultAlarm }
               STATUS  current
               DESCRIPTION
                        "OMTP11-PLUS LAN10g local fault alarm trap"
        ::= { omtp11PlusAlarmNotification 127 }

        omtp11PlusLan10gRemoteFaultAlarmTrap NOTIFICATION-TYPE
         OBJECTS { omtp11PlusLan10gRemoteFaultAlarm }
               STATUS  current
               DESCRIPTION
                        "OMTP11-PLUS LAN10g remote fault alarm trap"
        ::= { omtp11PlusAlarmNotification 128 }

        omtp11PlusFcTransmitDisparityInversionDefectAlarmTrap NOTIFICATION-TYPE
         OBJECTS { omtp11PlusFcTransmitDisparityInversionDefectAlarm }
               STATUS  current
               DESCRIPTION
                        "OMTP11-PLUS FC transmit display invert alarm trap"
        ::= { omtp11PlusAlarmNotification 141 }

        omtp11PlusFcTransmitDigitalLossOfLinkDefectAlarmTrap NOTIFICATION-TYPE
         OBJECTS { omtp11PlusFcTransmitDigitalLossOfLinkDefectAlarm }
               STATUS  current
               DESCRIPTION
                        "OMTP11-PLUS FC transmit dlolb alarm trap"
        ::= { omtp11PlusAlarmNotification 142 }

        omtp11PlusFcTrasnmitLossofSynchronizationDefectAlarmTrap NOTIFICATION-TYPE
         OBJECTS { omtp11PlusFcTrasnmitLossofSynchronizationDefectAlarm }
               STATUS  current
               DESCRIPTION
                        "OMTP11-PLUS FC transmit sync alarm trap"
        ::= { omtp11PlusAlarmNotification 143 }

        omtp11PlusFcReceiveDigitalLossofLinkDefectAlarmTrap NOTIFICATION-TYPE
         OBJECTS { omtp11PlusFcReceiveDigitalLossofLinkDefectAlarm }
               STATUS  current
               DESCRIPTION
                        "OMTP11-PLUS FC receive dlolb alarm trap"
        ::= { omtp11PlusAlarmNotification 144 }

        omtp11PlusFcReceiveLossofSynchronizationDefectAlarmTrap NOTIFICATION-TYPE
         OBJECTS { omtp11PlusFcReceiveLossofSynchronizationDefectAlarm }
               STATUS  current
               DESCRIPTION
                        "OMTP11-PLUS FC receive sync alarm trap"
        ::= { omtp11PlusAlarmNotification 145 }

        omtp11PlusFcReceiveTransitionDetectDefectAlarmTrap NOTIFICATION-TYPE
         OBJECTS { omtp11PlusFcReceiveTransitionDetectDefectAlarm }
               STATUS  current
               DESCRIPTION
                        "OMTP11-PLUS FC receive xdet alarm trap"
        ::= { omtp11PlusAlarmNotification 146 }

        omtp11PlusFcReceiveAnalogLossofSignalDefectAlarmTrap NOTIFICATION-TYPE
         OBJECTS { omtp11PlusFcReceiveAnalogLossofSignalDefectAlarm }
               STATUS  current
               DESCRIPTION
                        "OMTP11-PLUS FC receive asd alarm trap"
        ::= { omtp11PlusAlarmNotification 147 }

        omtp11PlusFcReceiveLineCodeViolationDefectAlarmTrap NOTIFICATION-TYPE
         OBJECTS { omtp11PlusFcReceiveLineCodeViolationDefectAlarm }
               STATUS  current
               DESCRIPTION
                        "OMTP11-PLUS FC receive lcv alarm trap"
        ::= { omtp11PlusAlarmNotification 148 }

        omtp11PlusGfpCsfSignalFailAlarmTrap NOTIFICATION-TYPE
         OBJECTS { omtp11PlusGfpCsfSignalFailAlarm }
               STATUS  current
               DESCRIPTION
                        "OMTP11-PLUS GFP signal failure alarm trap"
        ::= { omtp11PlusAlarmNotification 161 }

        omtp11PlusGfpCsfLinkFailAlarmTrap NOTIFICATION-TYPE
         OBJECTS { omtp11PlusGfpCsfLinkFailAlarm }
               STATUS  current
               DESCRIPTION
                        "OMTP11-PLUS GFP link failure alarm trap"
        ::= { omtp11PlusAlarmNotification 162 }

        omtp11PlusGfpCoreHeaderErrorAlarmTrap NOTIFICATION-TYPE
         OBJECTS { omtp11PlusGfpCoreHeaderErrorAlarm }
               STATUS  current
               DESCRIPTION
                        "OMTP11-PLUS GFP core header error alarm trap"
        ::= { omtp11PlusAlarmNotification 163 }

        omtp11PlusGfpExtentionHeaderErrorAlarmTrap NOTIFICATION-TYPE
         OBJECTS { omtp11PlusGfpExtentionHeaderErrorAlarm }
               STATUS  current
               DESCRIPTION
                        "OMTP11-PLUS GFP extention header error alarm"
        ::= { omtp11PlusAlarmNotification 164 }

             
--*****************************************************************************
--				    ALARM NOTIFICATION
--*****************************************************************************

	snmpCurrentNotificationsGroup NOTIFICATION-GROUP
		NOTIFICATIONS { 
					omtp11PlusXfpInputPowerFailureAlarmTrap,
					omtp11PlusXfpOutputPowerFailureAlarmTrap,
					omtp11PlusXfpHighTemperatureAlarmTrap,
					omtp11PlusXfpLowTemperatureAlarmTrap,
					omtp11PlusXfpHighTemperatureWarningTrap,
					omtp11PlusXfpLowTemperatureWarningTrap,
					omtp11PlusXfpHighBiasCurrentAlarmTrap,
					omtp11PlusXfpLowBiasCurrentAlarmTrap,
					omtp11PlusXfpHighBiasCurrentWarningTrap,
					omtp11PlusXfpLowBiasCurrentWarningTrap,
					omtp11PlusXfpInputHighPowerAlarmTrap,
					omtp11PlusXfpInputLowPowerAlarmTrap,
					omtp11PlusXfpInputHighPowerWarningTrap,
					omtp11PlusXfpInputLowPowerWarningTrap,
					omtp11PlusXfpOutputHighPowerAlarmTrap,
					omtp11PlusXfpOutputLowPowerAlarmTrap,
					omtp11PlusXfpOutputHighPowerWarningTrap,
					omtp11PlusXfpOutputLowPowerWarningTrap,
					omtp11PlusXfpHighSupplyVoltageAlarmTrap,
					omtp11PlusXfpLowSupplyVoltageAlarmTrap,
					omtp11PlusXfpHighSupplyVoltageWarningTrap,
					omtp11PlusXfpLowSupplyVoltageWarningTrap,
					omtp11PlusXfpPresenceAbsenceNotificationTrap,
					omtp11PlusOtuLossOfSignalAlarmTrap,
					omtp11PlusOtuLossOfFrameAlarmTrap,
					omtp11PlusOtuOutOfFrameAlarmTrap,
					omtp11PlusOtuLossOfMultiFrameAlarmTrap,
					omtp11PlusOtuOutOfMultiFrameAlarmTrap,
					omtp11PlusOtuSignalFailAlarmTrap,
					omtp11PlusOtuSignalDegradeAlarmTrap,
					omtp11PlusOtuAlarmIndicationSignalAlarmTrap,
					omtp11PlusOtuIncomingAlignmentErrorAlarmTrap,
					omtp11PlusOtuTraceIdentifierMismatchAlarmTrap,
					omtp11PlusOtuBackwardIncomingAlignmentErrorAlarmTrap,
					omtp11PlusOtuBackwardDefectIndicationAlarmTrap,
					omtp11PlusOduSignalFailAlarmTrap,
					omtp11PlusOduSignalDegradeAlarmTrap,
					omtp11PlusOduAlarmIndicationSignalAlarmTrap,
					omtp11PlusOduTcm1IncomingAlignmentErrorAlarmTrap,
					omtp11PlusOduTcm2IncomingAlignmentErrorAlarmTrap,
					omtp11PlusOduTcm3IncomingAlignmentErrorAlarmTrap,
					omtp11PlusOduTcm4IncomingAlignmentErrorAlarmTrap,
					omtp11PlusOduTcm5IncomingAlignmentErrorAlarmTrap,
					omtp11PlusOduTcm6IncomingAlignmentErrorAlarmTrap,
					omtp11PlusOduTraceIdentifierMismatchAlarmTrap,
					omtp11PlusOduLockedDefectAlarmTrap,
					omtp11PlusOduOpenConnectionIndicationAlarmTrap,
					omtp11PlusOduBackwardDefectIndicationAlarmTrap,
					omtp11PlusOduTcm1BackwardIncomingAlignmentErrorAlarmTrap,
					omtp11PlusOduTcm2BackwardIncomingAlignmentErrorAlarmTrap,
					omtp11PlusOduTcm3BackwardIncomingAlignmentErrorAlarmTrap,
					omtp11PlusOduTcm4BackwardIncomingAlignmentErrorAlarmTrap,
					omtp11PlusOduTcm5BackwardIncomingAlignmentErrorAlarmTrap,
					omtp11PlusOduTcm6BackwardIncomingAlignmentErrorAlarmTrap,
					omtp11PlusOpuPayloadMismatchAlarmTrap,
					omtp11PlusOchLossOfPayloadAlarmTrap,
					omtp11PlusSdhLossOfSignalAlarmTrap,
					omtp11PlusSdhOutOfFrameAlarmTrap,
					omtp11PlusSdhLossOfFrameAlarmTrap,
					omtp11PlusSdhRsAlarmIndicationSignalAlarmTrap,
					omtp11PlusSdhRsTraceIdentifierMismatchAlarmTrap,
					omtp11PlusSdhAuAlarmIndicationSignalAlarmTrap,
					omtp11PlusSdhAuLossOfPointerAlarmTrap,
					omtp11PlusSdhMsAlarmIndicationSignalAlarmTrap,
					omtp11PlusSdhMsRemoteErrorIndicationAlarmTrap,
					omtp11PlusSdhMsRemoteDefectIndicationAlarmTrap,
					omtp11PlusSdhMsRemoteFailureIndicationAlarmTrap,
					omtp11PlusSdhMsB2ExcessiveErrorAlarmTrap,
					omtp11PlusSdhMsB2SignalDegradeAlarmTrap,
					omtp11PlusSdhLossOfSequenceSynchronisationAlarmTrap,
					omtp11PlusSdhHigherOrderPathPayloadLabelMismatchAlarmTrap,
					omtp11PlusSdhHigherOrderPathUnequippedAlarmTrap,
					omtp11PlusWan10gLossOfSignalAlarmTrap,
					omtp11PlusWan10gOutOfFrameAlarmTrap,
					omtp11PlusWan10gLossOfFrameAlarmTrap,
					omtp11PlusWan10gRsAlarmIndicationSignalAlarmTrap,
					omtp11PlusWan10gRsTraceIdentifierMismatchAlarmTrap,
					omtp11PlusWan10gAuAlarmIndicationSignalAlarmTrap,
					omtp11PlusWan10gAuLossOfPointerAlarmTrap,
					omtp11PlusWan10gMsAlarmIndicationSignalAlarmTrap,
					omtp11PlusWan10gMsRemoteErrorIndicationAlarmTrap,
					omtp11PlusWan10gMsRemoteDefectIndicationAlarmTrap,
					omtp11PlusWan10gMsRemoteFailureIndicationAlarmTrap,
					omtp11PlusWan10gMsB2ExcessiveErrorAlarmTrap,
					omtp11PlusWan10gMsB2SignalDegradeAlarmTrap,
					omtp11PlusWan10gLossOfSequenceSynchronisationAlarmTrap,
					omtp11PlusWan10gHigherOrderPathPayloadLabelMismatchAlarmTrap,
					omtp11PlusWan10gHigherOrderPathUnequippedAlarmTrap,
					omtp11PlusLan10gLossOfSignalAlarmTrap,
					omtp11PlusLan10gLossOfSignalSyncAlarmTrap,
					omtp11PlusLan10gLinkFailureAlarmTrap,
					omtp11PlusLan10gFrameCheckSequenceAlarmTrap,
					omtp11PlusLan10gCarrierStatusAlarmTrap,
					omtp11PlusLan10gHighBerAlarmTrap,
					omtp11PlusLan10gLocalFaultAlarmTrap,
					omtp11PlusLan10gRemoteFaultAlarmTrap,
					omtp11PlusFcTransmitDisparityInversionDefectAlarmTrap,
					omtp11PlusFcTransmitDigitalLossOfLinkDefectAlarmTrap,
					omtp11PlusFcTrasnmitLossofSynchronizationDefectAlarmTrap,
					omtp11PlusFcReceiveDigitalLossofLinkDefectAlarmTrap,
					omtp11PlusFcReceiveLossofSynchronizationDefectAlarmTrap,
					omtp11PlusFcReceiveTransitionDetectDefectAlarmTrap,
					omtp11PlusFcReceiveAnalogLossofSignalDefectAlarmTrap,
					omtp11PlusFcReceiveLineCodeViolationDefectAlarmTrap,
					omtp11PlusGfpCsfSignalFailAlarmTrap,
					omtp11PlusGfpCsfLinkFailAlarmTrap,
					omtp11PlusGfpCoreHeaderErrorAlarmTrap,
					omtp11PlusGfpExtentionHeaderErrorAlarmTrap
		}
  	  STATUS current
  	  DESCRIPTION
		"The UTL OMTP11-PLUS current notifications group"
  	  ::= { omtp11Plus 6 }

	snmpcurrentGroup OBJECT-GROUP
		OBJECTS {
				omtp11PlusInterfaceNumber, 
				omtp11PlusEepromCardId,
				omtp11PlusEepromCardName,
				omtp11PlusEepromPartCode,
				omtp11PlusEepromCardSerialNumber,
				omtp11PlusEepromHardwareExternalReleaseVersion,
				omtp11PlusSoftwareExternalReleaseVersion,
				omtp11PlusEepromHardwareInternalReleaseVersion,
				omtp11PlusSoftwareInternalReleaseVersion,
				omtp11PlusEepromCardUidNumber,
				omtp11PlusEepromCardEui48Number,
				omtp11PlusEepromCardEui64Number,
				omtp11PlusCardRootFileSystemVersion,
				omtp11PlusCardInstallationDate,
				omtp11PlusCardCommissionDate,
				omtp11PlusCardRunningTime,
				omtp11PlusCardRestartCount,
				omtp11PlusXfpReadyForOperation,
				omtp11PlusXfpI2cCommunicationStatus,
				omtp11PlusXfpEepromPage,
				omtp11PlusCheckCodeOfXfpEepromPage,
				omtp11PlusExtendedCheckCodeOfXfpEepromPage,
				omtp11PlusXfpVendorName,
				omtp11PlusXfpVendorIeeeId,
				omtp11PlusXfpPartNumber,
				omtp11PlusXfpSerialNumber,
				omtp11PlusXfpRevisionNumber,
				omtp11PlusXfpManufacturingDate,
				omtp11PlusFixedXfpLaserWavelength,
				omtp11PlusXfpLaserWavelengthTolerance,
				omtp11PlusXfpWavelengthTunabilitySupported,
				omtp11PlusTunableXfpLaserWavelengthError,
				omtp11PlusTunableXfpLaserFrequencyError,
				omtp11PlusTunableXfpLaserFirstFrequency,
				omtp11PlusTunableXfpLaserLastFrequency,
				omtp11PlusTunableXfpWavelengthGridSpacing,
				omtp11PlusXfpConnectorType,
				omtp11PlusXfpLinkLength,
				omtp11PlusXfpCdrRateSupported,
				omtp11PlusXfpSignalEncodingTypeSupported,
				omtp11PlusXfpTransceiverCodesSupported,
				omtp11PlusXfpMaximumBitrateSupported,
				omtp11PlusXfpMinimumBitrateSupported,
				omtp11PlusXfpMaximumCaseTemperatureSupported,
				omtp11PlusXfpMaximumPowerDissipationSupported,
				omtp11PlusXfpMaximumPowerDissipationSupportedAtPowerDownMode,
				omtp11PlusXfpMaximumCurrentLimitSupportedAtPlus5vSupply,
				omtp11PlusXfpMaximumCurrentLimitSupportedAtPlus3Point3vSupply,
				omtp11PlusXfpMaximumCurrentLimitSupportedAtPlus1Point8vSupply,
				omtp11PlusXfpMaximumCurrentLimitSupportedAtMinus5Point2vSupply,
				omtp11PlusXfpLineLoopbackSupported,
				omtp11PlusXfpXfiLoopbackSupported,
				omtp11PlusXfpOptionalVpsSupported,
				omtp11PlusXfpLaserDisableThroughI2cSupported,
				omtp11PlusXfpPowerDownThroughI2cSupported,
				omtp11PlusXfpVpsLvRegulatorModeSupported,
				omtp11PlusXfpVpsBypassedRegulatorModeSupported,
				omtp11PlusXfpActiveFecControlSupported,
				omtp11PlusXfpOptionalCmuModeSupported,
				omtp11PlusXfpFecBerSupported,
				omtp11PlusXfpReceivePowerMeasurementIsInOmaOrAverage,
				omtp11PlusXfpActiveWavelengthControlSupported,
				omtp11PlusXfpTransmitterIsCooledOrUncooled,
				omtp11PlusXfpReceiverTypeIsPinOrApd,
				omtp11PlusCardGeneralDetailsTableRowStatus,
				omtp11PlusCardSoftwareUpgrade,
				omtp11PlusCardSignalMonitorState,
				omtp11PlusCardOpticalMonitorState,
				omtp11PlusCardSoftReset,
				omtp11PlusCardFactoryReset,
				omtp11PlusCardAccessStatus,
				omtp11PlusSyncSystemTimeWithNtpServer,
				omtp11PlusSyncRtcWithNtpServer,
				omtp11PlusSyncRtcWithSystemTime,
				omtp11PlusUpdateGivenTimeIntoSystem,
				omtp11PlusUpdateGivenTimeIntoRtc,
				omtp11PlusSystemTimeAndRtcTime,
				omtp11PlusTrafficConfiguration,
				omtp11PlusLoopbackState,
				omtp11PlusPortSignalMonitorState,
				omtp11PlusPortOpticalMonitorState,
				omtp11PlusClearSignalPerformance,
				omtp11PlusAlsState,
				omtp11PlusAlsPulseRepetitionTime,
				omtp11PlusOtuFecConfiguration,
				omtp11PlusOtuSignalFailThreshold,
				omtp11PlusOtuSignalDegradeThreshold,
				omtp11PlusOtuAlarmIndicationSignalAlarmInsertion,
				omtp11PlusOtuSapiTransmitTraceMessage,
				omtp11PlusOtuDapiTransmitTraceMessage,
				omtp11PlusOtuOperatorSpecificTransmitTraceMessage,
				omtp11PlusOtuSapiExpectedTraceMessage,
				omtp11PlusOtuDapiExpectedTraceMessage,
				omtp11PlusOtuOperatorSpecificExpectedTraceMessage,
				omtp11PlusOtuSapiReceivedTraceMessage,
				omtp11PlusOtuDapiReceivedTraceMessage,
				omtp11PlusOtuOperatorSpecificReceivedTraceMessage,
				omtp11PlusOduSignalFailThreshold,
				omtp11PlusOduSignalDegradeThreshold,
				omtp11PlusOduAlarmIndicationSignalAlarmInsertion,
				omtp11PlusOduLockedDefectAlarmInsertion,
				omtp11PlusOduOpenConnectionIndicationAlarmInsertion,
				omtp11PlusOduSapiTransmitTraceMessage,
				omtp11PlusOduDapiTransmitTraceMessage,
				omtp11PlusOduOperatorSpecificTransmitTraceMessage,
				omtp11PlusOduSapiExpectedTraceMessage,
				omtp11PlusOduDapiExpectedTraceMessage,
				omtp11PlusOduOperatorSpecificExpectedTraceMessage,
				omtp11PlusOduSapiReceivedTraceMessage,
				omtp11PlusOduDapiReceivedTraceMessage,
				omtp11PlusOduOperatorSpecificReceivedTraceMessage,
				omtp11PlusOpuTransmitPayloadType,
				omtp11PlusOpuReceivedPayloadType,
				omtp11PlusSdhMsB2ExcessiveErrorThreshold,
				omtp11PlusSdhMsB2SignalDegradeThreshold,
				omtp11PlusWan10gMsB2ExcessiveErrorThreshold,
				omtp11PlusWan10gMsB2SignalDegradeThreshold,
				omtp11PlusTunableXfpLaserWavelength,
				omtp11PlusTunableXfpLaserChannelNumber,
				omtp11PlusXfpLaserState,
				omtp11PlusXfpReset,
				omtp11PlusXfpPowerDownMode,
				omtp11PlusXfpLineLoopback,
				omtp11PlusXfpXfiLoopback,
				omtp11PlusXfpAmplitudeThresholdOfReceiverForFecControl,
				omtp11PlusXfpPhaseInEyeDiagramForFecControl,
				omtp11PlusXfpSystemReportingBer,
				omtp11PlusXfpHighTemperatureAlarmThreshold,
				omtp11PlusXfpLowTemperatureAlarmThreshold,
				omtp11PlusXfpHighTemperatureWarningThreshold,
				omtp11PlusXfpLowTemperatureWarningThreshold,
				omtp11PlusXfpHighBiasCurrentAlarmThreshold,
				omtp11PlusXfpLowBiasCurrentAlarmThreshold,
				omtp11PlusXfpHighBiasCurrentWarningThreshold,
				omtp11PlusXfpLowBiasCurrentWarningThreshold,
				omtp11PlusXfpInputHighPowerAlarmThreshold,
				omtp11PlusXfpInputLowPowerAlarmThreshold,
				omtp11PlusXfpInputHighPowerWarningThreshold,
				omtp11PlusXfpInputLowPowerWarningThreshold,
				omtp11PlusXfpOutputHighPowerAlarmThreshold,
				omtp11PlusXfpOutputLowPowerAlarmThreshold,
				omtp11PlusXfpOutputHighPowerWarningThreshold,
				omtp11PlusXfpOutputLowPowerWarningThreshold,
				omtp11PlusXfpHighSupplyVoltageAlarmThreshold,
				omtp11PlusXfpLowSupplyVoltageAlarmThreshold,
				omtp11PlusXfpHighSupplyVoltageWarningThreshold,
				omtp11PlusXfpLowSupplyVoltageWarningThreshold,
				omtp11PlusXfpInputPowerFailureAlarmInhibit,
				omtp11PlusXfpOutputPowerFailureAlarmInhibit,
				omtp11PlusXfpHighTemperatureAlarmInhibit,
				omtp11PlusXfpLowTemperatureAlarmInhibit,
				omtp11PlusXfpHighTemperatureWarningInhibit,
				omtp11PlusXfpLowTemperatureWarningInhibit,
				omtp11PlusXfpHighBiasCurrentAlarmInhibit,
				omtp11PlusXfpLowBiasCurrentAlarmInhibit,
				omtp11PlusXfpHighBiasCurrentWarningInhibit,
				omtp11PlusXfpLowBiasCurrentWarningInhibit,
				omtp11PlusXfpInputHighPowerAlarmInhibit,
				omtp11PlusXfpInputLowPowerAlarmInhibit,
				omtp11PlusXfpInputHighPowerWarningInhibit,
				omtp11PlusXfpInputLowPowerWarningInhibit,
				omtp11PlusXfpOutputHighPowerAlarmInhibit,
				omtp11PlusXfpOutputLowPowerAlarmInhibit,
				omtp11PlusXfpOutputHighPowerWarningInhibit,
				omtp11PlusXfpOutputLowPowerWarningInhibit,
				omtp11PlusXfpHighSupplyVoltageAlarmInhibit,
				omtp11PlusXfpLowSupplyVoltageAlarmInhibit,
				omtp11PlusXfpHighSupplyVoltageWarningInhibit,
				omtp11PlusXfpLowSupplyVoltageWarningInhibit,
				omtp11PlusXfpPresenceAbsenceNotificationInhibit,
				omtp11PlusOtuLossOfSignalAlarmInhibit,
				omtp11PlusOtuLossOfFrameAlarmInhibit,
				omtp11PlusOtuOutOfFrameAlarmInhibit,
				omtp11PlusOtuLossOfMultiFrameAlarmInhibit,
				omtp11PlusOtuOutOfMultiFrameAlarmInhibit,
				omtp11PlusOtuSignalFailAlarmInhibit,
				omtp11PlusOtuSignalDegradeAlarmInhibit,
				omtp11PlusOtuAlarmIndicationSignalAlarmInhibit,
				omtp11PlusOtuIncomingAlignmentErrorAlarmInhibit,
				omtp11PlusOtuTraceIdentifierMismatchAlarmInhibit,
				omtp11PlusOtuBackwardIncomingAlignmentErrorAlarmInhibit,
				omtp11PlusOtuBackwardDefectIndicationAlarmInhibit,
				omtp11PlusOduSignalFailAlarmInhibit,
				omtp11PlusOduSignalDegradeAlarmInhibit,
				omtp11PlusOduAlarmIndicationSignalAlarmInhibit,
				omtp11PlusOduTcm1IncomingAlignmentErrorAlarmInhibit,
				omtp11PlusOduTcm2IncomingAlignmentErrorAlarmInhibit,
				omtp11PlusOduTcm3IncomingAlignmentErrorAlarmInhibit,
				omtp11PlusOduTcm4IncomingAlignmentErrorAlarmInhibit,
				omtp11PlusOduTcm5IncomingAlignmentErrorAlarmInhibit,
				omtp11PlusOduTcm6IncomingAlignmentErrorAlarmInhibit,
				omtp11PlusOduTraceIdentifierMismatchAlarmInhibit,
				omtp11PlusOduLockedDefectAlarmInhibit,
				omtp11PlusOduOpenConnectionIndicationAlarmInhibit,
				omtp11PlusOduBackwardDefectIndicationAlarmInhibit,
				omtp11PlusOduTcm1BackwardIncomingAlignmentErrorAlarmInhibit,
				omtp11PlusOduTcm2BackwardIncomingAlignmentErrorAlarmInhibit,
				omtp11PlusOduTcm3BackwardIncomingAlignmentErrorAlarmInhibit,
				omtp11PlusOduTcm4BackwardIncomingAlignmentErrorAlarmInhibit,
				omtp11PlusOduTcm5BackwardIncomingAlignmentErrorAlarmInhibit,
				omtp11PlusOduTcm6BackwardIncomingAlignmentErrorAlarmInhibit,
				omtp11PlusOpuPayloadMismatchAlarmInhibit,
				omtp11PlusOchLossOfPayloadAlarmInhibit,
				omtp11PlusSdhLossOfSignalAlarmInhibit,
				omtp11PlusSdhOutOfFrameAlarmInhibit,
				omtp11PlusSdhLossOfFrameAlarmInhibit,
				omtp11PlusSdhRsAlarmIndicationSignalAlarmInhibit,
				omtp11PlusSdhRsTraceIdentifierMismatchAlarmInhibit,
				omtp11PlusSdhAuAlarmIndicationSignalAlarmInhibit,
				omtp11PlusSdhAuLossOfPointerAlarmInhibit,
				omtp11PlusSdhMsAlarmIndicationSignalAlarmInhibit,
				omtp11PlusSdhMsRemoteErrorIndicationAlarmInhibit,
				omtp11PlusSdhMsRemoteDefectIndicationAlarmInhibit,
				omtp11PlusSdhMsRemoteFailureIndicationAlarmInhibit,
				omtp11PlusSdhMsB2ExcessiveErrorAlarmInhibit,
				omtp11PlusSdhMsB2SignalDegradeAlarmInhibit,
				omtp11PlusSdhLossOfSequenceSynchronisationAlarmInhibit,
				omtp11PlusSdhHigherOrderPathPayloadLabelMismatchAlarmInhibit,
				omtp11PlusSdhHigherOrderPathUnequippedAlarmInhibit,
				omtp11PlusWan10gLossOfSignalAlarmInhibit,
				omtp11PlusWan10gOutOfFrameAlarmInhibit,
				omtp11PlusWan10gLossOfFrameAlarmInhibit,
				omtp11PlusWan10gRsAlarmIndicationSignalAlarmInhibit,
				omtp11PlusWan10gRsTraceIdentifierMismatchAlarmInhibit,
				omtp11PlusWan10gAuAlarmIndicationSignalAlarmInhibit,
				omtp11PlusWan10gAuLossOfPointerAlarmInhibit,
				omtp11PlusWan10gMsAlarmIndicationSignalAlarmInhibit,
				omtp11PlusWan10gMsRemoteErrorIndicationAlarmInhibit,
				omtp11PlusWan10gMsRemoteDefectIndicationAlarmInhibit,
				omtp11PlusWan10gMsRemoteFailureIndicationAlarmInhibit,
				omtp11PlusWan10gMsB2ExcessiveErrorAlarmInhibit,
				omtp11PlusWan10gMsB2SignalDegradeAlarmInhibit,
				omtp11PlusWan10gLossOfSequenceSynchronisationAlarmInhibit,
				omtp11PlusWan10gHigherOrderPathPayloadLabelMismatchAlarmInhibit,
				omtp11PlusWan10gHigherOrderPathUnequippedAlarmInhibit,
				omtp11PlusLan10gLossOfSignalAlarmInhibit,
				omtp11PlusLan10gLossOfSignalSyncAlarmInhibit,
				omtp11PlusLan10gLinkFailureAlarmInhibit,
				omtp11PlusLan10gFrameCheckSequenceAlarmInhibit,
				omtp11PlusLan10gCarrierStatusAlarmInhibit,
				omtp11PlusLan10gHighBerAlarmInhibit,
				omtp11PlusLan10gLocalFaultAlarmInhibit,
				omtp11PlusLan10gRemoteFaultAlarmInhibit,
				omtp11PlusFcTransmitDisparityInversionDefectAlarmInhibit,
				omtp11PlusFcTransmitDigitalLossOfLinkDefectAlarmInhibit,
				omtp11PlusFcTrasnmitLossofSynchronizationDefectAlarmInhibit,
				omtp11PlusFcReceiveDigitalLossofLinkDefectAlarmInhibit,
				omtp11PlusFcReceiveLossofSynchronizationDefectAlarmInhibit,
				omtp11PlusFcReceiveTransitionDetectDefectAlarmInhibit,
				omtp11PlusFcReceiveAnalogLossofSignalDefectAlarmInhibit,
				omtp11PlusFcReceiveLineCodeViolationDefectAlarmInhibit,
				omtp11PlusGfpCsfSignalFailAlarmInhibit,
				omtp11PlusGfpCsfLinkFailAlarmInhibit,
				omtp11PlusGfpCoreHeaderErrorAlarmInhibit,
				omtp11PlusGfpExtentionHeaderErrorAlarmInhibit,
				omtp11PlusXfpInputPowerFailureAlarmSeverity,
				omtp11PlusXfpOutputPowerFailureAlarmSeverity,
				omtp11PlusXfpHighTemperatureAlarmSeverity,
				omtp11PlusXfpLowTemperatureAlarmSeverity,
				omtp11PlusXfpHighTemperatureWarningSeverity,
				omtp11PlusXfpLowTemperatureWarningSeverity,
				omtp11PlusXfpHighBiasCurrentAlarmSeverity,
				omtp11PlusXfpLowBiasCurrentAlarmSeverity,
				omtp11PlusXfpHighBiasCurrentWarningSeverity,
				omtp11PlusXfpLowBiasCurrentWarningSeverity,
				omtp11PlusXfpInputHighPowerAlarmSeverity,
				omtp11PlusXfpInputLowPowerAlarmSeverity,
				omtp11PlusXfpInputHighPowerWarningSeverity,
				omtp11PlusXfpInputLowPowerWarningSeverity,
				omtp11PlusXfpOutputHighPowerAlarmSeverity,
				omtp11PlusXfpOutputLowPowerAlarmSeverity,
				omtp11PlusXfpOutputHighPowerWarningSeverity,
				omtp11PlusXfpOutputLowPowerWarningSeverity,
				omtp11PlusXfpHighSupplyVoltageAlarmSeverity,
				omtp11PlusXfpLowSupplyVoltageAlarmSeverity,
				omtp11PlusXfpHighSupplyVoltageWarningSeverity,
				omtp11PlusXfpLowSupplyVoltageWarningSeverity,
				omtp11PlusXfpPresenceAbsenceNotificationSeverity,
				omtp11PlusOtuLossOfSignalAlarmSeverity,
				omtp11PlusOtuLossOfFrameAlarmSeverity,
				omtp11PlusOtuOutOfFrameAlarmSeverity,
				omtp11PlusOtuLossOfMultiFrameAlarmSeverity,
				omtp11PlusOtuOutOfMultiFrameAlarmSeverity,
				omtp11PlusOtuSignalFailAlarmSeverity,
				omtp11PlusOtuSignalDegradeAlarmSeverity,
				omtp11PlusOtuAlarmIndicationSignalAlarmSeverity,
				omtp11PlusOtuIncomingAlignmentErrorAlarmSeverity,
				omtp11PlusOtuTraceIdentifierMismatchAlarmSeverity,
				omtp11PlusOtuBackwardIncomingAlignmentErrorAlarmSeverity,
				omtp11PlusOtuBackwardDefectIndicationAlarmSeverity,
				omtp11PlusOduSignalFailAlarmSeverity,
				omtp11PlusOduSignalDegradeAlarmSeverity,
				omtp11PlusOduAlarmIndicationSignalAlarmSeverity,
				omtp11PlusOduTcm1IncomingAlignmentErrorAlarmSeverity,
				omtp11PlusOduTcm2IncomingAlignmentErrorAlarmSeverity,
				omtp11PlusOduTcm3IncomingAlignmentErrorAlarmSeverity,
				omtp11PlusOduTcm4IncomingAlignmentErrorAlarmSeverity,
				omtp11PlusOduTcm5IncomingAlignmentErrorAlarmSeverity,
				omtp11PlusOduTcm6IncomingAlignmentErrorAlarmSeverity,
				omtp11PlusOduTraceIdentifierMismatchAlarmSeverity,
				omtp11PlusOduLockedDefectAlarmSeverity,
				omtp11PlusOduOpenConnectionIndicationAlarmSeverity,
				omtp11PlusOduBackwardDefectIndicationAlarmSeverity,
				omtp11PlusOduTcm1BackwardIncomingAlignmentErrorAlarmSeverity,
				omtp11PlusOduTcm2BackwardIncomingAlignmentErrorAlarmSeverity,
				omtp11PlusOduTcm3BackwardIncomingAlignmentErrorAlarmSeverity,
				omtp11PlusOduTcm4BackwardIncomingAlignmentErrorAlarmSeverity,
				omtp11PlusOduTcm5BackwardIncomingAlignmentErrorAlarmSeverity,
				omtp11PlusOduTcm6BackwardIncomingAlignmentErrorAlarmSeverity,
				omtp11PlusOpuPayloadMismatchAlarmSeverity,
				omtp11PlusOchLossOfPayloadAlarmSeverity,
				omtp11PlusSdhLossOfSignalAlarmSeverity,
				omtp11PlusSdhOutOfFrameAlarmSeverity,
				omtp11PlusSdhLossOfFrameAlarmSeverity,
				omtp11PlusSdhRsAlarmIndicationSignalAlarmSeverity,
				omtp11PlusSdhRsTraceIdentifierMismatchAlarmSeverity,
				omtp11PlusSdhAuAlarmIndicationSignalAlarmSeverity,
				omtp11PlusSdhAuLossOfPointerAlarmSeverity,
				omtp11PlusSdhMsAlarmIndicationSignalAlarmSeverity,
				omtp11PlusSdhMsRemoteErrorIndicationAlarmSeverity,
				omtp11PlusSdhMsRemoteDefectIndicationAlarmSeverity,
				omtp11PlusSdhMsRemoteFailureIndicationAlarmSeverity,
				omtp11PlusSdhMsB2ExcessiveErrorAlarmSeverity,
				omtp11PlusSdhMsB2SignalDegradeAlarmSeverity,
				omtp11PlusSdhLossOfSequenceSynchronisationAlarmSeverity,
				omtp11PlusSdhHigherOrderPathPayloadLabelMismatchAlarmSeverity,
				omtp11PlusSdhHigherOrderPathUnequippedAlarmSeverity,
				omtp11PlusWan10gLossOfSignalAlarmSeverity,
				omtp11PlusWan10gOutOfFrameAlarmSeverity,
				omtp11PlusWan10gLossOfFrameAlarmSeverity,
				omtp11PlusWan10gRsAlarmIndicationSignalAlarmSeverity,
				omtp11PlusWan10gRsTraceIdentifierMismatchAlarmSeverity,
				omtp11PlusWan10gAuAlarmIndicationSignalAlarmSeverity,
				omtp11PlusWan10gAuLossOfPointerAlarmSeverity,
				omtp11PlusWan10gMsAlarmIndicationSignalAlarmSeverity,
				omtp11PlusWan10gMsRemoteErrorIndicationAlarmSeverity,
				omtp11PlusWan10gMsRemoteDefectIndicationAlarmSeverity,
				omtp11PlusWan10gMsRemoteFailureIndicationAlarmSeverity,
				omtp11PlusWan10gMsB2ExcessiveErrorAlarmSeverity,
				omtp11PlusWan10gMsB2SignalDegradeAlarmSeverity,
				omtp11PlusWan10gLossOfSequenceSynchronisationAlarmSeverity,
				omtp11PlusWan10gHigherOrderPathPayloadLabelMismatchAlarmSeverity,
				omtp11PlusWan10gHigherOrderPathUnequippedAlarmSeverity,
				omtp11PlusLan10gLossOfSignalAlarmSeverity,
				omtp11PlusLan10gLossOfSignalSyncAlarmSeverity,
				omtp11PlusLan10gLinkFailureAlarmSeverity,
				omtp11PlusLan10gFrameCheckSequenceAlarmSeverity,
				omtp11PlusLan10gCarrierStatusAlarmSeverity,
				omtp11PlusLan10gHighBerAlarmSeverity,
				omtp11PlusLan10gLocalFaultAlarmSeverity,
				omtp11PlusLan10gRemoteFaultAlarmSeverity,
				omtp11PlusFcTransmitDisparityInversionDefectAlarmSeverity,
				omtp11PlusFcTransmitDigitalLossOfLinkDefectAlarmSeverity,
				omtp11PlusFcTrasnmitLossofSynchronizationDefectAlarmSeverity,
				omtp11PlusFcReceiveDigitalLossofLinkDefectAlarmSeverity,
				omtp11PlusFcReceiveLossofSynchronizationDefectAlarmSeverity,
				omtp11PlusFcReceiveTransitionDetectDefectAlarmSeverity,
				omtp11PlusFcReceiveAnalogLossofSignalDefectAlarmSeverity,
				omtp11PlusFcReceiveLineCodeViolationDefectAlarmSeverity,
				omtp11PlusGfpCsfSignalFailAlarmSeverity,
				omtp11PlusGfpCsfLinkFailAlarmSeverity,
				omtp11PlusGfpCoreHeaderErrorAlarmSeverity,
				omtp11PlusGfpExtentionHeaderErrorAlarmSeverity,
				omtp11PlusConfigurationTableRowStatus,
				omtp11PlusXfpInputPowerFailureAlarm,
				omtp11PlusXfpOutputPowerFailureAlarm,
				omtp11PlusXfpHighTemperatureAlarm,
				omtp11PlusXfpLowTemperatureAlarm,
				omtp11PlusXfpHighTemperatureWarning,
				omtp11PlusXfpLowTemperatureWarning,
				omtp11PlusXfpHighBiasCurrentAlarm,
				omtp11PlusXfpLowBiasCurrentAlarm,
				omtp11PlusXfpHighBiasCurrentWarning,
				omtp11PlusXfpLowBiasCurrentWarning,
				omtp11PlusXfpInputHighPowerAlarm,
				omtp11PlusXfpInputLowPowerAlarm,
				omtp11PlusXfpInputHighPowerWarning,
				omtp11PlusXfpInputLowPowerWarning,
				omtp11PlusXfpOutputHighPowerAlarm,
				omtp11PlusXfpOutputLowPowerAlarm,
				omtp11PlusXfpOutputHighPowerWarning,
				omtp11PlusXfpOutputLowPowerWarning,
				omtp11PlusXfpHighSupplyVoltageAlarm,
				omtp11PlusXfpLowSupplyVoltageAlarm,
				omtp11PlusXfpHighSupplyVoltageWarning,
				omtp11PlusXfpLowSupplyVoltageWarning,
				omtp11PlusXfpPresenceAbsenceNotification,
				omtp11PlusOtuLossOfSignalAlarm,
				omtp11PlusOtuLossOfFrameAlarm,
				omtp11PlusOtuOutOfFrameAlarm,
				omtp11PlusOtuLossOfMultiFrameAlarm,
				omtp11PlusOtuOutOfMultiFrameAlarm,
				omtp11PlusOtuSignalFailAlarm,
				omtp11PlusOtuSignalDegradeAlarm,
				omtp11PlusOtuAlarmIndicationSignalAlarm,
				omtp11PlusOtuIncomingAlignmentErrorAlarm,
				omtp11PlusOtuTraceIdentifierMismatchAlarm,
				omtp11PlusOtuBackwardIncomingAlignmentErrorAlarm,
				omtp11PlusOtuBackwardDefectIndicationAlarm,
				omtp11PlusOduSignalFailAlarm,
				omtp11PlusOduSignalDegradeAlarm,
				omtp11PlusOduAlarmIndicationSignalAlarm,
				omtp11PlusOduTcm1IncomingAlignmentErrorAlarm,
				omtp11PlusOduTcm2IncomingAlignmentErrorAlarm,
				omtp11PlusOduTcm3IncomingAlignmentErrorAlarm,
				omtp11PlusOduTcm4IncomingAlignmentErrorAlarm,
				omtp11PlusOduTcm5IncomingAlignmentErrorAlarm,
				omtp11PlusOduTcm6IncomingAlignmentErrorAlarm,
				omtp11PlusOduTraceIdentifierMismatchAlarm,
				omtp11PlusOduLockedDefectAlarm,
				omtp11PlusOduOpenConnectionIndicationAlarm,
				omtp11PlusOduBackwardDefectIndicationAlarm,
				omtp11PlusOduTcm1BackwardIncomingAlignmentErrorAlarm,
				omtp11PlusOduTcm2BackwardIncomingAlignmentErrorAlarm,
				omtp11PlusOduTcm3BackwardIncomingAlignmentErrorAlarm,
				omtp11PlusOduTcm4BackwardIncomingAlignmentErrorAlarm,
				omtp11PlusOduTcm5BackwardIncomingAlignmentErrorAlarm,
				omtp11PlusOduTcm6BackwardIncomingAlignmentErrorAlarm,
				omtp11PlusOpuPayloadMismatchAlarm,
				omtp11PlusOchLossOfPayloadAlarm,
				omtp11PlusSdhLossOfSignalAlarm,
				omtp11PlusSdhOutOfFrameAlarm,
				omtp11PlusSdhLossOfFrameAlarm,
				omtp11PlusSdhRsAlarmIndicationSignalAlarm,
				omtp11PlusSdhRsTraceIdentifierMismatchAlarm,
				omtp11PlusSdhAuAlarmIndicationSignalAlarm,
				omtp11PlusSdhAuLossOfPointerAlarm,
				omtp11PlusSdhMsAlarmIndicationSignalAlarm,
				omtp11PlusSdhMsRemoteErrorIndicationAlarm,
				omtp11PlusSdhMsRemoteDefectIndicationAlarm,
				omtp11PlusSdhMsRemoteFailureIndicationAlarm,
				omtp11PlusSdhMsB2ExcessiveErrorAlarm,
				omtp11PlusSdhMsB2SignalDegradeAlarm,
				omtp11PlusSdhLossOfSequenceSynchronisationAlarm,
				omtp11PlusSdhHigherOrderPathPayloadLabelMismatchAlarm,
				omtp11PlusSdhHigherOrderPathUnequippedAlarm,
				omtp11PlusWan10gLossOfSignalAlarm,
				omtp11PlusWan10gOutOfFrameAlarm,
				omtp11PlusWan10gLossOfFrameAlarm,
				omtp11PlusWan10gRsAlarmIndicationSignalAlarm,
				omtp11PlusWan10gRsTraceIdentifierMismatchAlarm,
				omtp11PlusWan10gAuAlarmIndicationSignalAlarm,
				omtp11PlusWan10gAuLossOfPointerAlarm,
				omtp11PlusWan10gMsAlarmIndicationSignalAlarm,
				omtp11PlusWan10gMsRemoteErrorIndicationAlarm,
				omtp11PlusWan10gMsRemoteDefectIndicationAlarm,
				omtp11PlusWan10gMsRemoteFailureIndicationAlarm,
				omtp11PlusWan10gMsB2ExcessiveErrorAlarm,
				omtp11PlusWan10gMsB2SignalDegradeAlarm,
				omtp11PlusWan10gLossOfSequenceSynchronisationAlarm,
				omtp11PlusWan10gHigherOrderPathPayloadLabelMismatchAlarm,
				omtp11PlusWan10gHigherOrderPathUnequippedAlarm,
				omtp11PlusLan10gLossOfSignalAlarm,
				omtp11PlusLan10gLossOfSignalSyncAlarm,
				omtp11PlusLan10gLinkFailureAlarm,
				omtp11PlusLan10gFrameCheckSequenceAlarm,
				omtp11PlusLan10gCarrierStatusAlarm,
				omtp11PlusLan10gHighBerAlarm,
				omtp11PlusLan10gLocalFaultAlarm,
				omtp11PlusLan10gRemoteFaultAlarm,
				omtp11PlusFcTransmitDisparityInversionDefectAlarm,
				omtp11PlusFcTransmitDigitalLossOfLinkDefectAlarm,
				omtp11PlusFcTrasnmitLossofSynchronizationDefectAlarm,
				omtp11PlusFcReceiveDigitalLossofLinkDefectAlarm,
				omtp11PlusFcReceiveLossofSynchronizationDefectAlarm,
				omtp11PlusFcReceiveTransitionDetectDefectAlarm,
				omtp11PlusFcReceiveAnalogLossofSignalDefectAlarm,
				omtp11PlusFcReceiveLineCodeViolationDefectAlarm,
				omtp11PlusGfpCsfSignalFailAlarm,
				omtp11PlusGfpCsfLinkFailAlarm,
				omtp11PlusGfpCoreHeaderErrorAlarm,
				omtp11PlusGfpExtentionHeaderErrorAlarm,
				omtp11PlusAlarmQueryTableRowStatus,
				omtp11PlusXfpInputPower,
				omtp11PlusXfpOutputPower,
				omtp11PlusXfpBiasCurrent,
				omtp11PlusXfpSupplyVoltage,
				omtp11PlusXfpTemperature,
				omtp11PlusOtnFecUncorrectedWords,
				omtp11PlusOtnFecCorrectedBits,
				omtp11PlusOtnFecZerosCorrectedBits,
				omtp11PlusOtnFecOnesCorrectedBits,
				omtp11PlusOtuBitInterleavedParityErrors,
				omtp11PlusOtuIncomingAlignmentErrorSeconds,
				omtp11PlusOtuBackwardErrorIndicationErrorCount,
				omtp11PlusOtuBackwardIncomingAlignmentErrorSeconds,
				omtp11PlusOtuErrorFreeSeconds,
				omtp11PlusOtuErrorSeconds,
				omtp11PlusOtuBackgroundBlockErrors,
				omtp11PlusOtuSevereErrorSeconds,
				omtp11PlusOtuUnavailableSeconds,
				omtp11PlusOtuBackgroundBlockErrorRatio,
				omtp11PlusOtuSevereErrorSecondsErrorRatio,
				omtp11PlusOtuFarEndErrorFreeSeconds,
				omtp11PlusOtuFarEndErrorSeconds,
				omtp11PlusOtuFarEndBackgroundBlockErrors,
				omtp11PlusOtuFarEndSevereErrorSeconds,
				omtp11PlusOtuFarEndUnavailableSeconds,
				omtp11PlusOtuFarEndBackgroundBlockErrorRatio,
				omtp11PlusOtuFarEndSevereErrorSecondsErrorRatio,
				omtp11PlusOtuErrorRatio,
				omtp11PlusOtuBitErrorRate,
				omtp11PlusOtuFramesReceived,
				omtp11PlusOduBitInterleavedParityErrors,
				omtp11PlusOduTcm1BitInterleavedParityErrors,
				omtp11PlusOduTcm2BitInterleavedParityErrors,
				omtp11PlusOduTcm3BitInterleavedParityErrors,
				omtp11PlusOduTcm4BitInterleavedParityErrors,
				omtp11PlusOduTcm5BitInterleavedParityErrors,
				omtp11PlusOduTcm6BitInterleavedParityErrors,
				omtp11PlusOduTcm1IncomingAlignmentErrorSeconds,
				omtp11PlusOduBackwardErrorIndicationErrorCount,
				omtp11PlusOduTcm1BackwardErrorIndicationErrorCount,
				omtp11PlusOduTcm2BackwardErrorIndicationErrorCount,
				omtp11PlusOduTcm3BackwardErrorIndicationErrorCount,
				omtp11PlusOduTcm4BackwardErrorIndicationErrorCount,
				omtp11PlusOduTcm5BackwardErrorIndicationErrorCount,
				omtp11PlusOduTcm6BackwardErrorIndicationErrorCount,
				omtp11PlusOduTcm1BackwardIncomingAlignmentErrorSeconds,
				omtp11PlusOduDelayMeasurement,
				omtp11PlusOduErrorFreeSeconds,
				omtp11PlusOduErrorSeconds,
				omtp11PlusOduBackgroundBlockErrors,
				omtp11PlusOduSevereErrorSeconds,
				omtp11PlusOduUnavailableSeconds,
				omtp11PlusOduBackgroundBlockErrorRatio,
				omtp11PlusOduSevereErrorSecondsErrorRatio,
				omtp11PlusOduFarEndErrorFreeSeconds,
				omtp11PlusOduFarEndErrorSeconds,
				omtp11PlusOduFarEndBackgroundBlockErrors,
				omtp11PlusOduFarEndSevereErrorSeconds,
				omtp11PlusOduFarEndUnavailableSeconds,
				omtp11PlusOduFarEndBackgroundBlockErrorRatio,
				omtp11PlusOduFarEndSevereErrorSecondsErrorRatio,
				omtp11PlusSdhRsB1BitInterleavedParityErrors,
				omtp11PlusSdhMsB2BitInterleavedParityErrors,
				omtp11PlusSdhMsB3BitInterleavedParityErrors,
				omtp11PlusSdhMsRemoteErrorIndicationErrorCount,
				omtp11PlusSdhMsRemoteDefectIndicationErrorCount,
				omtp11PlusSdhErrorFreeSeconds,
				omtp11PlusSdhErrorSeconds,
				omtp11PlusSdhBackgroundBlockErrors,
				omtp11PlusSdhSevereErrorSeconds,
				omtp11PlusSdhUnavailableSeconds,
				omtp11PlusSdhErrorSecondsErrorRatio,
				omtp11PlusSdhBackgroundBlockErrorRatio,
				omtp11PlusSdhSevereErrorSecondsErrorRatio,
				omtp11PlusWan10gRsB1BitInterleavedParityErrors,
				omtp11PlusWan10gMsB2BitInterleavedParityErrors,
				omtp11PlusWan10gMsB3BitInterleavedParityErrors,
				omtp11PlusWan10gMsRemoteErrorIndicationErrorCount,
				omtp11PlusWan10gMsRemoteDefectIndicationErrorCount,
				omtp11PlusWan10gErrorFreeSeconds,
				omtp11PlusWan10gErrorSeconds,
				omtp11PlusWan10gBackgroundBlockErrors,
				omtp11PlusWan10gSevereErrorSeconds,
				omtp11PlusWan10gUnavailableSeconds,
				omtp11PlusWan10gErrorSecondsErrorRatio,
				omtp11PlusWan10gBackgroundBlockErrorRatio,
				omtp11PlusWan10gSevereErrorSecondsErrorRatio,
				omtp11PlusLan10gMacTerminatedFramesTransmitted,
				omtp11PlusLan10gMacTerminatedFramesReceived,
				omtp11PlusLan10gMacTerminatedPauseFramesTransmitted,
				omtp11PlusLan10gMacTerminatedPauseFramesReceived,
				omtp11PlusLan10gMacTerminatedUnicastFramesTransmitted,
				omtp11PlusLan10gMacTerminatedUnicastFramesReceived,
				omtp11PlusLan10gMacTerminatedMulticastFramesTransmitted,
				omtp11PlusLan10gMacTerminatedMulticastFramesReceived,
				omtp11PlusLan10gMacTerminatedBroadcastFramesTransmitted,
				omtp11PlusLan10gMacTerminatedBroadcastFramesReceived,
				omtp11PlusLan10gMacTerminatedUnderSizeFramesTransmitted,
				omtp11PlusLan10gMacTerminatedUnderSizeFramesReceived,
				omtp11PlusLan10gMacTerminatedOverSizeFramesTransmitted,
				omtp11PlusLan10gMacTerminatedOverSizeFramesReceived,
				omtp11PlusLan10gMacTerminatedVlanTaggedFramesTransmitted,
				omtp11PlusLan10gMacTerminatedVlanTaggedFramesReceived,
				omtp11PlusLan10gMacTerminatedFrameSymbolErrorsReceived,
				omtp11PlusLan10gMacTerminatedFragmentFramesReceived,
				omtp11PlusLan10gMacTerminatedFrameCheckSequenceErrorsReceived,
				omtp11PlusLan10gMacTerminatedFramesReceivedWithNoDefect,
				omtp11PlusLan10gMacTerminatedBytesTransmitted,
				omtp11PlusLan10gMacTerminatedBytesReceived,
				omtp11PlusLan10gMacTerminatedControlFramesTransmitted,
				omtp11PlusLan10gMacTerminatedControlFramesReceived,
				omtp11PlusLan10gTransparentTransmitLcvCount,
				omtp11PlusLan10gTransparentTransmitPropagationErrorDeletionCount,
				omtp11PlusLan10gTransparentTransmitIdleDeletionCount,
				omtp11PlusLan10gTransparentTransmitConfDeletionCount,
				omtp11PlusLan10gTransparentTransmitPropagationInsertionCount,
				omtp11PlusLan10gTransparentTransmitIdleInsertionCount,
				omtp11PlusLan10gTransparentTransmitConfInsertionCount,
				omtp11PlusLan10gTransparentReceiveLcvCount,
				omtp11PlusLan10gTransparentReceivePropagationErrorDeletionCount,
				omtp11PlusLan10gTransparentReceiveIdleDeletionCount,
				omtp11PlusLan10gTransparentReceiveConfDeletionCount,
				omtp11PlusLan10gTransparentReceivePacketDeletionCount,
				omtp11PlusGfpCoreHeaderErrorCount,
				omtp11PlusGfpExtentionHeaderErrorCount,
				omtp11PlusGfpFrameCountWithSingleBitError,
				omtp11PlusGfpTypeHeaderErrorCount,
				omtp11PlusGfpReceiveDropFrameCount,
				omtp11PlusGfpReceiveExtensionHeaderIdentifierFilterDropCount,
				omtp11PlusFcTransmitWordCount,
				omtp11PlusFcTransmitBadCrc,
				omtp11PlusFcTransmitTotalPackets,
				omtp11PlusFcTransmitLcvCount,
				omtp11PlusFcReceiveWordCount,
				omtp11PlusFcReceiveBadCrc,
				omtp11PlusFcReceiveTotalPackets,
				omtp11PlusFcReceiveLcvCount,
				omtp11PlusFcTransmitFillWordInsertionCount,
				omtp11PlusFcTransmitPrimitiveSequenceInsertionCount,
				omtp11PlusFcTransmitFillWordDeletionCount,
				omtp11PlusFcTransmitPrimitiveSequenceDeletionCount,
				omtp11PlusPerformanceTableRowStatus,
				omtp11PlusDiagnosticTableRowStatus,
				omtp11PlusAccessCortinaRegister,
				omtp11PlusCollectCortinaRegisterDump,
				omtp11PlusCollectCortinaModulebGpllRxLockStatus,
				omtp11PlusCollectCortinaModulebGpllTxLockStatus,
				omtp11PlusCollectCortinaModulebTxSerdesLockStatus,
				omtp11PlusCollectCortinaModulebTxSerdesVcoTunedValue,
				omtp11PlusCollectCortinaModulebXfiCupllLockStatus,
				omtp11PlusCollectCortinaModulebAllClockLockStatus

		}
		STATUS  current
		DESCRIPTION
	    		"A collection of objects from RFC 1213 made current by this MIB module."
		::= { utlrnd 2 }

END

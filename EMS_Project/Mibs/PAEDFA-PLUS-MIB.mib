--*****************************************************************************
--				UTL PA EDFA PLUS MIB
--*****************************************************************************

PAEDFA-PLUS-MIB DEFINITIONS ::= BEGIN
 
		IMPORTS
		RowStatus				FROM STANDARD-MIB

		DisplayString				FROM RFC1213-MIB       

		OBJECT-IDENTITY, 
		NOTIFICATION-TYPE, 
		MODULE-IDENTITY, 
		Integer32, 
		Unsigned32, 
		IpAddress, 
		TimeTicks				FROM SNMPv2-SMI

		OBJECT-TYPE				FROM RFC-1212

		MODULE-COMPLIANCE, 
		OBJECT-GROUP, 
		NOTIFICATION-GROUP			FROM SNMPv2-CONF
		
		node, 
		rack, 
		subRack, 
		slot 					FROM SCC-MIB

		enterprises 				FROM RFC1155-SMI		

	;

	utl   	MODULE-IDENTITY
		LAST-UPDATED    	"1807130630Z"
		ORGANIZATION    	"United Telecoms Limited, Bangalore-560048."
		CONTACT-INFO    	"Website: http://www.utlindia.com."                                           
		DESCRIPTION     	"MIB module for UTL DWDM."
		REVISION 	    	"1807130630Z"

		DESCRIPTION    	 	"MIB module for PA EDFA Plus Card."

		::= { enterprises 18036 }

	utlrnd  OBJECT-IDENTITY
		STATUS  current

		DESCRIPTION "UTL R and D."

		::= { utl 1 }

	dwdm 				OBJECT IDENTIFIER	::=   { utlrnd 1 }
	indus 				OBJECT IDENTIFIER	::=   { dwdm 1 }
	paEdfaPlus 			OBJECT IDENTIFIER 	::=   { indus 141 }

	paEdfaPlusCardGeneralDetails 	OBJECT IDENTIFIER 	::=   { paEdfaPlus 1 }
	paEdfaPlusConfiguration 	OBJECT IDENTIFIER 	::=   { paEdfaPlus 2 }
	paEdfaPlusAlarm 		OBJECT IDENTIFIER 	::=   { paEdfaPlus 3 }
	paEdfaPlusPerformance 		OBJECT IDENTIFIER 	::=   { paEdfaPlus 4 }	

	paEdfaPlusAlarmQuery 		OBJECT IDENTIFIER 	::=   { paEdfaPlusAlarm 1 }
	paEdfaPlusAlarmNotification 	OBJECT IDENTIFIER 	::=   { paEdfaPlusAlarm 2 }

--*****************************************************************************
--			PA EDFA PLUS CARD GENERAL DETAILS
--*****************************************************************************

	paEdfaPlusCardGeneralDetailsTable OBJECT-TYPE
		SYNTAX  	SEQUENCE OF PaEdfaPlusCardGeneralDetailsEntry
		MAX-ACCESS	not-accessible
		STATUS		current

		DESCRIPTION
		 " we can get PA EDFA PLUS card general details "

		::= { paEdfaPlusCardGeneralDetails 1 }

	paEdfaPlusCardGeneralDetailsEntry OBJECT-TYPE
		SYNTAX  	PaEdfaPlusCardGeneralDetailsEntry
		MAX-ACCESS  	not-accessible
		STATUS  	current

		DESCRIPTION 
		 "Enter node rack, subrack, slot and paEdfaPlusInterface numbers"

		INDEX   { node, rack, subRack, slot, paEdfaPlusInterface }

		::= { paEdfaPlusCardGeneralDetailsTable 1 }

	PaEdfaPlusCardGeneralDetailsEntry ::=
		SEQUENCE {
				paEdfaPlusInterface					INTEGER,
				paEdfaPlusEepromCardId					INTEGER,
				paEdfaPlusEepromCardName				DisplayString,
				paEdfaPlusEepromPartCode				DisplayString,
				paEdfaPlusEepromCardSerialNumber			DisplayString,
				paEdfaPlusEepromHardwareExternalReleaseVersion		DisplayString,
				paEdfaPlusSoftwareExternalReleaseVersion		DisplayString,
				paEdfaPlusEepromHardwareInternalReleaseVersion		DisplayString,
				paEdfaPlusSoftwareInternalReleaseVersion		DisplayString,
				paEdfaPlusEepromCardUidNumber				DisplayString,
				paEdfaPlusEepromCardEUI48Number				DisplayString,
				paEdfaPlusEepromCardEUI64Number				DisplayString,
				paEdfaPlusCardRootFileSystemVersion			DisplayString,
				paEdfaPlusInstallationDate				DisplayString,
				paEdfaPlusCommissionDate				DisplayString,
				paEdfaPlusCardRunningTime				DisplayString,
				paEdfaPlusCardRestartCount				INTEGER,
				paEdfaPlusModuleVendorName				DisplayString,
				paEdfaPlusModuleSerialNumber				DisplayString,
				paEdfaPlusNumberOfChannelsSupported			INTEGER,
				paEdfaPlusNumberOfPumpSupported				INTEGER,
				paEdfaPlusMaxGainSupported				DisplayString,
				paEdfaPlusSaturationOutputPowerSupported		DisplayString,
				paEdfaPlusMidStageAccessSupport				INTEGER,
				paEdfaPlusDirection					INTEGER,
				paEdfaPlusStage2VoaPresenceStatus			INTEGER,
				paEdfaPlusCardGeneralDetailsTableRowStatus		RowStatus
			}

	paEdfaPlusInterface 	OBJECT-TYPE
		SYNTAX  	INTEGER
		MAX-ACCESS  not-accessible
		STATUS  	current
		DESCRIPTION	
			"pa edfa plus interface number, should be 0 always"

		::= { paEdfaPlusCardGeneralDetailsEntry 1 }

	paEdfaPlusEepromCardId OBJECT-TYPE
		SYNTAX  	INTEGER
		MAX-ACCESS  	read-only
		STATUS  	current

		DESCRIPTION
		 " Tells the card ID of the PAEDFA-PLUS card, present in the EEPROM "

		::= { paEdfaPlusCardGeneralDetailsEntry 2 }

	paEdfaPlusEepromCardName OBJECT-TYPE
		SYNTAX  	DisplayString (SIZE (0..255))
		MAX-ACCESS  	read-only
		STATUS		current

		DESCRIPTION
		 " Tells the card name of the PAEDFA-PLUS card, present in the EEPROM "

		::= { paEdfaPlusCardGeneralDetailsEntry 3 }

	paEdfaPlusEepromPartCode OBJECT-TYPE
		SYNTAX  	DisplayString (SIZE (0..255))
		MAX-ACCESS  	read-only
		STATUS		current

		DESCRIPTION
		 " Tells the part code of the PAEDFA-PLUS card, present in the EEPROM "

		::= { paEdfaPlusCardGeneralDetailsEntry 4 }

	paEdfaPlusEepromCardSerialNumber OBJECT-TYPE
		SYNTAX  	DisplayString (SIZE (0..255))
		MAX-ACCESS  	read-write
		STATUS		current

		DESCRIPTION
		 " This property get / set the information about PAEDFA-PLUS 
		 Card's Serial Number.
		-----------------------------
		Values:
		eg: 123456
		-----------------------------"

		::= { paEdfaPlusCardGeneralDetailsEntry 5 }

	paEdfaPlusEepromHardwareExternalReleaseVersion OBJECT-TYPE
		SYNTAX  	DisplayString (SIZE (0..255))
		MAX-ACCESS  	read-only
		STATUS		current

		DESCRIPTION
		 " To get the Card's Hardware External Release Version. This detail 
		 will be displayed to the customer. This version will increment 
		 only if there are significant architectural changes in the product.
		-----------------------------
		Value:
		eg: 0.1
		-----------------------------"

		::= { paEdfaPlusCardGeneralDetailsEntry 6 }

	paEdfaPlusSoftwareExternalReleaseVersion OBJECT-TYPE
		SYNTAX  	DisplayString (SIZE (0..255))
		MAX-ACCESS  	read-only
		STATUS		current

		DESCRIPTION
		 " To get the Card's Software External Release Version.  This detail 
		 will be displayed to the customer. This version will increment 
		 only if there are significant architectural changes in the product.
		-----------------------------
		Value:
		eg: 0.1
		-----------------------------"

		::= { paEdfaPlusCardGeneralDetailsEntry 7 }

	paEdfaPlusEepromHardwareInternalReleaseVersion OBJECT-TYPE
		SYNTAX  	DisplayString (SIZE (0..255))
		MAX-ACCESS  	read-only
		STATUS		current

		DESCRIPTION
		 " To get the Card's Hardware Internal Release Version. This detail 
		 is used for development purposes only. It differs from the external 
		 hardware version.
		-----------------------------
		Value:
		eg: 4.1
		-----------------------------"

		::= { paEdfaPlusCardGeneralDetailsEntry 8 }

	paEdfaPlusSoftwareInternalReleaseVersion OBJECT-TYPE
		SYNTAX  	DisplayString (SIZE (0..255))
		MAX-ACCESS  	read-only
		STATUS		current

		DESCRIPTION
		 " To get the Card's Software Internal Release Version.  This detail 
		 is used for development purposes only. It differs from the external 
		 software version.
		-----------------------------
		Value:
		eg: 5.1
		-----------------------------"

		::= { paEdfaPlusCardGeneralDetailsEntry 9 }

	paEdfaPlusEepromCardUidNumber OBJECT-TYPE
		SYNTAX  	DisplayString (SIZE (0..255))
		MAX-ACCESS  	read-only
		STATUS		current

		DESCRIPTION
		 " Tells the Card Unique Identifier It is a 4 byte address used to 
		 uniquely identify a card.
		------------------------------
		Value:
	      	eg: 12345678
		-----------------------------"

		::= { paEdfaPlusCardGeneralDetailsEntry 10 }

	paEdfaPlusEepromCardEUI48Number OBJECT-TYPE
		SYNTAX  	DisplayString (SIZE (0..255))
		MAX-ACCESS  	read-only
		STATUS		current

		DESCRIPTION
		 " Tells the Card EUI-48 Number. It’s a 6 byte address used to 
		 uniquely identify a card.
		-----------------------------
		Value:
	      	eg: 0004A3123456
		-----------------------------"

		::= { paEdfaPlusCardGeneralDetailsEntry 11 }

	paEdfaPlusEepromCardEUI64Number OBJECT-TYPE
		SYNTAX  	DisplayString (SIZE (0..255))
		MAX-ACCESS  	read-only
		STATUS		current

		DESCRIPTION
		 " Tells the Card EUI-64 Number. It’s a 8 byte address
		used to uniquely identify a card.
		-----------------------------
		Value:
	      	eg: 0004A31234567890
		-----------------------------"

		::= { paEdfaPlusCardGeneralDetailsEntry 12 }
		
        paEdfaPlusCardRootFileSystemVersion OBJECT-TYPE		 
		SYNTAX  DisplayString
		MAX-ACCESS  read-only
		STATUS current
		DESCRIPTION
			"Tells the Card's Root File System Version
			-----------------------------
			paEdfaPlusInterface: 0
			-----------------------------
			Value:
		      	eg: 8
			-----------------------------"
		::= { paEdfaPlusCardGeneralDetailsEntry 13 }

	paEdfaPlusInstallationDate OBJECT-TYPE
		SYNTAX  	DisplayString (SIZE (0..255))
		MAX-ACCESS  	read-write
		STATUS		current

		DESCRIPTION
		 " To get/set the card's installation date in dd/mm/yyyy format.
		-----------------------------
		Value:
	      	eg: 12/03/2016
		-----------------------------"

		::= { paEdfaPlusCardGeneralDetailsEntry 21 }

	paEdfaPlusCommissionDate OBJECT-TYPE
		SYNTAX  	DisplayString (SIZE (0..255))
		MAX-ACCESS  	read-write
		STATUS		current

		DESCRIPTION
		 " To get/set the card's commission date in  dd/mm/yyyy format.
		-----------------------------
		Value:
	      	eg: 20/03/2016
		-----------------------------"

		::= { paEdfaPlusCardGeneralDetailsEntry 22 }

	paEdfaPlusCardRunningTime OBJECT-TYPE
		SYNTAX  	DisplayString (SIZE (0..255))
		MAX-ACCESS  	read-only
		STATUS		current

		DESCRIPTION
		 " To get the duration of time for which the card is operational/running.
		-----------------------------
		Values:
	      	eg: 3d 2h 1m
		-----------------------------"

		::= { paEdfaPlusCardGeneralDetailsEntry 23 }

	paEdfaPlusCardRestartCount OBJECT-TYPE
		SYNTAX  	INTEGER
		MAX-ACCESS  	read-only
		STATUS		current

		DESCRIPTION
		 " To get the number of times the card has been soft reset. This value 
		 will get reset to 0 on factory reset.
		-----------------------------
		Values:
	      	eg: 10
		-----------------------------"

		::= { paEdfaPlusCardGeneralDetailsEntry 24 }

	paEdfaPlusModuleVendorName OBJECT-TYPE
		SYNTAX  	DisplayString (SIZE (0..255))
		MAX-ACCESS  	read-only
		STATUS		current

		DESCRIPTION
		 " to get PA EDFA PLUS card module vendor name.
		-----------------------------
		Values:
	      	eg: ACCELINK
		-----------------------------"

		::= { paEdfaPlusCardGeneralDetailsEntry 31 }

	paEdfaPlusModuleSerialNumber OBJECT-TYPE
		SYNTAX  	DisplayString (SIZE (0..255))
		MAX-ACCESS  	read-only
		STATUS		current

		DESCRIPTION
		 " to get PA EDFA PLUS card module serial number.
		-----------------------------
		Values:
	      	eg: 12345
		-----------------------------"

		::= { paEdfaPlusCardGeneralDetailsEntry 32 }

	paEdfaPlusNumberOfChannelsSupported OBJECT-TYPE
		SYNTAX  	INTEGER
		MAX-ACCESS  	read-only
		STATUS  	current

		DESCRIPTION
		 " to get PA EDFA PLUS card supports how many number of channels.
		-----------------------------
		Values:
	      	eg: 30
		-----------------------------"

		::= { paEdfaPlusCardGeneralDetailsEntry 33 }

	paEdfaPlusNumberOfPumpSupported OBJECT-TYPE
		SYNTAX  	INTEGER
		MAX-ACCESS  	read-only
		STATUS  	current

		DESCRIPTION
		 " to get PA EDFA PLUS card supports how many number of pumps.
		-----------------------------
		Values:
	      	eg: 2
		-----------------------------"

		::= { paEdfaPlusCardGeneralDetailsEntry 34 }

	paEdfaPlusMaxGainSupported OBJECT-TYPE
		SYNTAX  	DisplayString (SIZE (0..255))
		MAX-ACCESS  	read-only
		STATUS		current

		DESCRIPTION
		 " to get PA EDFA PLUS card supports maximum gain supported.
		-----------------------------
		Values:
	      	eg: 25.0
		-----------------------------"

		::= { paEdfaPlusCardGeneralDetailsEntry 35 }

	paEdfaPlusSaturationOutputPowerSupported OBJECT-TYPE
		SYNTAX  	DisplayString (SIZE (0..255))
		MAX-ACCESS  	read-only
		STATUS		current

		DESCRIPTION
		 " to get PA EDFA PLUS card supports saturation power.
		-----------------------------
		Values:
	      	eg: 19.0
		-----------------------------"

		::= { paEdfaPlusCardGeneralDetailsEntry 36 }

	paEdfaPlusMidStageAccessSupport OBJECT-TYPE
		SYNTAX  	INTEGER
		MAX-ACCESS  	read-only
		STATUS  	current

		DESCRIPTION
		 " to get PA EDFA PLUS card supoort status of mid stage access.
		-----------------------------
		Values:
	      	1 - MSA supported
		0 - MSA not supported
		-----------------------------"

		::= { paEdfaPlusCardGeneralDetailsEntry 37 }
		
	paEdfaPlusDirection	OBJECT-TYPE
		SYNTAX  	INTEGER
		MAX-ACCESS  read-only
		STATUS  	current
		DESCRIPTION	
		" to get BA EDFA card Direction.
		-----------------------------
		Values:
		1 - Direction 1
		2 - Direction 2
		3 - Direction 3
		4 - Direction 4
		-----------------------------"
		::= { paEdfaPlusCardGeneralDetailsEntry 38 }

	paEdfaPlusStage2VoaPresenceStatus	OBJECT-TYPE
		SYNTAX  	INTEGER
		MAX-ACCESS  read-only
		STATUS  	current
		DESCRIPTION	" to get PA EDFA PLUS inbuilt voa presence status.
		-----------------------------
		Values:
		1 - VOA present stage 2
		0 - VOA absent
		-----------------------------"
		::= { paEdfaPlusCardGeneralDetailsEntry 39 }

	paEdfaPlusCardGeneralDetailsTableRowStatus OBJECT-TYPE
	      SYNTAX      RowStatus
	      MAX-ACCESS  read-write
	      STATUS      current
	      DESCRIPTION
		      "	This is MIB realted property,
			NOT to be considered as a card property"
	      ::= { paEdfaPlusCardGeneralDetailsEntry 40 }

--*****************************************************************************
--			PA EDFA PLUS CONFIGURATION
--***************************************************************************** 

	paEdfaPlusConfigurationTable OBJECT-TYPE
		SYNTAX  	SEQUENCE OF PaEdfaPlusConfigurationEntry
		MAX-ACCESS  	not-accessible
		STATUS  	current

		DESCRIPTION
		 " we can get PA EDFA PLUS configuration details "

		::= { paEdfaPlusConfiguration 1 }
              
        paEdfaPlusConfigurationEntry OBJECT-TYPE
		SYNTAX  	PaEdfaPlusConfigurationEntry
		MAX-ACCESS  	not-accessible
		STATUS  	current

		DESCRIPTION  
		 "Enter node rack, subrack, slot and paEdfaPlusInterface numbers"

		INDEX   { node, rack, subRack, slot, paEdfaPlusInterface }

		::= { paEdfaPlusConfigurationTable 1 }
	
	PaEdfaPlusConfigurationEntry ::= 
		SEQUENCE {
				paEdfaPlusCardSoftReset	 								INTEGER,
				paEdfaPlusCardDefaultFactoryReset							INTEGER,
				paEdfaPlusAlarmMonitoringStatus	 							INTEGER,
				paEdfaPlusManageUnmanageStatus								INTEGER,
				paEdfaPlusSyncSystemTimeWithNtpServer				DisplayString,
				paEdfaPlusSyncRtcWithNtpServer						DisplayString,
				paEdfaPlusSyncRtcWithSystemTime						DisplayString,
				paEdfaPlusUpdateGivenTimeIntoSystem					DisplayString,
				paEdfaPlusUpdateGivenTimeIntoRtc					DisplayString,
				paEdfaPlusSystemTimeAndRtcTime						DisplayString,
				paEdfaPlusVariableOpticalAttenuatorReset						INTEGER,
				paEdfaPlusPump1LaserStatus	 							INTEGER,
				paEdfaPlusPump2LaserStatus	 							INTEGER,
				paEdfaPlusAutomaticPowerReductionStatusForStage1					INTEGER,
				paEdfaPlusAutomaticPowerReductionStatusForStage2					INTEGER,
				paEdfaPlusAutomaticLaserShutdownStatusForStage1						INTEGER,
				paEdfaPlusAutomaticLaserShutdownStatusForStage2						INTEGER,
				paEdfaPlusModuleOperatingModeForStage1							DisplayString,
				paEdfaPlusModuleOperatingModeForStage2							DisplayString,
				paEdfaPlusModuleGainInAutomaticGainControlModeForStage1					DisplayString,
				paEdfaPlusModuleGainInAutomaticGainControlModeForStage2					DisplayString,
				paEdfaPlusModuleOutputPowerInAutomaticPowerControlMode					DisplayString,
				paEdfaPlusPump1OperatingCurrentInAutomaticCurrentControlMode				DisplayString,
				paEdfaPlusPump2OperatingCurrentInAutomaticCurrentControlMode				DisplayString,
				paEdfaPlusGainTilt	 								DisplayString,
				paEdfaPlusVariableOpticalAttenuatorAttenuationForStage2					DisplayString,
				paEdfaPlusOutputPowerLimitFunctionStatusInAutomaticGainControlModeForStage1		INTEGER,
				paEdfaPlusOutputPowerLimitFunctionStatusInAutomaticGainControlModeForStage2		INTEGER,
				paEdfaPlusOutputPowerLimitInAutomaticGainControlModeForStage1				DisplayString,
				paEdfaPlusOutputPowerLimitInAutomaticGainControlModeForStage2				DisplayString,
				paEdfaPlusAutomaticPowerReductionForStage1Threshold					DisplayString,
				paEdfaPlusAutomaticPowerReductionForStage2Threshold					DisplayString,
				paEdfaPlusOpticalInputPowerFailureAlarmForStage1Threshold				DisplayString,
				paEdfaPlusOpticalInputPowerFailureAlarmForStage2Threshold				DisplayString,
				paEdfaPlusOpticalHighInputPowerAlarmForStage1Threshold					DisplayString,
				paEdfaPlusOpticalHighInputPowerAlarmForStage2Threshold					DisplayString,
				paEdfaPlusOpticalLowInputPowerAlarmForStage1Threshold					DisplayString,
				paEdfaPlusOpticalLowInputPowerAlarmForStage2Threshold					DisplayString,
				paEdfaPlusOpticalHighInputPowerWarningForStage1Threshold				DisplayString,
				paEdfaPlusOpticalHighInputPowerWarningForStage2Threshold				DisplayString,
				paEdfaPlusOpticalLowInputPowerWarningForStage1Threshold					DisplayString,
				paEdfaPlusOpticalLowInputPowerWarningForStage2Threshold					DisplayString,
				paEdfaPlusOpticalOutputPowerFailureAlarmForStage1Threshold				DisplayString,
				paEdfaPlusOpticalOutputPowerFailureAlarmForStage2Threshold				DisplayString,
				paEdfaPlusOpticalHighOutputPowerAlarmForStage1Threshold					DisplayString,
				paEdfaPlusOpticalHighOutputPowerAlarmForStage2Threshold					DisplayString,
				paEdfaPlusOpticalLowOutputPowerAlarmForStage1Threshold					DisplayString,
				paEdfaPlusOpticalLowOutputPowerAlarmForStage2Threshold					DisplayString,
				paEdfaPlusOpticalHighOutputPowerWarningForStage1Threshold				DisplayString,
				paEdfaPlusOpticalHighOutputPowerWarningForStage2Threshold				DisplayString,
				paEdfaPlusOpticalLowOutputPowerWarningForStage1Threshold				DisplayString,
				paEdfaPlusOpticalLowOutputPowerWarningForStage2Threshold				DisplayString,
				paEdfaPlusModuleHighTemperatureAlarmThreshold						DisplayString,
				paEdfaPlusModuleLowTemperatureAlarmThreshold						DisplayString,
				paEdfaPlusModuleHighTemperatureWarningThreshold						DisplayString,
				paEdfaPlusModuleLowTemperatureWarningThreshold						DisplayString,
				paEdfaPlusPump1HighTemperatureAlarmThreshold						DisplayString,
				paEdfaPlusPump2HighTemperatureAlarmThreshold						DisplayString,
				paEdfaPlusPump1LowTemperatureAlarmThreshold						DisplayString,
				paEdfaPlusPump2LowTemperatureAlarmThreshold						DisplayString,
				paEdfaPlusPump1HighTemperatureWarningThreshold						DisplayString,
				paEdfaPlusPump2HighTemperatureWarningThreshold						DisplayString,
				paEdfaPlusPump1LowTemperatureWarningThreshold						DisplayString,
				paEdfaPlusPump2LowTemperatureWarningThreshold						DisplayString,
				paEdfaPlusPump1HighOperatingCurrentAlarmThreshold					DisplayString,
				paEdfaPlusPump2HighOperatingCurrentAlarmThreshold					DisplayString,
				paEdfaPlusPump1LowOperatingCurrentAlarmThreshold					DisplayString,
				paEdfaPlusPump2LowOperatingCurrentAlarmThreshold					DisplayString,
				paEdfaPlusPump1HighOperatingCurrentWarningThreshold					DisplayString,
				paEdfaPlusPump2HighOperatingCurrentWarningThreshold					DisplayString,
				paEdfaPlusPump1LowOperatingCurrentWarningThreshold					DisplayString,
				paEdfaPlusPump2LowOperatingCurrentWarningThreshold					DisplayString,
				paEdfaPlusPump1HighThermoElectricCoolerCurrentAlarmThreshold				DisplayString,
				paEdfaPlusPump2HighThermoElectricCoolerCurrentAlarmThreshold				DisplayString,
				paEdfaPlusPump1LowThermoElectricCoolerCurrentAlarmThreshold				DisplayString,
				paEdfaPlusPump2LowThermoElectricCoolerCurrentAlarmThreshold				DisplayString,
				paEdfaPlusPump1HighThermoElectricCoolerCurrentWarningThreshold				DisplayString,
				paEdfaPlusPump2HighThermoElectricCoolerCurrentWarningThreshold				DisplayString,
				paEdfaPlusPump1LowThermoElectricCoolerCurrentWarningThreshold				DisplayString,
				paEdfaPlusPump2LowThermoElectricCoolerCurrentWarningThreshold				DisplayString,
				paEdfaPlusVariableOpticalAttenuatorHighInputPowerAlarmThreshold 			DisplayString,
				paEdfaPlusVariableOpticalAttenuatorLowInputPowerAlarmThreshold 				DisplayString,
				paEdfaPlusVariableOpticalAttenuatorHighInputPowerWarningThreshold 			DisplayString,
				paEdfaPlusVariableOpticalAttenuatorLowInputPowerWarningThreshold 			DisplayString,
				paEdfaPlusOpticalInputPowerFailureAlarmForStage1Inhibit 				INTEGER,
				paEdfaPlusOpticalInputPowerFailureAlarmForStage2Inhibit 				INTEGER,
				paEdfaPlusOpticalHighInputPowerAlarmForStage1Inhibit					INTEGER,
				paEdfaPlusOpticalHighInputPowerAlarmForStage2Inhibit					INTEGER,
				paEdfaPlusOpticalLowInputPowerAlarmForStage1Inhibit	 				INTEGER,
				paEdfaPlusOpticalLowInputPowerAlarmForStage2Inhibit	 				INTEGER,
				paEdfaPlusOpticalHighInputPowerWarningForStage1Inhibit	 				INTEGER,
				paEdfaPlusOpticalHighInputPowerWarningForStage2Inhibit	 				INTEGER,
				paEdfaPlusOpticalLowInputPowerWarningForStage1Inhibit 					INTEGER,
				paEdfaPlusOpticalLowInputPowerWarningForStage2Inhibit 					INTEGER,
				paEdfaPlusOpticalOutputPowerFailureAlarmForStage1Inhibit				INTEGER,
				paEdfaPlusOpticalOutputPowerFailureAlarmForStage2Inhibit				INTEGER,
				paEdfaPlusOpticalHighOutputPowerAlarmForStage1Inhibit					INTEGER,
				paEdfaPlusOpticalHighOutputPowerAlarmForStage2Inhibit					INTEGER,
				paEdfaPlusOpticalLowOutputPowerAlarmForStage1Inhibit					INTEGER,
				paEdfaPlusOpticalLowOutputPowerAlarmForStage2Inhibit					INTEGER,
				paEdfaPlusOpticalHighOutputPowerWarningForStage1Inhibit					INTEGER,
				paEdfaPlusOpticalHighOutputPowerWarningForStage2Inhibit					INTEGER,
				paEdfaPlusOpticalLowOutputPowerWarningForStage1Inhibit					INTEGER,
				paEdfaPlusOpticalLowOutputPowerWarningForStage2Inhibit					INTEGER,
				paEdfaPlusModuleHighTemperatureAlarmInhibit						INTEGER,
				paEdfaPlusModuleLowTemperatureAlarmInhibit						INTEGER,
				paEdfaPlusModuleHighTemperatureWarningInhibit						INTEGER,
				paEdfaPlusModuleLowTemperatureWarningInhibit						INTEGER,
				paEdfaPlusPump1HighTemperatureAlarmInhibit						INTEGER,
				paEdfaPlusPump2HighTemperatureAlarmInhibit						INTEGER,
				paEdfaPlusPump1LowTemperatureAlarmInhibit						INTEGER,
				paEdfaPlusPump2LowTemperatureAlarmInhibit						INTEGER,
				paEdfaPlusPump1HighTemperatureWarningInhibit						INTEGER,
				paEdfaPlusPump2HighTemperatureWarningInhibit						INTEGER,
				paEdfaPlusPump1LowTemperatureWarningInhibit						INTEGER,
				paEdfaPlusPump2LowTemperatureWarningInhibit						INTEGER,
				paEdfaPlusPump1HighOperatingCurrentAlarmInhibit						INTEGER,
				paEdfaPlusPump2HighOperatingCurrentAlarmInhibit						INTEGER,
				paEdfaPlusPump1LowOperatingCurrentAlarmInhibit						INTEGER,
				paEdfaPlusPump2LowOperatingCurrentAlarmInhibit						INTEGER,
				paEdfaPlusPump1HighOperatingCurrentWarningInhibit					INTEGER,
				paEdfaPlusPump2HighOperatingCurrentWarningInhibit					INTEGER,
				paEdfaPlusPump1LowOperatingCurrentWarningInhibit					INTEGER,
				paEdfaPlusPump2LowOperatingCurrentWarningInhibit					INTEGER,
				paEdfaPlusPump1HighThermoElectricCoolerCurrentAlarmInhibit				INTEGER,
				paEdfaPlusPump2HighThermoElectricCoolerCurrentAlarmInhibit				INTEGER,
				paEdfaPlusPump1LowThermoElectricCoolerCurrentAlarmInhibit				INTEGER,
				paEdfaPlusPump2LowThermoElectricCoolerCurrentAlarmInhibit				INTEGER,
				paEdfaPlusPump1HighThermoElectricCoolerCurrentWarningInhibit				INTEGER,
				paEdfaPlusPump2HighThermoElectricCoolerCurrentWarningInhibit				INTEGER,
				paEdfaPlusPump1LowThermoElectricCoolerCurrentWarningInhibit				INTEGER,
				paEdfaPlusPump2LowThermoElectricCoolerCurrentWarningInhibit				INTEGER,
				paEdfaPlusVariableOpticalAttenuatorHighInputPowerAlarmInhibit				INTEGER,
				paEdfaPlusVariableOpticalAttenuatorLowInputPowerAlarmInhibit				INTEGER,
				paEdfaPlusVariableOpticalAttenuatorHighInputPowerWarningInhibit				INTEGER,
				paEdfaPlusVariableOpticalAttenuatorLowInputPowerWarningInhibit				INTEGER,
				paEdfaPlusInputOutOfRangeAlarmInhibit							INTEGER,
				paEdfaPlusOutputOutOfRangeAlarmInhibit							INTEGER,
				paEdfaPlusPumpBiasCurrentAlarmInhibit							INTEGER,
				paEdfaPlusPump1CoolingTemperatureAlarmInhibit						INTEGER,
				paEdfaPlusPump2CoolingTemperatureAlarmInhibit						INTEGER,
				paEdfaPlusPump1LaserPowerAlarmInhibit							INTEGER,
				paEdfaPlusPump2LaserPowerAlarmInhibit							INTEGER,
				paEdfaPlusOpticalInputPowerFailureAlarmForStage1Severity 				DisplayString,
				paEdfaPlusOpticalInputPowerFailureAlarmForStage2Severity 				DisplayString,
				paEdfaPlusOpticalHighInputPowerAlarmForStage1Severity 					DisplayString,
				paEdfaPlusOpticalHighInputPowerAlarmForStage2Severity 					DisplayString,
				paEdfaPlusOpticalLowInputPowerAlarmForStage1Severity 					DisplayString,
				paEdfaPlusOpticalLowInputPowerAlarmForStage2Severity 					DisplayString,
				paEdfaPlusOpticalHighInputPowerWarningForStage1Severity 				DisplayString,
				paEdfaPlusOpticalHighInputPowerWarningForStage2Severity 				DisplayString,
				paEdfaPlusOpticalLowInputPowerWarningForStage1Severity 					DisplayString,
				paEdfaPlusOpticalLowInputPowerWarningForStage2Severity 					DisplayString,
				paEdfaPlusOpticalOutputPowerFailureAlarmForStage1Severity 				DisplayString,
				paEdfaPlusOpticalOutputPowerFailureAlarmForStage2Severity 				DisplayString,
				paEdfaPlusOpticalHighOutputPowerAlarmForStage1Severity 					DisplayString,
				paEdfaPlusOpticalHighOutputPowerAlarmForStage2Severity 					DisplayString,
				paEdfaPlusOpticalLowOutputPowerAlarmForStage1Severity 					DisplayString,
				paEdfaPlusOpticalLowOutputPowerAlarmForStage2Severity	 				DisplayString,
				paEdfaPlusOpticalHighOutputPowerWarningForStage1Severity 				DisplayString,
				paEdfaPlusOpticalHighOutputPowerWarningForStage2Severity 				DisplayString,
				paEdfaPlusOpticalLowOutputPowerWarningForStage1Severity 				DisplayString,
				paEdfaPlusOpticalLowOutputPowerWarningForStage2Severity 				DisplayString,
				paEdfaPlusModuleHighTemperatureAlarmSeverity 						DisplayString,
				paEdfaPlusModuleLowTemperatureAlarmSeverity 						DisplayString,
				paEdfaPlusModuleHighTemperatureWarningSeverity 						DisplayString,
				paEdfaPlusModuleLowTemperatureWarningSeverity 						DisplayString,
				paEdfaPlusPump1HighTemperatureAlarmSeverity 						DisplayString,
				paEdfaPlusPump2HighTemperatureAlarmSeverity 						DisplayString,
				paEdfaPlusPump1LowTemperatureAlarmSeverity 						DisplayString,
				paEdfaPlusPump2LowTemperatureAlarmSeverity 						DisplayString,
				paEdfaPlusPump1HighTemperatureWarningSeverity 						DisplayString,
				paEdfaPlusPump2HighTemperatureWarningSeverity 						DisplayString,
				paEdfaPlusPump1LowTemperatureWarningSeverity 						DisplayString,
				paEdfaPlusPump2LowTemperatureWarningSeverity 						DisplayString,
				paEdfaPlusPump1HighOperatingCurrentAlarmSeverity 					DisplayString,
				paEdfaPlusPump2HighOperatingCurrentAlarmSeverity 					DisplayString,
				paEdfaPlusPump1LowOperatingCurrentAlarmSeverity 					DisplayString,
				paEdfaPlusPump2LowOperatingCurrentAlarmSeverity 					DisplayString,
				paEdfaPlusPump1HighOperatingCurrentWarningSeverity 					DisplayString,
				paEdfaPlusPump2HighOperatingCurrentWarningSeverity 					DisplayString,
				paEdfaPlusPump1LowOperatingCurrentWarningSeverity 					DisplayString,
				paEdfaPlusPump2LowOperatingCurrentWarningSeverity 					DisplayString,
				paEdfaPlusPump1HighThermoElectricCoolerCurrentAlarmSeverity				DisplayString,
				paEdfaPlusPump2HighThermoElectricCoolerCurrentAlarmSeverity 				DisplayString,
				paEdfaPlusPump1LowThermoElectricCoolerCurrentAlarmSeverity 				DisplayString,
				paEdfaPlusPump2LowThermoElectricCoolerCurrentAlarmSeverity 				DisplayString,
				paEdfaPlusPump1HighThermoElectricCoolerCurrentWarningSeverity 				DisplayString,
				paEdfaPlusPump2HighThermoElectricCoolerCurrentWarningSeverity 				DisplayString,
				paEdfaPlusPump1LowThermoElectricCoolerCurrentWarningSeverity 				DisplayString,
				paEdfaPlusPump2LowThermoElectricCoolerCurrentWarningSeverity 				DisplayString,
				paEdfaPlusVariableOpticalAttenuatorHighInputPowerAlarmSeverity 				DisplayString,
				paEdfaPlusVariableOpticalAttenuatorLowInputPowerAlarmSeverity 				DisplayString,
				paEdfaPlusVariableOpticalAttenuatorHighInputPowerWarningSeverity 			DisplayString,
				paEdfaPlusVariableOpticalAttenuatorLowInputPowerWarningSeverity 			DisplayString,
				paEdfaPlusInputOutOfRangeAlarmSeverity 							DisplayString,
				paEdfaPlusOutputOutOfRangeAlarmSeverity 						DisplayString,
				paEdfaPlusPumpBiasCurrentAlarmSeverity 							DisplayString,
				paEdfaPlusPump1CoolingTemperatureAlarmSeverity						DisplayString,
				paEdfaPlusPump2CoolingTemperatureAlarmSeverity						DisplayString,
				paEdfaPlusPump1LaserPowerAlarmSeverity							DisplayString,
				paEdfaPlusPump2LaserPowerAlarmSeverity							DisplayString,
				paEdfaPlusCardSoftwareUpgrade								DisplayString,
				paEdfaPlusMidInOutOfRangeAlarmInhibit							INTEGER,
				paEdfaPlusMidOutOutOfRangeAlarmInhibit							INTEGER,
				paEdfaPlusMidInOutOfRangeAlarmSeverity							DisplayString,
				paEdfaPlusMidOutOutOfRangeAlarmSeverity							DisplayString,
				paEdfaPlusConfigurationTableRowStatus							RowStatus
			}
		
	paEdfaPlusCardSoftReset OBJECT-TYPE
		SYNTAX  	INTEGER
		MAX-ACCESS  	read-write
		STATUS  	current

		DESCRIPTION
		"Valid only as a SET command.
		Reboots the Card, Reconfigures the Card 
		i.e All Configuration Parameter	like Laser State,
		thresholds, operating mode & gain will be restored to 
		previous state.
		-----------------------------
		Values:
		Dont care, any value
		eg: 0
		-----------------------------"

		::= { paEdfaPlusConfigurationEntry 1 }		
	
	paEdfaPlusCardDefaultFactoryReset OBJECT-TYPE
		SYNTAX  	INTEGER
		MAX-ACCESS  	read-write
		STATUS  	current

		DESCRIPTION
		"Valid only as a SET command.
		Sets the Card To Factory Default State
		i.e All Configuration Parameter	like Laser State,
		thresholds, operating mode & gain will be set to 
		default state. "

		::= { paEdfaPlusConfigurationEntry 2 }

	paEdfaPlusAlarmMonitoringStatus OBJECT-TYPE
		SYNTAX  	INTEGER
		MAX-ACCESS  	read-write
		STATUS  	current

		DESCRIPTION
		"This property sets or gets the card's Alarm
		monitoring state. Disabling card alarm monitoring 
		will not provide any alarms and performances
		information to the user.
		-----------------------------
		Values:
		1 - Card Alarm Monitoring is enabled
		0 - Card Alarm Monitoring is disabled
		-----------------------------"

		::= { paEdfaPlusConfigurationEntry 3 }

	paEdfaPlusManageUnmanageStatus OBJECT-TYPE
		SYNTAX  	INTEGER
		MAX-ACCESS  	read-write
		STATUS  	current

		DESCRIPTION
		"This property will tell whether the card is 
		accessible from EMS/LCT or not. Turning off the
		accessbility to the card, will not allow the user
		to access any configuration, alarm or performance
		of the card and also turns off fast alarm
		triggering, global alarm led indication
		-----------------------------
		Values:
		1 - Card is accessible from EMS/LCT
		0 - Card is inaccessible from EMS/LCT
		-----------------------------"

		::= { paEdfaPlusConfigurationEntry 4 }

	paEdfaPlusSyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that particular server. 
					If we are not providing NTP server IP address 
					then the system will be synced with the NTP server 
					which is already been registered with card. 
					If both are absent then error message will be returned
					-----------------------------
						Interface : 0
					-----------------------------
						If we want to provide NTP server IP address then
						Value should be a valid IP address as shown below
						: 192.168.21.25
						
						If we don't want to provide NTP server address then no
						need to pass any value. 
					---------------------------"
  						
  		::= { paEdfaPlusConfigurationEntry 5 }
  		
  	paEdfaPlusSyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 192.168.21.25
							
						If we don't want to provide NTP server address, then no
						need to pass any value. 
						---------------------------"
  						
  		::= { paEdfaPlusConfigurationEntry 6 }
  		
  	paEdfaPlusSyncRtcWithSystemTime	 OBJECT-TYPE
		SYNTAX  		DisplayString
  		MAX-ACCESS  	read-write
  		STATUS  		current
  		DESCRIPTION	 	" when we want to manually sync the time value
  						present in RTC with the time value in linux kernel
  						we can use this OID. With this set operation, 
  						the time available with linux kernel will be updated
  						into RTC. It is not required to provide any value for 
  						this operation"
  						
  		::= { paEdfaPlusConfigurationEntry 7 }
  		
  	paEdfaPlusUpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2017-10-31 15:20:44
						---------------------------"
						
  		::= { paEdfaPlusConfigurationEntry 8 }
  		
  	paEdfaPlusUpdateGivenTimeIntoRtc	 OBJECT-TYPE
		SYNTAX  		DisplayString
  		MAX-ACCESS  	read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD H:M:S
						
						Example: 2017-10-31 15:20:44
						---------------------------"
						
  		::= { paEdfaPlusConfigurationEntry 9 }
  		
  	paEdfaPlusSystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { paEdfaPlusConfigurationEntry 10 }

	paEdfaPlusVariableOpticalAttenuatorReset OBJECT-TYPE
		SYNTAX  	INTEGER
		MAX-ACCESS  	read-write
		STATUS  	current

		DESCRIPTION
		 " to reset variable optical attenuator of PA EDFA PLUS card.
		-----------------------------
		Values:
		Dont care, any value
		eg: 0
		-----------------------------"

		::= { paEdfaPlusConfigurationEntry 21 }

	paEdfaPlusPump1LaserStatus OBJECT-TYPE
		SYNTAX  	INTEGER
		MAX-ACCESS  	read-write
		STATUS  	current

		DESCRIPTION
		 " to set/get PA EDFA PLUS card pump 1 laser status.
		-----------------------------
		Values:
		1 - Laser ON
		0 - Laser OFF
		-----------------------------"

		::= { paEdfaPlusConfigurationEntry 22 }

	paEdfaPlusPump2LaserStatus OBJECT-TYPE
		SYNTAX  	INTEGER
		MAX-ACCESS  	read-write
		STATUS  	current

		DESCRIPTION
		 " to set/get PA EDFA PLUS card pump 2 laser status.
		-----------------------------
		Values:
		1 - Laser ON
		0 - Laser OFF
		-----------------------------"

		::= { paEdfaPlusConfigurationEntry 23 }

	paEdfaPlusAutomaticPowerReductionStatusForStage1 OBJECT-TYPE
		SYNTAX  	INTEGER
		MAX-ACCESS  	read-write
		STATUS  	current

		DESCRIPTION
		 " to set/get PA EDFA PLUS card automatic power reduction status for stage 1.
		-----------------------------
		Values:
		1 - Automatic power reduction function ON
		0 - Automatic power reduction function OFF
		-----------------------------"

		::= { paEdfaPlusConfigurationEntry 24 }

	paEdfaPlusAutomaticPowerReductionStatusForStage2 OBJECT-TYPE
		SYNTAX  	INTEGER
		MAX-ACCESS  	read-write
		STATUS  	current

		DESCRIPTION
		 " to set/get PA EDFA PLUS card automatic power reduction status for stage 2.
		-----------------------------
		Values:
		1 - Automatic power reduction function ON
		0 - Automatic power reduction function OFF
		-----------------------------"

		::= { paEdfaPlusConfigurationEntry 25 }

	paEdfaPlusAutomaticLaserShutdownStatusForStage1 OBJECT-TYPE
		SYNTAX  	INTEGER
		MAX-ACCESS  	read-write
		STATUS  	current

		DESCRIPTION
		 " to set/get PA EDFA PLUS card automatic laser shutdown status for stage 1.
		-----------------------------
		Values:
		1 - Automatic laser shutdown function ON
		0 - Automatic laser shutdown function OFF
		-----------------------------"

		::= { paEdfaPlusConfigurationEntry 26 }

	paEdfaPlusAutomaticLaserShutdownStatusForStage2 OBJECT-TYPE
		SYNTAX  	INTEGER
		MAX-ACCESS  	read-write
		STATUS  	current

		DESCRIPTION
		 " to set/get PA EDFA PLUS card automatic laser shutdown status for stage 2.
		-----------------------------
		Values:
		1 - Automatic laser shutdown function ON
		0 - Automatic laser shutdown function OFF
		-----------------------------"

		::= { paEdfaPlusConfigurationEntry 27 }

	paEdfaPlusModuleOperatingModeForStage1	OBJECT-TYPE
		SYNTAX  	DisplayString (SIZE (0..255))
		MAX-ACCESS  	read-write
		STATUS  	current

		DESCRIPTION
		 "To set/get PA EDFA PLUS card module operating mode of Stage 1.
		-----------------------------
		Values:
		APC - Automatic power control mode
		AGC - Automatic gain control mode
		ACC - Automatic current control mode
		-----------------------------"

		::= { paEdfaPlusConfigurationEntry 28 }

	paEdfaPlusModuleOperatingModeForStage2	OBJECT-TYPE
		SYNTAX  	DisplayString (SIZE (0..255))
		MAX-ACCESS  	read-write
		STATUS  	current

		DESCRIPTION
		 " to set/get PA EDFA PLUS card module operating mode of Stage 2.
		-----------------------------
		Values:
		APC - Automatic power control mode
		AGC - Automatic gain control mode
		ACC - Automatic current control mode
		-----------------------------"

		::= { paEdfaPlusConfigurationEntry 29 }		
      
	paEdfaPlusModuleGainInAutomaticGainControlModeForStage1 OBJECT-TYPE
		SYNTAX  	DisplayString (SIZE (0..255))
		MAX-ACCESS  	read-write
		STATUS  	current

		DESCRIPTION
		 " to set/get PA EDFA PLUS card module gain in automatic gain control mode for stage 1.
		-----------------------------
		Values:
		eg. : 15.5
		-----------------------------"

		::= { paEdfaPlusConfigurationEntry 30 }
		
	paEdfaPlusModuleGainInAutomaticGainControlModeForStage2 OBJECT-TYPE
		SYNTAX  	DisplayString (SIZE (0..255))
		MAX-ACCESS  	read-write
		STATUS  	current

		DESCRIPTION
		 " to set/get PA EDFA PLUS card module gain in automatic gain control mode for stage 2.
		-----------------------------
		Values:
		eg. : 15.5
		-----------------------------"

		::= { paEdfaPlusConfigurationEntry 31 }			
     
	paEdfaPlusModuleOutputPowerInAutomaticPowerControlMode OBJECT-TYPE
		SYNTAX  	DisplayString (SIZE (0..255))
		MAX-ACCESS  	read-write
		STATUS  	current

		DESCRIPTION
		 " to set/get PA EDFA PLUS card module output power in automatic power control mode.
		-----------------------------
		Values:
		eg. : 15.5
		-----------------------------"

		::= { paEdfaPlusConfigurationEntry 32 }		
    
	paEdfaPlusPump1OperatingCurrentInAutomaticCurrentControlMode OBJECT-TYPE
		SYNTAX  	DisplayString (SIZE (0..255))
		MAX-ACCESS  	read-write
		STATUS  	current

		DESCRIPTION
		 " to set/get PA EDFA PLUS card pump 1 operating current in automatic current control mode.
		-----------------------------
		Values:
		eg. : 15.5
		-----------------------------"

		::= { paEdfaPlusConfigurationEntry 33 }

	paEdfaPlusPump2OperatingCurrentInAutomaticCurrentControlMode OBJECT-TYPE
		SYNTAX  	DisplayString (SIZE (0..255))
		MAX-ACCESS  	read-write
		STATUS  	current

		DESCRIPTION
		 " to set/get PA EDFA PLUS card pump 2 operating current in automatic current control mode.
		-----------------------------
		Values:
		eg. : 15.5
		-----------------------------"

		::= { paEdfaPlusConfigurationEntry 34 }
              
    	paEdfaPlusGainTilt OBJECT-TYPE
		SYNTAX  	DisplayString (SIZE (0..255))
		MAX-ACCESS  	read-write
		STATUS  	current

		DESCRIPTION
		 " to set/get PA EDFA PLUS card gain tilt.
		-----------------------------
		Values:
		eg. : 15.5
		-----------------------------"

		::= { paEdfaPlusConfigurationEntry 35 } 
      
	paEdfaPlusVariableOpticalAttenuatorAttenuationForStage2 OBJECT-TYPE
		SYNTAX  	DisplayString (SIZE (0..255))
		MAX-ACCESS  	read-write
		STATUS  	current

		DESCRIPTION
		 " to set/get PA EDFA PLUS card variable optical attenuator attenuation.
		-----------------------------
		Values:
		eg. : 15.5
		-----------------------------"

		::= { paEdfaPlusConfigurationEntry 36 }	

	paEdfaPlusOutputPowerLimitFunctionStatusInAutomaticGainControlModeForStage1 OBJECT-TYPE
		SYNTAX  	INTEGER
		MAX-ACCESS  	read-write
		STATUS  	current

		DESCRIPTION
		 " to set/get PA EDFA PLUS card output power limit function enable/disable status in automatic gain control mode for stage 1.
		-----------------------------
		Values:
		1 - Output power limit function will be enabled 
		0 - Output power limit function will be disabled 
		-----------------------------"

		::= { paEdfaPlusConfigurationEntry 37 }

	paEdfaPlusOutputPowerLimitFunctionStatusInAutomaticGainControlModeForStage2 OBJECT-TYPE
		SYNTAX  	INTEGER
		MAX-ACCESS  	read-write
		STATUS  	current

		DESCRIPTION
		 " to set/get PA EDFA PLUS card output power limit function enable/disable status in automatic gain control mode for stage 2.
		-----------------------------
		Values:
		1 - Output power limit function will be enabled 
		0 - Output power limit function will be disabled 
		-----------------------------"

		::= { paEdfaPlusConfigurationEntry 38 }

	paEdfaPlusOutputPowerLimitInAutomaticGainControlModeForStage1 OBJECT-TYPE
		SYNTAX  	DisplayString (SIZE (0..255))
		MAX-ACCESS  	read-write
		STATUS  	current

		DESCRIPTION
		 " to set/get PA EDFA PLUS card output power limit in automatic gain control mode for stage 1.
		-----------------------------
		Values:
		eg. : 15.5
		-----------------------------"

		::= { paEdfaPlusConfigurationEntry 39 }

	paEdfaPlusOutputPowerLimitInAutomaticGainControlModeForStage2 OBJECT-TYPE
		SYNTAX  	DisplayString (SIZE (0..255))
		MAX-ACCESS  	read-write
		STATUS  	current

		DESCRIPTION
		 " to set/get PA EDFA PLUS card output power limit in automatic gain control mode for stage 2.
		-----------------------------
		Values:
		eg. : 15.5
		-----------------------------"

		::= { paEdfaPlusConfigurationEntry 40 }	
      
	paEdfaPlusAutomaticPowerReductionForStage1Threshold OBJECT-TYPE
		SYNTAX  	DisplayString (SIZE (0..255))
		MAX-ACCESS  	read-write
		STATUS  	current

		DESCRIPTION
		 " to set/get PA EDFA PLUS card automatic power reduction threshold for Stage 1.
		-----------------------------
		Values:
		eg. : 15.5
		-----------------------------"

		::= { paEdfaPlusConfigurationEntry 51 }		

	paEdfaPlusAutomaticPowerReductionForStage2Threshold OBJECT-TYPE
		SYNTAX  	DisplayString (SIZE (0..255))
		MAX-ACCESS  	read-write
		STATUS  	current

		DESCRIPTION
		 " to set/get PA EDFA PLUS card automatic power reduction threshold for Stage 2.
		-----------------------------
		Values:
		eg. : 15.5
		-----------------------------"

		::= { paEdfaPlusConfigurationEntry 52 }	
              
	paEdfaPlusOpticalInputPowerFailureAlarmForStage1Threshold OBJECT-TYPE
		SYNTAX  	DisplayString (SIZE (0..255))
		MAX-ACCESS  	read-write
		STATUS  	current

		DESCRIPTION
		 " to set/get PA EDFA PLUS card optical input power failure alarm threshold for stage 1.
		-----------------------------
		Values:
		eg. : -21.0
		-----------------------------"

		::= { paEdfaPlusConfigurationEntry 53 }	
   
	paEdfaPlusOpticalInputPowerFailureAlarmForStage2Threshold OBJECT-TYPE
		SYNTAX  	DisplayString (SIZE (0..255))
		MAX-ACCESS  	read-write
		STATUS  	current

		DESCRIPTION
		 " to set/get PA EDFA PLUS card optical input power failure alarm threshold for stage 2.
		-----------------------------
		Values:
		eg. : -21.0
		-----------------------------"

		::= { paEdfaPlusConfigurationEntry 54 }	
           
     	paEdfaPlusOpticalHighInputPowerAlarmForStage1Threshold OBJECT-TYPE
		SYNTAX  	DisplayString (SIZE (0..255))
		MAX-ACCESS  	read-write
		STATUS  	current

		DESCRIPTION
		 " to set/get PA EDFA PLUS card optical high input power alarm threshold for stage 1.
		-----------------------------
		Values:
		eg. : 3.0
		-----------------------------"

		::= { paEdfaPlusConfigurationEntry 55 }         

     	paEdfaPlusOpticalHighInputPowerAlarmForStage2Threshold OBJECT-TYPE
		SYNTAX  	DisplayString (SIZE (0..255))
		MAX-ACCESS  	read-write
		STATUS  	current

		DESCRIPTION
		 " to set/get PA EDFA PLUS card optical high input power alarm threshold for stage 2.
		-----------------------------
		Values:
		eg. : 3.0
		-----------------------------"

		::= { paEdfaPlusConfigurationEntry 56 } 
         
      	paEdfaPlusOpticalLowInputPowerAlarmForStage1Threshold  OBJECT-TYPE
		SYNTAX  	DisplayString (SIZE (0..255))
		MAX-ACCESS  	read-write
		STATUS  	current

		DESCRIPTION
		 " to set/get PA EDFA PLUS card optical low input power alarm threshold for stage 1.
		-----------------------------
		Values:
		eg. : -18.0
		-----------------------------"

		::= { paEdfaPlusConfigurationEntry 57 }

      	paEdfaPlusOpticalLowInputPowerAlarmForStage2Threshold  OBJECT-TYPE
		SYNTAX  	DisplayString (SIZE (0..255))
		MAX-ACCESS  	read-write
		STATUS  	current

		DESCRIPTION
		 " to set/get PA EDFA PLUS card optical low input power alarm threshold for stage 2.
		-----------------------------
		Values:
		eg. : -18.0
		-----------------------------"

		::= { paEdfaPlusConfigurationEntry 58 }

	paEdfaPlusOpticalHighInputPowerWarningForStage1Threshold OBJECT-TYPE
		SYNTAX  	DisplayString (SIZE (0..255))
		MAX-ACCESS  	read-write
		STATUS  	current

		DESCRIPTION
		 " to set/get PA EDFA PLUS card optical high input power warning threshold for stage 1.
		-----------------------------
		Values:
		eg. : 2.0
		-----------------------------"

		::= { paEdfaPlusConfigurationEntry 59 }         

	paEdfaPlusOpticalHighInputPowerWarningForStage2Threshold OBJECT-TYPE
		SYNTAX  	DisplayString (SIZE (0..255))
		MAX-ACCESS  	read-write
		STATUS  	current

		DESCRIPTION
		 " to set/get PA EDFA PLUS card optical high input power warning threshold for stage 2.
		-----------------------------
		Values:
		eg. : 2.0
		-----------------------------"

		::= { paEdfaPlusConfigurationEntry 60 }
         
      	paEdfaPlusOpticalLowInputPowerWarningForStage1Threshold  OBJECT-TYPE
		SYNTAX  	DisplayString (SIZE (0..255))
		MAX-ACCESS  	read-write
		STATUS  	current

		DESCRIPTION
		 " to set/get PA EDFA PLUS card optical low input power warning threshold for stage 1.
		-----------------------------
		Values:
		eg. : -19.0
		-----------------------------"

		::= { paEdfaPlusConfigurationEntry 61 } 

      	paEdfaPlusOpticalLowInputPowerWarningForStage2Threshold  OBJECT-TYPE
		SYNTAX  	DisplayString (SIZE (0..255))
		MAX-ACCESS  	read-write
		STATUS  	current

		DESCRIPTION
		 " to set/get PA EDFA PLUS card optical low input power warning threshold for stage 2.
		-----------------------------
		Values:
		eg. : -19.0
		-----------------------------"

		::= { paEdfaPlusConfigurationEntry 62 }

	paEdfaPlusOpticalOutputPowerFailureAlarmForStage1Threshold OBJECT-TYPE
		SYNTAX  	DisplayString (SIZE (0..255))
		MAX-ACCESS  	read-write
		STATUS  	current

		DESCRIPTION
		 " to set/get PA EDFA PLUS card optical output power failure alarm threshold for stage 1.
		-----------------------------
		Values:
		eg. : 5.0
		-----------------------------"

		::= { paEdfaPlusConfigurationEntry 63 }         
 
	paEdfaPlusOpticalOutputPowerFailureAlarmForStage2Threshold OBJECT-TYPE
		SYNTAX  	DisplayString (SIZE (0..255))
		MAX-ACCESS  	read-write
		STATUS  	current

		DESCRIPTION
		 " to set/get PA EDFA PLUS card optical output power failure alarm threshold for stage 2.
		-----------------------------
		Values:
		eg. : 5.0
		-----------------------------"

		::= { paEdfaPlusConfigurationEntry 64 }
        
      	paEdfaPlusOpticalHighOutputPowerAlarmForStage1Threshold  OBJECT-TYPE
		SYNTAX  	DisplayString (SIZE (0..255))
		MAX-ACCESS  	read-write
		STATUS  	current

		DESCRIPTION
		 " to set/get PA EDFA PLUS card optical high output power alarm threshold for stage 1.
		-----------------------------
		Values:
		eg. : 19.0
		-----------------------------"

		::= { paEdfaPlusConfigurationEntry 65 }

      	paEdfaPlusOpticalHighOutputPowerAlarmForStage2Threshold  OBJECT-TYPE
		SYNTAX  	DisplayString (SIZE (0..255))
		MAX-ACCESS  	read-write
		STATUS  	current

		DESCRIPTION
		 " to set/get PA EDFA PLUS card optical high output power alarm threshold for stage 2.
		-----------------------------
		Values:
		eg. : 19.0
		-----------------------------"

		::= { paEdfaPlusConfigurationEntry 66 } 

	paEdfaPlusOpticalLowOutputPowerAlarmForStage1Threshold OBJECT-TYPE
		SYNTAX  	DisplayString (SIZE (0..255))
		MAX-ACCESS  	read-write
		STATUS  	current

		DESCRIPTION
		 " to set/get PA EDFA PLUS card optical low output power alarm threshold for stage 1.
		-----------------------------
		Values:
		eg. : 10.0
		-----------------------------"

		::= { paEdfaPlusConfigurationEntry 67 }         

	paEdfaPlusOpticalLowOutputPowerAlarmForStage2Threshold OBJECT-TYPE
		SYNTAX  	DisplayString (SIZE (0..255))
		MAX-ACCESS  	read-write
		STATUS  	current

		DESCRIPTION
		 " to set/get PA EDFA PLUS card optical low output power alarm threshold for stage 2.
		-----------------------------
		Values:
		eg. : 10.0
		-----------------------------"

		::= { paEdfaPlusConfigurationEntry 68 }  
         
      	paEdfaPlusOpticalHighOutputPowerWarningForStage1Threshold  OBJECT-TYPE
		SYNTAX  	DisplayString (SIZE (0..255))
		MAX-ACCESS  	read-write
		STATUS  	current

		DESCRIPTION
		 " to set/get PA EDFA PLUS card optical high output power warning threshold for stage 1.
		-----------------------------
		Values:
		eg. : 18.0
		-----------------------------"

		::= { paEdfaPlusConfigurationEntry 69 } 

      	paEdfaPlusOpticalHighOutputPowerWarningForStage2Threshold  OBJECT-TYPE
		SYNTAX  	DisplayString (SIZE (0..255))
		MAX-ACCESS  	read-write
		STATUS  	current

		DESCRIPTION
		 " to set/get PA EDFA PLUS card optical high output power warning threshold for stage 2.
		-----------------------------
		Values:
		eg. : 18.0
		-----------------------------"

		::= { paEdfaPlusConfigurationEntry 70 } 

	paEdfaPlusOpticalLowOutputPowerWarningForStage1Threshold OBJECT-TYPE
		SYNTAX  	DisplayString (SIZE (0..255))
		MAX-ACCESS  	read-write
		STATUS  	current

		DESCRIPTION
		 " to set/get PA EDFA PLUS card optical low output power warning threshold for stage 1.
		-----------------------------
		Values:
		eg. : 1.0
		-----------------------------"

		::= { paEdfaPlusConfigurationEntry 71 }         

	paEdfaPlusOpticalLowOutputPowerWarningForStage2Threshold OBJECT-TYPE
		SYNTAX  	DisplayString (SIZE (0..255))
		MAX-ACCESS  	read-write
		STATUS  	current

		DESCRIPTION
		 " to set/get PA EDFA PLUS card optical low output power warning threshold for stage 2.
		-----------------------------
		Values:
		eg. : 1.0
		-----------------------------"

		::= { paEdfaPlusConfigurationEntry 72 }
         
      	paEdfaPlusModuleHighTemperatureAlarmThreshold  OBJECT-TYPE
		SYNTAX  	DisplayString (SIZE (0..255))
		MAX-ACCESS  	read-write
		STATUS  	current

		DESCRIPTION
		 " to set/get PA EDFA PLUS card module high temperature alarm threshold.
		-----------------------------
		Values:
		eg. : 75.0
		-----------------------------"

		::= { paEdfaPlusConfigurationEntry 73 } 

	paEdfaPlusModuleLowTemperatureAlarmThreshold OBJECT-TYPE
		SYNTAX  	DisplayString (SIZE (0..255))
		MAX-ACCESS  	read-write
		STATUS  	current

		DESCRIPTION
		 " to set/get PA EDFA PLUS card module low temperature alarm threshold.
		-----------------------------
		Values:
		eg. : 5.0
		-----------------------------"

		::= { paEdfaPlusConfigurationEntry 74 }         
         
      	paEdfaPlusModuleHighTemperatureWarningThreshold  OBJECT-TYPE
		SYNTAX  	DisplayString (SIZE (0..255))
		MAX-ACCESS  	read-write
		STATUS  	current

		DESCRIPTION
		 " to set/get PA EDFA PLUS card module high temperature warning threshold.
		-----------------------------
		Values:
		eg. : 60.0
		-----------------------------"

		::= { paEdfaPlusConfigurationEntry 75 }             

	paEdfaPlusModuleLowTemperatureWarningThreshold  OBJECT-TYPE
		SYNTAX  	DisplayString (SIZE (0..255))
		MAX-ACCESS  	read-write
		STATUS  	current

		DESCRIPTION
		 " to set/get PA EDFA PLUS card module low temperature warning threshold.
		-----------------------------
		Values:
		eg. : 8.0
		-----------------------------"

		::= { paEdfaPlusConfigurationEntry 76 }

	paEdfaPlusPump1HighTemperatureAlarmThreshold  OBJECT-TYPE
		SYNTAX  	DisplayString (SIZE (0..255))
		MAX-ACCESS  	read-write
		STATUS  	current

		DESCRIPTION
		 " to set/get PA EDFA PLUS card pump 1 high temperature alarm threshold.
		-----------------------------
		Values:
		eg. : 75.0
		-----------------------------"

		::= { paEdfaPlusConfigurationEntry 77 }

	paEdfaPlusPump2HighTemperatureAlarmThreshold  OBJECT-TYPE
		SYNTAX  	DisplayString (SIZE (0..255))
		MAX-ACCESS  	read-write
		STATUS  	current

		DESCRIPTION
		 " to set/get PA EDFA PLUS card pump 2 high temperature alarm threshold.
		-----------------------------
		Values:
		eg. : 75.0
		-----------------------------"

		::= { paEdfaPlusConfigurationEntry 78 }

	paEdfaPlusPump1LowTemperatureAlarmThreshold  OBJECT-TYPE
		SYNTAX  	DisplayString (SIZE (0..255))
		MAX-ACCESS  	read-write
		STATUS  	current

		DESCRIPTION
		 " to set/get PA EDFA PLUS card pump 1 low temperature alarm threshold.
		-----------------------------
		Values:
		eg. : 5.0
		-----------------------------"

		::= { paEdfaPlusConfigurationEntry 79 }

	paEdfaPlusPump2LowTemperatureAlarmThreshold  OBJECT-TYPE
		SYNTAX  	DisplayString (SIZE (0..255))
		MAX-ACCESS  	read-write
		STATUS  	current

		DESCRIPTION
		 " to set/get PA EDFA PLUS card pump 2 low temperature alarm threshold.
		-----------------------------
		Values:
		eg. : 5.0
		-----------------------------"

		::= { paEdfaPlusConfigurationEntry 80 }

	paEdfaPlusPump1HighTemperatureWarningThreshold  OBJECT-TYPE
		SYNTAX  	DisplayString (SIZE (0..255))
		MAX-ACCESS  	read-write
		STATUS  	current

		DESCRIPTION
		 " to set/get PA EDFA PLUS card pump 1 high temperature warning threshold.
		-----------------------------
		Values:
		eg. : 60.0
		-----------------------------"

		::= { paEdfaPlusConfigurationEntry 81 }

	paEdfaPlusPump2HighTemperatureWarningThreshold  OBJECT-TYPE
		SYNTAX  	DisplayString (SIZE (0..255))
		MAX-ACCESS  	read-write
		STATUS  	current

		DESCRIPTION
		 " to set/get PA EDFA PLUS card pump 2 high temperature warning threshold.
		-----------------------------
		Values:
		eg. : 60.0
		-----------------------------"

		::= { paEdfaPlusConfigurationEntry 82 }

	paEdfaPlusPump1LowTemperatureWarningThreshold  OBJECT-TYPE
		SYNTAX  	DisplayString (SIZE (0..255))
		MAX-ACCESS  	read-write
		STATUS  	current

		DESCRIPTION
		 " to set/get PA EDFA PLUS card pump 1 low temperature warning threshold.
		-----------------------------
		Values:
		eg. : 8.0
		-----------------------------"

		::= { paEdfaPlusConfigurationEntry 83 }

	paEdfaPlusPump2LowTemperatureWarningThreshold  OBJECT-TYPE
		SYNTAX  	DisplayString (SIZE (0..255))
		MAX-ACCESS  	read-write
		STATUS  	current

		DESCRIPTION
		 " to set/get PA EDFA PLUS card pump 2 low temperature warning threshold.
		-----------------------------
		Values:
		eg. : 8.0
		-----------------------------"

		::= { paEdfaPlusConfigurationEntry 84 }

	paEdfaPlusPump1HighOperatingCurrentAlarmThreshold  OBJECT-TYPE
		SYNTAX  	DisplayString (SIZE (0..255))
		MAX-ACCESS  	read-write
		STATUS  	current

		DESCRIPTION
		 " to set/get PA EDFA PLUS card pump 1 high operating current alarm threshold.
		-----------------------------
		Values:
		eg. : 15.5
		-----------------------------"

		::= { paEdfaPlusConfigurationEntry 85 }

	paEdfaPlusPump2HighOperatingCurrentAlarmThreshold  OBJECT-TYPE
		SYNTAX  	DisplayString (SIZE (0..255))
		MAX-ACCESS  	read-write
		STATUS  	current

		DESCRIPTION
		 " to set/get PA EDFA PLUS card pump 2 high operating current alarm threshold.
		-----------------------------
		Values:
		eg. : 15.5
		-----------------------------"

		::= { paEdfaPlusConfigurationEntry 86 }

	paEdfaPlusPump1LowOperatingCurrentAlarmThreshold  OBJECT-TYPE
		SYNTAX  	DisplayString (SIZE (0..255))
		MAX-ACCESS  	read-write
		STATUS  	current

		DESCRIPTION
		 " to set/get PA EDFA PLUS card pump 1 low operating current alarm threshold.
		-----------------------------
		Values:
		eg. : 15.5
		-----------------------------"

		::= { paEdfaPlusConfigurationEntry 87 }

	paEdfaPlusPump2LowOperatingCurrentAlarmThreshold  OBJECT-TYPE
		SYNTAX  	DisplayString (SIZE (0..255))
		MAX-ACCESS  	read-write
		STATUS  	current

		DESCRIPTION
		 " to set/get PA EDFA PLUS card pump 2 low operating current alarm threshold.
		-----------------------------
		Values:
		eg. : 15.5
		-----------------------------"

		::= { paEdfaPlusConfigurationEntry 88 }
	
	paEdfaPlusPump1HighOperatingCurrentWarningThreshold  OBJECT-TYPE
		SYNTAX  	DisplayString (SIZE (0..255))
		MAX-ACCESS  	read-write
		STATUS  	current

		DESCRIPTION
		 " to set/get PA EDFA PLUS card pump 1 high operating current warning threshold.
		-----------------------------
		Values:
		eg. : 15.5
		-----------------------------"

		::= { paEdfaPlusConfigurationEntry 89 }

	paEdfaPlusPump2HighOperatingCurrentWarningThreshold  OBJECT-TYPE
		SYNTAX  	DisplayString (SIZE (0..255))
		MAX-ACCESS  	read-write
		STATUS  	current

		DESCRIPTION
		 " to set/get PA EDFA PLUS card pump 2 high operating current warning threshold.
		-----------------------------
		Values:
		eg. : 15.5
		-----------------------------"

		::= { paEdfaPlusConfigurationEntry 90 }

	paEdfaPlusPump1LowOperatingCurrentWarningThreshold  OBJECT-TYPE
		SYNTAX  	DisplayString (SIZE (0..255))
		MAX-ACCESS  	read-write
		STATUS  	current

		DESCRIPTION
		 " to set/get PA EDFA PLUS card pump 1 high operating current warning threshold.
		-----------------------------
		Values:
		eg. : 15.5
		-----------------------------"

		::= { paEdfaPlusConfigurationEntry 91 }

	paEdfaPlusPump2LowOperatingCurrentWarningThreshold  OBJECT-TYPE
		SYNTAX  	DisplayString (SIZE (0..255))
		MAX-ACCESS  	read-write
		STATUS  	current

		DESCRIPTION
		 " to set/get PA EDFA PLUS card pump 2 high operating current warning threshold.
		-----------------------------
		Values:
		eg. : 15.5
		-----------------------------"

		::= { paEdfaPlusConfigurationEntry 92 }

	paEdfaPlusPump1HighThermoElectricCoolerCurrentAlarmThreshold  OBJECT-TYPE
		SYNTAX  	DisplayString (SIZE (0..255))
		MAX-ACCESS  	read-write
		STATUS  	current

		DESCRIPTION
		 " to set/get PA EDFA PLUS card pump 1 high thermo electric cooler current alarm threshold.
		-----------------------------
		Values:
		eg. : 15.5
		-----------------------------"

		::= { paEdfaPlusConfigurationEntry 93 }

	paEdfaPlusPump2HighThermoElectricCoolerCurrentAlarmThreshold  OBJECT-TYPE
		SYNTAX  	DisplayString (SIZE (0..255))
		MAX-ACCESS  	read-write
		STATUS  	current

		DESCRIPTION
		 " to set/get PA EDFA PLUS card pump 2 high thermo electric cooler current alarm threshold.
		-----------------------------
		Values:
		eg. : 15.5
		-----------------------------"

		::= { paEdfaPlusConfigurationEntry 94 }

	paEdfaPlusPump1LowThermoElectricCoolerCurrentAlarmThreshold  OBJECT-TYPE
		SYNTAX  	DisplayString (SIZE (0..255))
		MAX-ACCESS  	read-write
		STATUS  	current

		DESCRIPTION
		 " to set/get PA EDFA PLUS card pump 1 low thermo electric cooler current alarm threshold.
		-----------------------------
		Values:
		eg. : 15.5
		-----------------------------"

		::= { paEdfaPlusConfigurationEntry 95 }

	paEdfaPlusPump2LowThermoElectricCoolerCurrentAlarmThreshold  OBJECT-TYPE
		SYNTAX  	DisplayString (SIZE (0..255))
		MAX-ACCESS  	read-write
		STATUS  	current

		DESCRIPTION
		 " to set/get PA EDFA PLUS card pump 2 low thermo electric cooler current alarm threshold.
		-----------------------------
		Values:
		eg. : 15.5
		-----------------------------"

		::= { paEdfaPlusConfigurationEntry 96 }

	paEdfaPlusPump1HighThermoElectricCoolerCurrentWarningThreshold  OBJECT-TYPE
		SYNTAX  	DisplayString (SIZE (0..255))
		MAX-ACCESS  	read-write
		STATUS  	current

		DESCRIPTION
		 " to set/get PA EDFA PLUS card pump 1 high thermo electric cooler current warning threshold.
		-----------------------------
		Values:
		eg. : 15.5
		-----------------------------"

		::= { paEdfaPlusConfigurationEntry 97 }

	paEdfaPlusPump2HighThermoElectricCoolerCurrentWarningThreshold  OBJECT-TYPE
		SYNTAX  	DisplayString (SIZE (0..255))
		MAX-ACCESS  	read-write
		STATUS  	current

		DESCRIPTION
		 " to set/get PA EDFA PLUS card pump 2 high thermo electric cooler current warning threshold.
		-----------------------------
		Values:
		eg. : 15.5
		-----------------------------"

		::= { paEdfaPlusConfigurationEntry 98 }

	paEdfaPlusPump1LowThermoElectricCoolerCurrentWarningThreshold  OBJECT-TYPE
		SYNTAX  	DisplayString (SIZE (0..255))
		MAX-ACCESS  	read-write
		STATUS  	current

		DESCRIPTION
		 " to set/get PA EDFA PLUS card pump 1 low thermo electric cooler current warning threshold.
		-----------------------------
		Values:
		eg. : 15.5
		-----------------------------"

		::= { paEdfaPlusConfigurationEntry 99 }

	paEdfaPlusPump2LowThermoElectricCoolerCurrentWarningThreshold  OBJECT-TYPE
		SYNTAX  	DisplayString (SIZE (0..255))
		MAX-ACCESS  	read-write
		STATUS  	current

		DESCRIPTION
		 " to set/get PA EDFA PLUS card pump 2 low thermo electric cooler current warning threshold.
		-----------------------------
		Values:
		eg. : 15.5
		-----------------------------"

		::= { paEdfaPlusConfigurationEntry 100 }

	paEdfaPlusVariableOpticalAttenuatorHighInputPowerAlarmThreshold  OBJECT-TYPE
		SYNTAX  	DisplayString (SIZE (0..255))
		MAX-ACCESS  	read-write
		STATUS  	current

		DESCRIPTION
		 " to set/get PA EDFA PLUS card variable optical attenuator high input power alarm threshold.
		-----------------------------
		Values:
		eg. : 15.5
		-----------------------------"

		::= { paEdfaPlusConfigurationEntry 101 }

	paEdfaPlusVariableOpticalAttenuatorLowInputPowerAlarmThreshold  OBJECT-TYPE
		SYNTAX  	DisplayString (SIZE (0..255))
		MAX-ACCESS  	read-write
		STATUS  	current

		DESCRIPTION
		 " to set/get PA EDFA PLUS card variable optical attenuator low input power alarm threshold.
		-----------------------------
		Values:
		eg. : 15.5
		-----------------------------"

		::= { paEdfaPlusConfigurationEntry 102 }

	paEdfaPlusVariableOpticalAttenuatorHighInputPowerWarningThreshold  OBJECT-TYPE
		SYNTAX  	DisplayString (SIZE (0..255))
		MAX-ACCESS  	read-write
		STATUS  	current

		DESCRIPTION
		 " to set/get PA EDFA PLUS card variable optical attenuator high input power warning threshold.
		-----------------------------
		Values:
		eg. : 15.5
		-----------------------------"

		::= { paEdfaPlusConfigurationEntry 103 }

	paEdfaPlusVariableOpticalAttenuatorLowInputPowerWarningThreshold  OBJECT-TYPE
		SYNTAX  	DisplayString (SIZE (0..255))
		MAX-ACCESS  	read-write
		STATUS  	current

		DESCRIPTION
		 " to set/get PA EDFA PLUS card variable optical attenuator low input power alarm threshold.
		-----------------------------
		Values:
		eg. : 15.5
		-----------------------------"

		::= { paEdfaPlusConfigurationEntry 104 }

	paEdfaPlusOpticalInputPowerFailureAlarmForStage1Inhibit OBJECT-TYPE
		SYNTAX  	INTEGER
		MAX-ACCESS  	read-write
		STATUS  	current

		DESCRIPTION
		 " to set/get PA EDFA PLUS card optical input power failure alarm inhibit status for stage 1.
		-----------------------------
		Value:
		1 - Inhibit
		0 - Do Not Inhibit
		-----------------------------"

		::= { paEdfaPlusConfigurationEntry 131 }	                                              

	paEdfaPlusOpticalInputPowerFailureAlarmForStage2Inhibit OBJECT-TYPE
		SYNTAX  	INTEGER
		MAX-ACCESS  	read-write
		STATUS  	current

		DESCRIPTION
		 " to set/get PA EDFA PLUS card optical input power failure alarm inhibit status for stage 2.
		-----------------------------
		Value:
		1 - Inhibit
		0 - Do Not Inhibit
		-----------------------------"

		::= { paEdfaPlusConfigurationEntry 132 }
                      
	paEdfaPlusOpticalHighInputPowerAlarmForStage1Inhibit OBJECT-TYPE
		SYNTAX  	INTEGER
		MAX-ACCESS  	read-write
		STATUS  	current

		DESCRIPTION
		 " to set/get PA EDFA PLUS card optical high input power alarm inhibit status for stage 1.
		-----------------------------
		Value:
		1 - Inhibit
		0 - Do Not Inhibit
		-----------------------------"

		::= { paEdfaPlusConfigurationEntry 133 }	              

	paEdfaPlusOpticalHighInputPowerAlarmForStage2Inhibit OBJECT-TYPE
		SYNTAX  	INTEGER
		MAX-ACCESS  	read-write
		STATUS  	current

		DESCRIPTION
		 " to set/get PA EDFA PLUS card optical high input power alarm inhibit status for stage 2.
		-----------------------------
		Value:
		1 - Inhibit
		0 - Do Not Inhibit
		-----------------------------"

		::= { paEdfaPlusConfigurationEntry 134 }
                      
	paEdfaPlusOpticalLowInputPowerAlarmForStage1Inhibit OBJECT-TYPE
		SYNTAX  	INTEGER
		MAX-ACCESS  	read-write
		STATUS  	current

		DESCRIPTION
		 " to set/get PA EDFA PLUS card optical low input power alarm inhibit status for stage 1.
		-----------------------------
		Value:
		1 - Inhibit
		0 - Do Not Inhibit
		-----------------------------"

		::= { paEdfaPlusConfigurationEntry 135 }	              

	paEdfaPlusOpticalLowInputPowerAlarmForStage2Inhibit OBJECT-TYPE
		SYNTAX  	INTEGER
		MAX-ACCESS  	read-write
		STATUS  	current

		DESCRIPTION
		 " to set/get PA EDFA PLUS card optical low input power alarm inhibit status for stage 2.
		-----------------------------
		Value:
		1 - Inhibit
		0 - Do Not Inhibit
		-----------------------------"

		::= { paEdfaPlusConfigurationEntry 136 }
                      
	paEdfaPlusOpticalHighInputPowerWarningForStage1Inhibit OBJECT-TYPE
		SYNTAX  	INTEGER
		MAX-ACCESS  	read-write
		STATUS  	current

		DESCRIPTION
		 " to set/get PA EDFA PLUS card optical high input power warning inhibit status for stage 1.
		-----------------------------
		Value:
		1 - Inhibit
		0 - Do Not Inhibit
		-----------------------------"

		::= { paEdfaPlusConfigurationEntry 137 }	              

	paEdfaPlusOpticalHighInputPowerWarningForStage2Inhibit OBJECT-TYPE
		SYNTAX  	INTEGER
		MAX-ACCESS  	read-write
		STATUS  	current

		DESCRIPTION
		 " to set/get PA EDFA PLUS card optical high input power warning inhibit status for stage 2.
		-----------------------------
		Value:
		1 - Inhibit
		0 - Do Not Inhibit
		-----------------------------"

		::= { paEdfaPlusConfigurationEntry 138 }
                      
	paEdfaPlusOpticalLowInputPowerWarningForStage1Inhibit OBJECT-TYPE
		SYNTAX  	INTEGER
		MAX-ACCESS  	read-write
		STATUS  	current

		DESCRIPTION
		 " to set/get PA EDFA PLUS card optical low input power warning inhibit status for stage 1.
		-----------------------------
		Value:
		1 - Inhibit
		0 - Do Not Inhibit
		-----------------------------"

		::= { paEdfaPlusConfigurationEntry 139 }              

	paEdfaPlusOpticalLowInputPowerWarningForStage2Inhibit OBJECT-TYPE
		SYNTAX  	INTEGER
		MAX-ACCESS  	read-write
		STATUS  	current

		DESCRIPTION
		 " to set/get PA EDFA PLUS card optical low input power warning inhibit status for stage 2.
		-----------------------------
		Value:
		1 - Inhibit
		0 - Do Not Inhibit
		-----------------------------"

		::= { paEdfaPlusConfigurationEntry 140 } 
                    
	paEdfaPlusOpticalOutputPowerFailureAlarmForStage1Inhibit OBJECT-TYPE
		SYNTAX  	INTEGER
		MAX-ACCESS  	read-write
		STATUS  	current

		DESCRIPTION
		 " to set/get PA EDFA PLUS card optical output power failure alarm inhibit status for stage 1.
		-----------------------------
		Value:
		1 - Inhibit
		0 - Do Not Inhibit
		-----------------------------"

		::= { paEdfaPlusConfigurationEntry 141 }

	paEdfaPlusOpticalOutputPowerFailureAlarmForStage2Inhibit OBJECT-TYPE
		SYNTAX  	INTEGER
		MAX-ACCESS  	read-write
		STATUS  	current

		DESCRIPTION
		 " to set/get PA EDFA PLUS card optical output power failure alarm inhibit status for stage 2.
		-----------------------------
		Value:
		1 - Inhibit
		0 - Do Not Inhibit
		-----------------------------"

		::= { paEdfaPlusConfigurationEntry 142 }


	paEdfaPlusOpticalHighOutputPowerAlarmForStage1Inhibit OBJECT-TYPE
		SYNTAX  	INTEGER
		MAX-ACCESS  	read-write
		STATUS  	current

		DESCRIPTION
		 " to set/get PA EDFA PLUS card optical high output power alarm inhibit status for stage 1.
		-----------------------------
		Value:
		1 - Inhibit
		0 - Do Not Inhibit
		-----------------------------"

		::= { paEdfaPlusConfigurationEntry 143 }

	paEdfaPlusOpticalHighOutputPowerAlarmForStage2Inhibit OBJECT-TYPE
		SYNTAX  	INTEGER
		MAX-ACCESS  	read-write
		STATUS  	current

		DESCRIPTION
		 " to set/get PA EDFA PLUS card optical high output power alarm inhibit status for stage 2.
		-----------------------------
		Value:
		1 - Inhibit
		0 - Do Not Inhibit
		-----------------------------"

		::= { paEdfaPlusConfigurationEntry 144 }

	paEdfaPlusOpticalLowOutputPowerAlarmForStage1Inhibit OBJECT-TYPE
		SYNTAX  	INTEGER
		MAX-ACCESS  	read-write
		STATUS  	current

		DESCRIPTION
		 " to set/get PA EDFA PLUS card optical low output power alarm inhibit status for stage 1.
		-----------------------------
		Value:
		1 - Inhibit
		0 - Do Not Inhibit
		-----------------------------"

		::= { paEdfaPlusConfigurationEntry 145 }

	paEdfaPlusOpticalLowOutputPowerAlarmForStage2Inhibit OBJECT-TYPE
		SYNTAX  	INTEGER
		MAX-ACCESS  	read-write
		STATUS  	current

		DESCRIPTION
		 " to set/get PA EDFA PLUS card optical low output power alarm inhibit status for stage 2.
		-----------------------------
		Value:
		1 - Inhibit
		0 - Do Not Inhibit
		-----------------------------"

		::= { paEdfaPlusConfigurationEntry 146 }

	paEdfaPlusOpticalHighOutputPowerWarningForStage1Inhibit OBJECT-TYPE
		SYNTAX  	INTEGER
		MAX-ACCESS  	read-write
		STATUS  	current

		DESCRIPTION
		 " to set/get PA EDFA PLUS card optical high output power warning inhibit status for stage 1.
		-----------------------------
		Value:
		1 - Inhibit
		0 - Do Not Inhibit
		-----------------------------"

		::= { paEdfaPlusConfigurationEntry 147 }

	paEdfaPlusOpticalHighOutputPowerWarningForStage2Inhibit OBJECT-TYPE
		SYNTAX  	INTEGER
		MAX-ACCESS  	read-write
		STATUS  	current

		DESCRIPTION
		 " to set/get PA EDFA PLUS card optical high output power warning inhibit status for stage 2.
		-----------------------------
		Value:
		1 - Inhibit
		0 - Do Not Inhibit
		-----------------------------"

		::= { paEdfaPlusConfigurationEntry 148 }

	paEdfaPlusOpticalLowOutputPowerWarningForStage1Inhibit OBJECT-TYPE
		SYNTAX  	INTEGER
		MAX-ACCESS  	read-write
		STATUS  	current

		DESCRIPTION
		 " to set/get PA EDFA PLUS card optical low output power warning inhibit status for stage 1.
		-----------------------------
		Value:
		1 - Inhibit
		0 - Do Not Inhibit
		-----------------------------"

		::= { paEdfaPlusConfigurationEntry 149 }

	paEdfaPlusOpticalLowOutputPowerWarningForStage2Inhibit OBJECT-TYPE
		SYNTAX  	INTEGER
		MAX-ACCESS  	read-write
		STATUS  	current

		DESCRIPTION
		 " to set/get PA EDFA PLUS card optical low output power warning inhibit status for stage 2.
		-----------------------------
		Value:
		1 - Inhibit
		0 - Do Not Inhibit
		-----------------------------"

		::= { paEdfaPlusConfigurationEntry 150 }

	paEdfaPlusModuleHighTemperatureAlarmInhibit OBJECT-TYPE
		SYNTAX  	INTEGER
		MAX-ACCESS  	read-write
		STATUS  	current

		DESCRIPTION
		 " to set/get PA EDFA PLUS card module high temperature alarm inhibit status.
		-----------------------------
		Value:
		1 - Inhibit
		0 - Do Not Inhibit
		-----------------------------"

		::= { paEdfaPlusConfigurationEntry 151 }

	paEdfaPlusModuleLowTemperatureAlarmInhibit OBJECT-TYPE
		SYNTAX  	INTEGER
		MAX-ACCESS  	read-write
		STATUS  	current

		DESCRIPTION
		 " to set/get PA EDFA PLUS card module low temperature alarm inhibit status.
		-----------------------------
		Value:
		1 - Inhibit
		0 - Do Not Inhibit
		-----------------------------"

		::= { paEdfaPlusConfigurationEntry 152 }

	paEdfaPlusModuleHighTemperatureWarningInhibit OBJECT-TYPE
		SYNTAX  	INTEGER
		MAX-ACCESS  	read-write
		STATUS  	current

		DESCRIPTION
		 " to set/get PA EDFA PLUS card module high temperature warning inhibit status.
		-----------------------------
		Value:
		1 - Inhibit
		0 - Do Not Inhibit
		-----------------------------"

		::= { paEdfaPlusConfigurationEntry 153 }

	paEdfaPlusModuleLowTemperatureWarningInhibit OBJECT-TYPE
		SYNTAX  	INTEGER
		MAX-ACCESS  	read-write
		STATUS  	current

		DESCRIPTION
		 " to set/get PA EDFA PLUS card module low temperature warning inhibit status.
		-----------------------------
		Value:
		1 - Inhibit
		0 - Do Not Inhibit
		-----------------------------"

		::= { paEdfaPlusConfigurationEntry 154 }

	paEdfaPlusPump1HighTemperatureAlarmInhibit OBJECT-TYPE
		SYNTAX  	INTEGER
		MAX-ACCESS  	read-write
		STATUS  	current

		DESCRIPTION
		 " to set/get PA EDFA PLUS card pump 1 high temperature alarm inhibit status.
		-----------------------------
		Value:
		1 - Inhibit
		0 - Do Not Inhibit
		-----------------------------"

		::= { paEdfaPlusConfigurationEntry 155 }

	paEdfaPlusPump2HighTemperatureAlarmInhibit OBJECT-TYPE
		SYNTAX  	INTEGER
		MAX-ACCESS  	read-write
		STATUS  	current

		DESCRIPTION
		 " to set/get PA EDFA PLUS card pump 2 high temperature alarm inhibit status.
		-----------------------------
		Value:
		1 - Inhibit
		0 - Do Not Inhibit
		-----------------------------"

		::= { paEdfaPlusConfigurationEntry 156 }

	paEdfaPlusPump1LowTemperatureAlarmInhibit OBJECT-TYPE
		SYNTAX  	INTEGER
		MAX-ACCESS  	read-write
		STATUS  	current

		DESCRIPTION
		 " to set/get PA EDFA PLUS card pump 1 low temperature alarm inhibit status.
		-----------------------------
		Value:
		1 - Inhibit
		0 - Do Not Inhibit
		-----------------------------"

		::= { paEdfaPlusConfigurationEntry 157 }

	paEdfaPlusPump2LowTemperatureAlarmInhibit OBJECT-TYPE
		SYNTAX  	INTEGER
		MAX-ACCESS  	read-write
		STATUS  	current

		DESCRIPTION
		 " to set/get PA EDFA PLUS card pump 2 low temperature alarm inhibit status.
		-----------------------------
		Value:
		1 - Inhibit
		0 - Do Not Inhibit
		-----------------------------"

		::= { paEdfaPlusConfigurationEntry 158 }

	paEdfaPlusPump1HighTemperatureWarningInhibit OBJECT-TYPE
		SYNTAX  	INTEGER
		MAX-ACCESS  	read-write
		STATUS  	current

		DESCRIPTION
		 " to set/get PA EDFA PLUS card pump 1 high temperature warning inhibit status.
		-----------------------------
		Value:
		1 - Inhibit
		0 - Do Not Inhibit
		-----------------------------"

		::= { paEdfaPlusConfigurationEntry 159 }

	paEdfaPlusPump2HighTemperatureWarningInhibit OBJECT-TYPE
		SYNTAX  	INTEGER
		MAX-ACCESS  	read-write
		STATUS  	current

		DESCRIPTION
		 " to set/get PA EDFA PLUS card pump 2 high temperature warning inhibit status.
		-----------------------------
		Value:
		1 - Inhibit
		0 - Do Not Inhibit
		-----------------------------"

		::= { paEdfaPlusConfigurationEntry 160 }

	paEdfaPlusPump1LowTemperatureWarningInhibit OBJECT-TYPE
		SYNTAX  	INTEGER
		MAX-ACCESS  	read-write
		STATUS  	current

		DESCRIPTION
		 " to set/get PA EDFA PLUS card pump 1 low temperature warning inhibit status.
		-----------------------------
		Value:
		1 - Inhibit
		0 - Do Not Inhibit
		-----------------------------"

		::= { paEdfaPlusConfigurationEntry 161 }

	paEdfaPlusPump2LowTemperatureWarningInhibit OBJECT-TYPE
		SYNTAX  	INTEGER
		MAX-ACCESS  	read-write
		STATUS  	current

		DESCRIPTION
		 " to set/get PA EDFA PLUS card pump 2 low temperature warning inhibit status.
		-----------------------------
		Value:
		1 - Inhibit
		0 - Do Not Inhibit
		-----------------------------"

		::= { paEdfaPlusConfigurationEntry 162 }

	paEdfaPlusPump1HighOperatingCurrentAlarmInhibit OBJECT-TYPE
		SYNTAX  	INTEGER
		MAX-ACCESS  	read-write
		STATUS  	current

		DESCRIPTION
		 " to set/get PA EDFA PLUS card pump 1 high operating current alarm inhibit status.
		-----------------------------
		Value:
		1 - Inhibit
		0 - Do Not Inhibit
		-----------------------------"

		::= { paEdfaPlusConfigurationEntry 163 }

	paEdfaPlusPump2HighOperatingCurrentAlarmInhibit OBJECT-TYPE
		SYNTAX  	INTEGER
		MAX-ACCESS  	read-write
		STATUS  	current

		DESCRIPTION
		 " to set/get PA EDFA PLUS card pump 2 high operating current alarm inhibit status.
		-----------------------------
		Value:
		1 - Inhibit
		0 - Do Not Inhibit
		-----------------------------"

		::= { paEdfaPlusConfigurationEntry 164 }

	paEdfaPlusPump1LowOperatingCurrentAlarmInhibit OBJECT-TYPE
		SYNTAX  	INTEGER
		MAX-ACCESS  	read-write
		STATUS  	current

		DESCRIPTION
		 " to set/get PA EDFA PLUS card pump 1 low operating current alarm inhibit status.
		-----------------------------
		Value:
		1 - Inhibit
		0 - Do Not Inhibit
		-----------------------------"

		::= { paEdfaPlusConfigurationEntry 165 }

	paEdfaPlusPump2LowOperatingCurrentAlarmInhibit OBJECT-TYPE
		SYNTAX  	INTEGER
		MAX-ACCESS  	read-write
		STATUS  	current

		DESCRIPTION
		 " to set/get PA EDFA PLUS card pump 2 low operating current alarm inhibit status.
		-----------------------------
		Value:
		1 - Inhibit
		0 - Do Not Inhibit
		-----------------------------"

		::= { paEdfaPlusConfigurationEntry 166 }

	paEdfaPlusPump1HighOperatingCurrentWarningInhibit OBJECT-TYPE
		SYNTAX  	INTEGER
		MAX-ACCESS  	read-write
		STATUS  	current

		DESCRIPTION
		 " to set/get PA EDFA PLUS card pump 1 high operating current warning inhibit status.
		-----------------------------
		Value:
		1 - Inhibit
		0 - Do Not Inhibit
		-----------------------------"

		::= { paEdfaPlusConfigurationEntry 167 }

	paEdfaPlusPump2HighOperatingCurrentWarningInhibit OBJECT-TYPE
		SYNTAX  	INTEGER
		MAX-ACCESS  	read-write
		STATUS  	current

		DESCRIPTION
		 " to set/get PA EDFA PLUS card pump 2 high operating current warning inhibit status.
		-----------------------------
		Value:
		1 - Inhibit
		0 - Do Not Inhibit
		-----------------------------"

		::= { paEdfaPlusConfigurationEntry 168 }

	paEdfaPlusPump1LowOperatingCurrentWarningInhibit OBJECT-TYPE
		SYNTAX  	INTEGER
		MAX-ACCESS  	read-write
		STATUS  	current

		DESCRIPTION
		 " to set/get PA EDFA PLUS card pump 1 low operating current warning inhibit status.
		-----------------------------
		Value:
		1 - Inhibit
		0 - Do Not Inhibit
		-----------------------------"

		::= { paEdfaPlusConfigurationEntry 169 }

	paEdfaPlusPump2LowOperatingCurrentWarningInhibit OBJECT-TYPE
		SYNTAX  	INTEGER
		MAX-ACCESS  	read-write
		STATUS  	current

		DESCRIPTION
		 " to set/get PA EDFA PLUS card pump 2 low operating current warning inhibit status.
		-----------------------------
		Value:
		1 - Inhibit
		0 - Do Not Inhibit
		-----------------------------"

		::= { paEdfaPlusConfigurationEntry 170 }

	paEdfaPlusPump1HighThermoElectricCoolerCurrentAlarmInhibit OBJECT-TYPE
		SYNTAX  	INTEGER
		MAX-ACCESS  	read-write
		STATUS  	current

		DESCRIPTION
		 " to set/get PA EDFA PLUS card pump 1 high thermo electric cooler current alarm inhibit status.
		-----------------------------
		Value:
		1 - Inhibit
		0 - Do Not Inhibit
		-----------------------------"

		::= { paEdfaPlusConfigurationEntry 171 }

	paEdfaPlusPump2HighThermoElectricCoolerCurrentAlarmInhibit OBJECT-TYPE
		SYNTAX  	INTEGER
		MAX-ACCESS  	read-write
		STATUS  	current

		DESCRIPTION
		 " to set/get PA EDFA PLUS card pump 2 high thermo electric cooler current alarm inhibit status.
		-----------------------------
		Value:
		1 - Inhibit
		0 - Do Not Inhibit
		-----------------------------"

		::= { paEdfaPlusConfigurationEntry 172 }


	paEdfaPlusPump1LowThermoElectricCoolerCurrentAlarmInhibit OBJECT-TYPE
		SYNTAX  	INTEGER
		MAX-ACCESS  	read-write
		STATUS  	current

		DESCRIPTION
		 " to set/get PA EDFA PLUS card pump 1 low thermo electric cooler current alarm inhibit status.
		-----------------------------
		Value:
		1 - Inhibit
		0 - Do Not Inhibit
		-----------------------------"

		::= { paEdfaPlusConfigurationEntry 173 }

	paEdfaPlusPump2LowThermoElectricCoolerCurrentAlarmInhibit OBJECT-TYPE
		SYNTAX  	INTEGER
		MAX-ACCESS  	read-write
		STATUS  	current

		DESCRIPTION
		 " to set/get PA EDFA PLUS card pump 2 low thermo electric cooler current alarm inhibit status.
		-----------------------------
		Value:
		1 - Inhibit
		0 - Do Not Inhibit
		-----------------------------"

		::= { paEdfaPlusConfigurationEntry 174 }

	paEdfaPlusPump1HighThermoElectricCoolerCurrentWarningInhibit OBJECT-TYPE
		SYNTAX  	INTEGER
		MAX-ACCESS  	read-write
		STATUS  	current

		DESCRIPTION
		 " to set/get PA EDFA PLUS card pump 1 high thermo electric cooler current warning inhibit status.
		-----------------------------
		Value:
		1 - Inhibit
		0 - Do Not Inhibit
		-----------------------------"

		::= { paEdfaPlusConfigurationEntry 175 }

	paEdfaPlusPump2HighThermoElectricCoolerCurrentWarningInhibit OBJECT-TYPE
		SYNTAX  	INTEGER
		MAX-ACCESS  	read-write
		STATUS  	current

		DESCRIPTION
		 " to set/get PA EDFA PLUS card pump 2 high thermo electric cooler current warning inhibit status.
		-----------------------------
		Value:
		1 - Inhibit
		0 - Do Not Inhibit
		-----------------------------"

		::= { paEdfaPlusConfigurationEntry 176 }

	paEdfaPlusPump1LowThermoElectricCoolerCurrentWarningInhibit OBJECT-TYPE
		SYNTAX  	INTEGER
		MAX-ACCESS  	read-write
		STATUS  	current

		DESCRIPTION
		 " to set/get PA EDFA PLUS card pump 1 low thermo electric cooler current warning inhibit status.
		-----------------------------
		Value:
		1 - Inhibit
		0 - Do Not Inhibit
		-----------------------------"

		::= { paEdfaPlusConfigurationEntry 177 } 

	paEdfaPlusPump2LowThermoElectricCoolerCurrentWarningInhibit OBJECT-TYPE
		SYNTAX  	INTEGER
		MAX-ACCESS  	read-write
		STATUS  	current

		DESCRIPTION
		 " to set/get PA EDFA PLUS card pump 2 low thermo electric cooler current warning inhibit status.
		-----------------------------
		Value:
		1 - Inhibit
		0 - Do Not Inhibit
		-----------------------------"

		::= { paEdfaPlusConfigurationEntry 178 } 
                               	
	paEdfaPlusVariableOpticalAttenuatorHighInputPowerAlarmInhibit OBJECT-TYPE
		SYNTAX  	INTEGER
		MAX-ACCESS  	read-write
		STATUS  	current

		DESCRIPTION
		 " to set/get PA EDFA PLUS card variable optical attenuator high input power alarm inhibit status.
		-----------------------------
		Value:
		1 - Inhibit
		0 - Do Not Inhibit
		-----------------------------"

		::= { paEdfaPlusConfigurationEntry 179 }

	paEdfaPlusVariableOpticalAttenuatorLowInputPowerAlarmInhibit OBJECT-TYPE
		SYNTAX  	INTEGER
		MAX-ACCESS  	read-write
		STATUS  	current

		DESCRIPTION
		 " to set/get PA EDFA PLUS card variable optical attenuator low input power alarm inhibit status.
		-----------------------------
		Value:
		1 - Inhibit
		0 - Do Not Inhibit
		-----------------------------"

		::= { paEdfaPlusConfigurationEntry 180 }

	paEdfaPlusVariableOpticalAttenuatorHighInputPowerWarningInhibit OBJECT-TYPE
		SYNTAX  	INTEGER
		MAX-ACCESS  	read-write
		STATUS  	current

		DESCRIPTION
		 " to set/get PA EDFA PLUS card variable optical attenuator high input power warning inhibit status.
		-----------------------------
		Value:
		1 - Inhibit
		0 - Do Not Inhibit
		-----------------------------"

		::= { paEdfaPlusConfigurationEntry 181 }

	paEdfaPlusVariableOpticalAttenuatorLowInputPowerWarningInhibit OBJECT-TYPE
		SYNTAX  	INTEGER
		MAX-ACCESS  	read-write
		STATUS  	current

		DESCRIPTION
		 " to set/get PA EDFA PLUS card variable optical attenuator low input power warning inhibit status.
		-----------------------------
		Value:
		1 - Inhibit
		0 - Do Not Inhibit
		-----------------------------"

		::= { paEdfaPlusConfigurationEntry 182 }

	paEdfaPlusInputOutOfRangeAlarmInhibit OBJECT-TYPE
		SYNTAX  	INTEGER
		MAX-ACCESS  	read-write
		STATUS  	current

		DESCRIPTION
		 " to set/get PA EDFA PLUS card Input Out Of Range Alarm Inhibit status.
		-----------------------------
		Value:
		1 - Inhibit
		0 - Do Not Inhibit
		-----------------------------"

		::= { paEdfaPlusConfigurationEntry 183 }

	paEdfaPlusOutputOutOfRangeAlarmInhibit OBJECT-TYPE
		SYNTAX  	INTEGER
		MAX-ACCESS  	read-write
		STATUS  	current

		DESCRIPTION
		 " to set/get PA EDFA PLUS card Output Out Of Range Alarm Inhibit status.
		-----------------------------
		Value:
		1 - Inhibit
		0 - Do Not Inhibit
		-----------------------------"

		::= { paEdfaPlusConfigurationEntry 184 }

	paEdfaPlusPumpBiasCurrentAlarmInhibit OBJECT-TYPE
		SYNTAX  	INTEGER
		MAX-ACCESS  	read-write
		STATUS  	current

		DESCRIPTION
		 " to set/get PA EDFA PLUS card Pump Bias Current Alarm Inhibit status.
		-----------------------------
		Value:
		1 - Inhibit
		0 - Do Not Inhibit
		-----------------------------"

		::= { paEdfaPlusConfigurationEntry 185 }

	paEdfaPlusPump1CoolingTemperatureAlarmInhibit OBJECT-TYPE
		SYNTAX  	INTEGER
		MAX-ACCESS  	read-write
		STATUS  	current

		DESCRIPTION
		 " to set/get PA EDFA PLUS card Pump 1 cooling temperature Alarm Inhibit status.
		-----------------------------
		Value:
		1 - Inhibit
		0 - Do Not Inhibit
		-----------------------------"

		::= { paEdfaPlusConfigurationEntry 186 }

	paEdfaPlusPump2CoolingTemperatureAlarmInhibit OBJECT-TYPE
		SYNTAX  	INTEGER
		MAX-ACCESS  	read-write
		STATUS  	current

		DESCRIPTION
		 " to set/get PA EDFA PLUS card Pump 2 cooling temperature Alarm Inhibit status.
		-----------------------------
		Value:
		1 - Inhibit
		0 - Do Not Inhibit
		-----------------------------"

		::= { paEdfaPlusConfigurationEntry 187 }

	paEdfaPlusPump1LaserPowerAlarmInhibit OBJECT-TYPE
		SYNTAX  	INTEGER
		MAX-ACCESS  	read-write
		STATUS  	current

		DESCRIPTION
		 " to set/get PA EDFA PLUS card Pump 1 laser power Alarm Inhibit status.
		-----------------------------
		Value:
		1 - Inhibit
		0 - Do Not Inhibit
		-----------------------------"

		::= { paEdfaPlusConfigurationEntry 188 }

	paEdfaPlusPump2LaserPowerAlarmInhibit OBJECT-TYPE
		SYNTAX  	INTEGER
		MAX-ACCESS  	read-write
		STATUS  	current

		DESCRIPTION
		 " to set/get PA EDFA PLUS card Pump 2 laser power Alarm Inhibit status.
		-----------------------------
		Value:
		1 - Inhibit
		0 - Do Not Inhibit
		-----------------------------"

		::= { paEdfaPlusConfigurationEntry 189 }

	paEdfaPlusOpticalInputPowerFailureAlarmForStage1Severity OBJECT-TYPE
		SYNTAX  	DisplayString
		MAX-ACCESS  	read-write
		STATUS  	current

		DESCRIPTION
		 " to set/get PA EDFA PLUS card optical input power failure alarm severity level for stage 1.
		-----------------------------
		Value:
		critical
		major
		minor
		deferred
		---------------------------"

		::= { paEdfaPlusConfigurationEntry 221 }	                                              

	paEdfaPlusOpticalInputPowerFailureAlarmForStage2Severity OBJECT-TYPE
		SYNTAX  	DisplayString
		MAX-ACCESS  	read-write
		STATUS  	current

		DESCRIPTION
		 " to set/get PA EDFA PLUS card optical input power failure alarm severity level for stage 2.
		-----------------------------
		Value:
		critical
		major
		minor
		deferred
		---------------------------"

		::= { paEdfaPlusConfigurationEntry 222 }
                      
	paEdfaPlusOpticalHighInputPowerAlarmForStage1Severity OBJECT-TYPE
		SYNTAX  	DisplayString
		MAX-ACCESS  	read-write
		STATUS  	current

		DESCRIPTION
		 " to set/get PA EDFA PLUS card optical high input power alarm severity level for stage 1.
		-----------------------------
		Value:
		critical
		major
		minor
		deferred
		---------------------------"

		::= { paEdfaPlusConfigurationEntry 223 }	              

	paEdfaPlusOpticalHighInputPowerAlarmForStage2Severity OBJECT-TYPE
		SYNTAX  	DisplayString
		MAX-ACCESS  	read-write
		STATUS  	current

		DESCRIPTION
		 " to set/get PA EDFA PLUS card optical high input power alarm severity level for stage 2.
		-----------------------------
		Value:
		critical
		major
		minor
		deferred
		---------------------------"

		::= { paEdfaPlusConfigurationEntry 224 }
                      
	paEdfaPlusOpticalLowInputPowerAlarmForStage1Severity OBJECT-TYPE
		SYNTAX  	DisplayString
		MAX-ACCESS  	read-write
		STATUS  	current

		DESCRIPTION
		 " to set/get PA EDFA PLUS card optical low input power alarm severity level for stage 1.
		-----------------------------
		Value:
		critical
		major
		minor
		deferred
		---------------------------"

		::= { paEdfaPlusConfigurationEntry 225 }	              

	paEdfaPlusOpticalLowInputPowerAlarmForStage2Severity OBJECT-TYPE
		SYNTAX  	DisplayString
		MAX-ACCESS  	read-write
		STATUS  	current

		DESCRIPTION
		 " to set/get PA EDFA PLUS card optical low input power alarm severity level for stage 2.
		-----------------------------
		Value:
		critical
		major
		minor
		deferred
		---------------------------"

		::= { paEdfaPlusConfigurationEntry 226 }
                      
	paEdfaPlusOpticalHighInputPowerWarningForStage1Severity OBJECT-TYPE
		SYNTAX  	DisplayString
		MAX-ACCESS  	read-write
		STATUS  	current

		DESCRIPTION
		 " to set/get PA EDFA PLUS card optical high input power warning severity level for stage 1.
		-----------------------------
		Value:
		critical
		major
		minor
		deferred
		---------------------------"

		::= { paEdfaPlusConfigurationEntry 227 }	              

	paEdfaPlusOpticalHighInputPowerWarningForStage2Severity OBJECT-TYPE
		SYNTAX  	DisplayString
		MAX-ACCESS  	read-write
		STATUS  	current

		DESCRIPTION
		 " to set/get PA EDFA PLUS card optical high input power warning severity level for stage 2.
		-----------------------------
		Value:
		critical
		major
		minor
		deferred
		---------------------------"

		::= { paEdfaPlusConfigurationEntry 228 }
                      
	paEdfaPlusOpticalLowInputPowerWarningForStage1Severity OBJECT-TYPE
		SYNTAX  	DisplayString
		MAX-ACCESS  	read-write
		STATUS  	current

		DESCRIPTION
		 " to set/get PA EDFA PLUS card optical low input power warning severity level for stage 1.
		-----------------------------
		Value:
		critical
		major
		minor
		deferred
		---------------------------"

		::= { paEdfaPlusConfigurationEntry 229 }              

	paEdfaPlusOpticalLowInputPowerWarningForStage2Severity OBJECT-TYPE
		SYNTAX  	DisplayString
		MAX-ACCESS  	read-write
		STATUS  	current

		DESCRIPTION
		 " to set/get PA EDFA PLUS card optical low input power warning severity level for stage 2.
		-----------------------------
		Value:
		critical
		major
		minor
		deferred
		---------------------------"

		::= { paEdfaPlusConfigurationEntry 230 } 
                    
	paEdfaPlusOpticalOutputPowerFailureAlarmForStage1Severity OBJECT-TYPE
		SYNTAX  	DisplayString
		MAX-ACCESS  	read-write
		STATUS  	current

		DESCRIPTION
		 " to set/get PA EDFA PLUS card optical output power failure alarm severity level for stage 1.
		-----------------------------
		Value:
		critical
		major
		minor
		deferred
		---------------------------"

		::= { paEdfaPlusConfigurationEntry 231 }

	paEdfaPlusOpticalOutputPowerFailureAlarmForStage2Severity OBJECT-TYPE
		SYNTAX  	DisplayString
		MAX-ACCESS  	read-write
		STATUS  	current

		DESCRIPTION
		 " to set/get PA EDFA PLUS card optical output power failure alarm severity level for stage 2.
		-----------------------------
		Value:
		critical
		major
		minor
		deferred
		---------------------------"

		::= { paEdfaPlusConfigurationEntry 232 }


	paEdfaPlusOpticalHighOutputPowerAlarmForStage1Severity OBJECT-TYPE
		SYNTAX  	DisplayString
		MAX-ACCESS  	read-write
		STATUS  	current

		DESCRIPTION
		 " to set/get PA EDFA PLUS card optical high output power alarm severity level for stage 1.
		-----------------------------
		Value:
		critical
		major
		minor
		deferred
		---------------------------"

		::= { paEdfaPlusConfigurationEntry 233 }

	paEdfaPlusOpticalHighOutputPowerAlarmForStage2Severity OBJECT-TYPE
		SYNTAX  	DisplayString
		MAX-ACCESS  	read-write
		STATUS  	current

		DESCRIPTION
		 " to set/get PA EDFA PLUS card optical high output power alarm severity level for stage 2.
		-----------------------------
		Value:
		critical
		major
		minor
		deferred
		---------------------------"

		::= { paEdfaPlusConfigurationEntry 234 }

	paEdfaPlusOpticalLowOutputPowerAlarmForStage1Severity OBJECT-TYPE
		SYNTAX  	DisplayString
		MAX-ACCESS  	read-write
		STATUS  	current

		DESCRIPTION
		 " to set/get PA EDFA PLUS card optical low output power alarm severity level for stage 1.
		-----------------------------
		Value:
		critical
		major
		minor
		deferred
		---------------------------"

		::= { paEdfaPlusConfigurationEntry 235 }

	paEdfaPlusOpticalLowOutputPowerAlarmForStage2Severity OBJECT-TYPE
		SYNTAX  	DisplayString
		MAX-ACCESS  	read-write
		STATUS  	current

		DESCRIPTION
		 " to set/get PA EDFA PLUS card optical low output power alarm severity level for stage 2.
		-----------------------------
		Value:
		critical
		major
		minor
		deferred
		---------------------------"

		::= { paEdfaPlusConfigurationEntry 236 }

	paEdfaPlusOpticalHighOutputPowerWarningForStage1Severity OBJECT-TYPE
		SYNTAX  	DisplayString
		MAX-ACCESS  	read-write
		STATUS  	current

		DESCRIPTION
		 " to set/get PA EDFA PLUS card optical high output power warning severity level for stage 1.
		-----------------------------
		Value:
		critical
		major
		minor
		deferred
		---------------------------"

		::= { paEdfaPlusConfigurationEntry 237 }

	paEdfaPlusOpticalHighOutputPowerWarningForStage2Severity OBJECT-TYPE
		SYNTAX  	DisplayString
		MAX-ACCESS  	read-write
		STATUS  	current

		DESCRIPTION
		 " to set/get PA EDFA PLUS card optical high output power warning severity level for stage 2.
		-----------------------------
		Value:
		critical
		major
		minor
		deferred
		---------------------------"

		::= { paEdfaPlusConfigurationEntry 238 }

	paEdfaPlusOpticalLowOutputPowerWarningForStage1Severity OBJECT-TYPE
		SYNTAX  	DisplayString
		MAX-ACCESS  	read-write
		STATUS  	current

		DESCRIPTION
		 " to set/get PA EDFA PLUS card optical low output power warning severity level for stage 1.
		-----------------------------
		Value:
		critical
		major
		minor
		deferred
		---------------------------"

		::= { paEdfaPlusConfigurationEntry 239 }

	paEdfaPlusOpticalLowOutputPowerWarningForStage2Severity OBJECT-TYPE
		SYNTAX  	DisplayString
		MAX-ACCESS  	read-write
		STATUS  	current

		DESCRIPTION
		 " to set/get PA EDFA PLUS card optical low output power warning severity level for stage 2.
		-----------------------------
		Value:
		critical
		major
		minor
		deferred
		---------------------------"

		::= { paEdfaPlusConfigurationEntry 240 }

	paEdfaPlusModuleHighTemperatureAlarmSeverity OBJECT-TYPE
		SYNTAX  	DisplayString
		MAX-ACCESS  	read-write
		STATUS  	current

		DESCRIPTION
		 " to set/get PA EDFA PLUS card module high temperature alarm severity level.
		-----------------------------
		Value:
		critical
		major
		minor
		deferred
		---------------------------"

		::= { paEdfaPlusConfigurationEntry 241 }

	paEdfaPlusModuleLowTemperatureAlarmSeverity OBJECT-TYPE
		SYNTAX  	DisplayString
		MAX-ACCESS  	read-write
		STATUS  	current

		DESCRIPTION
		 " to set/get PA EDFA PLUS card module low temperature alarm severity level.
		-----------------------------
		Value:
		critical
		major
		minor
		deferred
		---------------------------"

		::= { paEdfaPlusConfigurationEntry 242 }

	paEdfaPlusModuleHighTemperatureWarningSeverity OBJECT-TYPE
		SYNTAX  	DisplayString
		MAX-ACCESS  	read-write
		STATUS  	current

		DESCRIPTION
		 " to set/get PA EDFA PLUS card module high temperature warning severity level.
		-----------------------------
		Value:
		critical
		major
		minor
		deferred
		---------------------------"

		::= { paEdfaPlusConfigurationEntry 243 }

	paEdfaPlusModuleLowTemperatureWarningSeverity OBJECT-TYPE
		SYNTAX  	DisplayString
		MAX-ACCESS  	read-write
		STATUS  	current

		DESCRIPTION
		 " to set/get PA EDFA PLUS card module low temperature warning severity level.
		-----------------------------
		Value:
		critical
		major
		minor
		deferred
		---------------------------"

		::= { paEdfaPlusConfigurationEntry 244 }

	paEdfaPlusPump1HighTemperatureAlarmSeverity OBJECT-TYPE
		SYNTAX  	DisplayString
		MAX-ACCESS  	read-write
		STATUS  	current

		DESCRIPTION
		 " to set/get PA EDFA PLUS card pump 1 high temperature alarm severity level.
		-----------------------------
		Value:
		critical
		major
		minor
		deferred
		---------------------------"

		::= { paEdfaPlusConfigurationEntry 245 }

	paEdfaPlusPump2HighTemperatureAlarmSeverity OBJECT-TYPE
		SYNTAX  	DisplayString
		MAX-ACCESS  	read-write
		STATUS  	current

		DESCRIPTION
		 " to set/get PA EDFA PLUS card pump 2 high temperature alarm severity level.
		-----------------------------
		Value:
		critical
		major
		minor
		deferred
		---------------------------"

		::= { paEdfaPlusConfigurationEntry 246 }

	paEdfaPlusPump1LowTemperatureAlarmSeverity OBJECT-TYPE
		SYNTAX  	DisplayString
		MAX-ACCESS  	read-write
		STATUS  	current

		DESCRIPTION
		 " to set/get PA EDFA PLUS card pump 1 low temperature alarm severity level.
		-----------------------------
		Value:
		critical
		major
		minor
		deferred
		---------------------------"

		::= { paEdfaPlusConfigurationEntry 247 }

	paEdfaPlusPump2LowTemperatureAlarmSeverity OBJECT-TYPE
		SYNTAX  	DisplayString
		MAX-ACCESS  	read-write
		STATUS  	current

		DESCRIPTION
		 " to set/get PA EDFA PLUS card pump 2 low temperature alarm severity level.
		-----------------------------
		Value:
		critical
		major
		minor
		deferred
		---------------------------"

		::= { paEdfaPlusConfigurationEntry 248 }

	paEdfaPlusPump1HighTemperatureWarningSeverity OBJECT-TYPE
		SYNTAX  	DisplayString
		MAX-ACCESS  	read-write
		STATUS  	current

		DESCRIPTION
		 " to set/get PA EDFA PLUS card pump 1 high temperature warning severity level.
		-----------------------------
		Value:
		critical
		major
		minor
		deferred
		---------------------------"

		::= { paEdfaPlusConfigurationEntry 249 }

	paEdfaPlusPump2HighTemperatureWarningSeverity OBJECT-TYPE
		SYNTAX  	DisplayString
		MAX-ACCESS  	read-write
		STATUS  	current

		DESCRIPTION
		 " to set/get PA EDFA PLUS card pump 2 high temperature warning severity level.
		-----------------------------
		Value:
		critical
		major
		minor
		deferred
		---------------------------"

		::= { paEdfaPlusConfigurationEntry 250 }

	paEdfaPlusPump1LowTemperatureWarningSeverity OBJECT-TYPE
		SYNTAX  	DisplayString
		MAX-ACCESS  	read-write
		STATUS  	current

		DESCRIPTION
		 " to set/get PA EDFA PLUS card pump 1 low temperature warning severity level.
		-----------------------------
		Value:
		critical
		major
		minor
		deferred
		---------------------------"

		::= { paEdfaPlusConfigurationEntry 251 }

	paEdfaPlusPump2LowTemperatureWarningSeverity OBJECT-TYPE
		SYNTAX  	DisplayString
		MAX-ACCESS  	read-write
		STATUS  	current

		DESCRIPTION
		 " to set/get PA EDFA PLUS card pump 2 low temperature warning severity level.
		-----------------------------
		Value:
		critical
		major
		minor
		deferred
		---------------------------"

		::= { paEdfaPlusConfigurationEntry 252 }

	paEdfaPlusPump1HighOperatingCurrentAlarmSeverity OBJECT-TYPE
		SYNTAX  	DisplayString
		MAX-ACCESS  	read-write
		STATUS  	current

		DESCRIPTION
		 " to set/get PA EDFA PLUS card pump 1 high operating current alarm severity level.
		-----------------------------
		Value:
		critical
		major
		minor
		deferred
		---------------------------"

		::= { paEdfaPlusConfigurationEntry 253 }

	paEdfaPlusPump2HighOperatingCurrentAlarmSeverity OBJECT-TYPE
		SYNTAX  	DisplayString
		MAX-ACCESS  	read-write
		STATUS  	current

		DESCRIPTION
		 " to set/get PA EDFA PLUS card pump 2 high operating current alarm severity level.
		-----------------------------
		Value:
		critical
		major
		minor
		deferred
		---------------------------"

		::= { paEdfaPlusConfigurationEntry 254 }

	paEdfaPlusPump1LowOperatingCurrentAlarmSeverity OBJECT-TYPE
		SYNTAX  	DisplayString
		MAX-ACCESS  	read-write
		STATUS  	current

		DESCRIPTION
		 " to set/get PA EDFA PLUS card pump 1 low operating current alarm severity level.
		-----------------------------
		Value:
		critical
		major
		minor
		deferred
		---------------------------"

		::= { paEdfaPlusConfigurationEntry 255 }

	paEdfaPlusPump2LowOperatingCurrentAlarmSeverity OBJECT-TYPE
		SYNTAX  	DisplayString
		MAX-ACCESS  	read-write
		STATUS  	current

		DESCRIPTION
		 " to set/get PA EDFA PLUS card pump 2 low operating current alarm severity level.
		-----------------------------
		Value:
		critical
		major
		minor
		deferred
		---------------------------"

		::= { paEdfaPlusConfigurationEntry 256 }

	paEdfaPlusPump1HighOperatingCurrentWarningSeverity OBJECT-TYPE
		SYNTAX  	DisplayString
		MAX-ACCESS  	read-write
		STATUS  	current

		DESCRIPTION
		 " to set/get PA EDFA PLUS card pump 1 high operating current warning severity level.
		-----------------------------
		Value:
		critical
		major
		minor
		deferred
		---------------------------"

		::= { paEdfaPlusConfigurationEntry 257 }

	paEdfaPlusPump2HighOperatingCurrentWarningSeverity OBJECT-TYPE
		SYNTAX  	DisplayString
		MAX-ACCESS  	read-write
		STATUS  	current

		DESCRIPTION
		 " to set/get PA EDFA PLUS card pump 2 high operating current warning severity level.
		-----------------------------
		Value:
		critical
		major
		minor
		deferred
		---------------------------"

		::= { paEdfaPlusConfigurationEntry 258 }

	paEdfaPlusPump1LowOperatingCurrentWarningSeverity OBJECT-TYPE
		SYNTAX  	DisplayString
		MAX-ACCESS  	read-write
		STATUS  	current

		DESCRIPTION
		 " to set/get PA EDFA PLUS card pump 1 low operating current warning severity level.
		-----------------------------
		Value:
		critical
		major
		minor
		deferred
		---------------------------"

		::= { paEdfaPlusConfigurationEntry 259 }

	paEdfaPlusPump2LowOperatingCurrentWarningSeverity OBJECT-TYPE
		SYNTAX  	DisplayString
		MAX-ACCESS  	read-write
		STATUS  	current

		DESCRIPTION
		 " to set/get PA EDFA PLUS card pump 2 low operating current warning severity level.
		-----------------------------
		Value:
		critical
		major
		minor
		deferred
		---------------------------"

		::= { paEdfaPlusConfigurationEntry 260 }

	paEdfaPlusPump1HighThermoElectricCoolerCurrentAlarmSeverity OBJECT-TYPE
		SYNTAX  	DisplayString
		MAX-ACCESS  	read-write
		STATUS  	current

		DESCRIPTION
		 " to set/get PA EDFA PLUS card pump 1 high thermo electric cooler current alarm severity level.
		-----------------------------
		Value:
		critical
		major
		minor
		deferred
		---------------------------"

		::= { paEdfaPlusConfigurationEntry 261 }

	paEdfaPlusPump2HighThermoElectricCoolerCurrentAlarmSeverity OBJECT-TYPE
		SYNTAX  	DisplayString
		MAX-ACCESS  	read-write
		STATUS  	current

		DESCRIPTION
		 " to set/get PA EDFA PLUS card pump 2 high thermo electric cooler current alarm severity level.
		-----------------------------
		Value:
		critical
		major
		minor
		deferred
		---------------------------"

		::= { paEdfaPlusConfigurationEntry 262 }


	paEdfaPlusPump1LowThermoElectricCoolerCurrentAlarmSeverity OBJECT-TYPE
		SYNTAX  	DisplayString
		MAX-ACCESS  	read-write
		STATUS  	current

		DESCRIPTION
		 " to set/get PA EDFA PLUS card pump 1 low thermo electric cooler current alarm severity level.
		-----------------------------
		Value:
		critical
		major
		minor
		deferred
		---------------------------"

		::= { paEdfaPlusConfigurationEntry 263 }

	paEdfaPlusPump2LowThermoElectricCoolerCurrentAlarmSeverity OBJECT-TYPE
		SYNTAX  	DisplayString
		MAX-ACCESS  	read-write
		STATUS  	current

		DESCRIPTION
		 " to set/get PA EDFA PLUS card pump 2 low thermo electric cooler current alarm severity level.
		-----------------------------
		Value:
		critical
		major
		minor
		deferred
		---------------------------"

		::= { paEdfaPlusConfigurationEntry 264 }

	paEdfaPlusPump1HighThermoElectricCoolerCurrentWarningSeverity OBJECT-TYPE
		SYNTAX  	DisplayString
		MAX-ACCESS  	read-write
		STATUS  	current

		DESCRIPTION
		 " to set/get PA EDFA PLUS card pump 1 high thermo electric cooler current warning severity level.
		-----------------------------
		Value:
		critical
		major
		minor
		deferred
		---------------------------"

		::= { paEdfaPlusConfigurationEntry 265 }

	paEdfaPlusPump2HighThermoElectricCoolerCurrentWarningSeverity OBJECT-TYPE
		SYNTAX  	DisplayString
		MAX-ACCESS  	read-write
		STATUS  	current

		DESCRIPTION
		 " to set/get PA EDFA PLUS card pump 2 high thermo electric cooler current warning severity level.
		-----------------------------
		Value:
		critical
		major
		minor
		deferred
		---------------------------"

		::= { paEdfaPlusConfigurationEntry 266 }

	paEdfaPlusPump1LowThermoElectricCoolerCurrentWarningSeverity OBJECT-TYPE
		SYNTAX  	DisplayString
		MAX-ACCESS  	read-write
		STATUS  	current

		DESCRIPTION
		 " to set/get PA EDFA PLUS card pump 1 low thermo electric cooler current warning severity level.
		-----------------------------
		Value:
		critical
		major
		minor
		deferred
		---------------------------"

		::= { paEdfaPlusConfigurationEntry 267 } 

	paEdfaPlusPump2LowThermoElectricCoolerCurrentWarningSeverity OBJECT-TYPE
		SYNTAX  	DisplayString
		MAX-ACCESS  	read-write
		STATUS  	current

		DESCRIPTION
		 " to set/get PA EDFA PLUS card pump 2 low thermo electric cooler current warning severity level.
		-----------------------------
		Value:
		critical
		major
		minor
		deferred
		---------------------------"

		::= { paEdfaPlusConfigurationEntry 268 } 
                               	
	paEdfaPlusVariableOpticalAttenuatorHighInputPowerAlarmSeverity OBJECT-TYPE
		SYNTAX  	DisplayString
		MAX-ACCESS  	read-write
		STATUS  	current

		DESCRIPTION
		 " to set/get PA EDFA PLUS card variable optical attenuator high input power alarm severity level.
		-----------------------------
		Value:
		critical
		major
		minor
		deferred
		---------------------------"

		::= { paEdfaPlusConfigurationEntry 269 }

	paEdfaPlusVariableOpticalAttenuatorLowInputPowerAlarmSeverity OBJECT-TYPE
		SYNTAX  	DisplayString
		MAX-ACCESS  	read-write
		STATUS  	current

		DESCRIPTION
		 " to set/get PA EDFA PLUS card variable optical attenuator low input power alarm severity level.
		-----------------------------
		Value:
		critical
		major
		minor
		deferred
		---------------------------"

		::= { paEdfaPlusConfigurationEntry 270 }

	paEdfaPlusVariableOpticalAttenuatorHighInputPowerWarningSeverity OBJECT-TYPE
		SYNTAX  	DisplayString
		MAX-ACCESS  	read-write
		STATUS  	current

		DESCRIPTION
		 " to set/get PA EDFA PLUS card variable optical attenuator high input power warning severity level.
		-----------------------------
		Value:
		critical
		major
		minor
		deferred
		---------------------------"

		::= { paEdfaPlusConfigurationEntry 271 }

	paEdfaPlusVariableOpticalAttenuatorLowInputPowerWarningSeverity OBJECT-TYPE
		SYNTAX  	DisplayString
		MAX-ACCESS  	read-write
		STATUS  	current

		DESCRIPTION
		 " to set/get PA EDFA PLUS card variable optical attenuator low input power warning severity level.
		-----------------------------
		Value:
		critical
		major
		minor
		deferred
		---------------------------"

		::= { paEdfaPlusConfigurationEntry 272 }

	paEdfaPlusInputOutOfRangeAlarmSeverity OBJECT-TYPE
		SYNTAX  	DisplayString
		MAX-ACCESS  	read-write
		STATUS  	current

		DESCRIPTION
		 " to set/get PA EDFA PLUS card Input Out Of Range Alarm severity level.
		-----------------------------
		Value:
		critical
		major
		minor
		deferred
		---------------------------"

		::= { paEdfaPlusConfigurationEntry 273 }

	paEdfaPlusOutputOutOfRangeAlarmSeverity OBJECT-TYPE
		SYNTAX  	DisplayString
		MAX-ACCESS  	read-write
		STATUS  	current

		DESCRIPTION
		 " to set/get PA EDFA PLUS card Output Out Of Range Alarm severity level.
		-----------------------------
		Value:
		critical
		major
		minor
		deferred
		---------------------------"

		::= { paEdfaPlusConfigurationEntry 274 }

	paEdfaPlusPumpBiasCurrentAlarmSeverity OBJECT-TYPE
		SYNTAX  	DisplayString
		MAX-ACCESS  	read-write
		STATUS  	current

		DESCRIPTION
		 " to set/get PA EDFA PLUS card Pump Bias Current Alarm severity level.
		-----------------------------
		Value:
		critical
		major
		minor
		deferred
		---------------------------"

		::= { paEdfaPlusConfigurationEntry 275 }

	paEdfaPlusPump1CoolingTemperatureAlarmSeverity OBJECT-TYPE
		SYNTAX  	DisplayString
		MAX-ACCESS  	read-write
		STATUS  	current

		DESCRIPTION
		 " to set/get PA EDFA PLUS card Pump 1 cooling temperature alarm severity level for stage 1.
		-----------------------------
		Value:
		critical
		major
		minor
		deferred
		---------------------------"

		::= { paEdfaPlusConfigurationEntry 276 }

	paEdfaPlusPump2CoolingTemperatureAlarmSeverity OBJECT-TYPE
		SYNTAX  	DisplayString
		MAX-ACCESS  	read-write
		STATUS  	current

		DESCRIPTION
		 " to set/get PA EDFA PLUS card Pump 2 cooling temperature alarm severity level for stage 1.
		-----------------------------
		Value:
		critical
		major
		minor
		deferred
		---------------------------"

		::= { paEdfaPlusConfigurationEntry 277 }

	paEdfaPlusPump1LaserPowerAlarmSeverity OBJECT-TYPE
		SYNTAX  	DisplayString
		MAX-ACCESS  	read-write
		STATUS  	current

		DESCRIPTION
		 " to set/get PA EDFA PLUS card Pump 1 laser power alarm severity level for stage 1.
		-----------------------------
		Value:
		critical
		major
		minor
		deferred
		---------------------------"

		::= { paEdfaPlusConfigurationEntry 278 }

	paEdfaPlusPump2LaserPowerAlarmSeverity OBJECT-TYPE
		SYNTAX  	DisplayString
		MAX-ACCESS  	read-write
		STATUS  	current

		DESCRIPTION
		 " to set/get PA EDFA PLUS card Pump 2 laser power alarm severity level for stage 1.
		-----------------------------
		Value:
		critical
		major
		minor
		deferred
		---------------------------"

		::= { paEdfaPlusConfigurationEntry 279 }

	paEdfaPlusCardSoftwareUpgrade OBJECT-TYPE
		SYNTAX 		DisplayString
		MAX-ACCESS 	read-write
		STATUS 		current
		DESCRIPTION
			"Valid only as SET command.
			This property upgrades the software of the PA-EDFA-PLUS card
			It takes the path of the software release as
			a value,
			paEdfaPlusInterface: 0
			Values:
			eg: /home/root/rel-2.0.0.tar.gz
			-----------------------------"

		::= { paEdfaPlusConfigurationEntry 280 }

	paEdfaPlusMidInOutOfRangeAlarmInhibit OBJECT-TYPE
		SYNTAX  	INTEGER
		MAX-ACCESS  	read-write
		STATUS  	current

		DESCRIPTION
		 " to set/get PA EDFA PLUS card Mid Input Out Of Range Alarm Inhibit status.
		-----------------------------
		Value:
		1 - Inhibit
		0 - Do Not Inhibit
		-----------------------------"

		::= { paEdfaPlusConfigurationEntry 281 }

	paEdfaPlusMidOutOutOfRangeAlarmInhibit OBJECT-TYPE
		SYNTAX  	INTEGER
		MAX-ACCESS  	read-write
		STATUS  	current

		DESCRIPTION
		 " to set/get PA EDFA PLUS card Mid Output Out Of Range Alarm Inhibit status.
		-----------------------------
		Value:
		1 - Inhibit
		0 - Do Not Inhibit
		-----------------------------"

		::= { paEdfaPlusConfigurationEntry 282 }

	paEdfaPlusMidInOutOfRangeAlarmSeverity OBJECT-TYPE
		SYNTAX  	DisplayString
		MAX-ACCESS  	read-write
		STATUS  	current

		DESCRIPTION
		 " to set/get PA EDFA PLUS card Mid Input Out Of Range Alarm severity level.
		-----------------------------
		Value:
		critical
		major
		minor
		deferred
		---------------------------"

		::= { paEdfaPlusConfigurationEntry 283 }

	paEdfaPlusMidOutOutOfRangeAlarmSeverity OBJECT-TYPE
		SYNTAX  	DisplayString
		MAX-ACCESS  	read-write
		STATUS  	current

		DESCRIPTION
		 " to set/get PA EDFA PLUS card Mid Output Out Of Range Alarm severity level.
		-----------------------------
		Value:
		critical
		major
		minor
		deferred
		---------------------------"

		::= { paEdfaPlusConfigurationEntry 284 }

	paEdfaPlusConfigurationTableRowStatus OBJECT-TYPE
              SYNTAX      RowStatus
              MAX-ACCESS  read-write
              STATUS      current
              DESCRIPTION
                      "	This is MIB realted property,
			NOT to be considered as a card property"
              ::= { paEdfaPlusConfigurationEntry 285 }

--*****************************************************************************
--				PA EDFA PLUS ALARMS
--*****************************************************************************         
              
	paEdfaPlusAlarmQueryTable OBJECT-TYPE
		SYNTAX  	SEQUENCE OF PaEdfaPlusAlarmQueryEntry
		MAX-ACCESS  	not-accessible
		STATUS  	current

		DESCRIPTION
		 "we can get PA EDFA PLUS card alarm details"

		::= { paEdfaPlusAlarmQuery 1 }
	      
	paEdfaPlusAlarmQueryEntry OBJECT-TYPE
		SYNTAX  	PaEdfaPlusAlarmQueryEntry
		MAX-ACCESS  	not-accessible
		STATUS  	current

		DESCRIPTION
		 "Enter node rack, subrack, slot and paEdfaPlusInterface numbers"

		INDEX   { node, rack, subRack, slot, paEdfaPlusInterface }

		::= { paEdfaPlusAlarmQueryTable 1 }

	PaEdfaPlusAlarmQueryEntry ::= 
		SEQUENCE {
				paEdfaPlusOpticalInputPowerFailureAlarmForStage1 		DisplayString,
				paEdfaPlusOpticalInputPowerFailureAlarmForStage2 		DisplayString,
				paEdfaPlusOpticalHighInputPowerAlarmForStage1			DisplayString,
				paEdfaPlusOpticalHighInputPowerAlarmForStage2			DisplayString,
				paEdfaPlusOpticalLowInputPowerAlarmForStage1	 		DisplayString,
				paEdfaPlusOpticalLowInputPowerAlarmForStage2	 		DisplayString,
				paEdfaPlusOpticalHighInputPowerWarningForStage1	 		DisplayString,
				paEdfaPlusOpticalHighInputPowerWarningForStage2	 		DisplayString,
				paEdfaPlusOpticalLowInputPowerWarningForStage1 			DisplayString,
				paEdfaPlusOpticalLowInputPowerWarningForStage2 			DisplayString,
				paEdfaPlusOpticalOutputPowerFailureAlarmForStage1		DisplayString,
				paEdfaPlusOpticalOutputPowerFailureAlarmForStage2		DisplayString,
				paEdfaPlusOpticalHighOutputPowerAlarmForStage1			DisplayString,
				paEdfaPlusOpticalHighOutputPowerAlarmForStage2			DisplayString,
				paEdfaPlusOpticalLowOutputPowerAlarmForStage1			DisplayString,
				paEdfaPlusOpticalLowOutputPowerAlarmForStage2			DisplayString,
				paEdfaPlusOpticalHighOutputPowerWarningForStage1		DisplayString,
				paEdfaPlusOpticalHighOutputPowerWarningForStage2		DisplayString,
				paEdfaPlusOpticalLowOutputPowerWarningForStage1			DisplayString,
				paEdfaPlusOpticalLowOutputPowerWarningForStage2			DisplayString,
				paEdfaPlusModuleHighTemperatureAlarm				DisplayString,
				paEdfaPlusModuleLowTemperatureAlarm				DisplayString,
				paEdfaPlusModuleHighTemperatureWarning				DisplayString,
				paEdfaPlusModuleLowTemperatureWarning				DisplayString,
				paEdfaPlusPump1HighTemperatureAlarm				DisplayString,
				paEdfaPlusPump2HighTemperatureAlarm				DisplayString,
				paEdfaPlusPump1LowTemperatureAlarm				DisplayString,
				paEdfaPlusPump2LowTemperatureAlarm				DisplayString,
				paEdfaPlusPump1HighTemperatureWarning				DisplayString,
				paEdfaPlusPump2HighTemperatureWarning				DisplayString,
				paEdfaPlusPump1LowTemperatureWarning				DisplayString,
				paEdfaPlusPump2LowTemperatureWarning				DisplayString,
				paEdfaPlusPump1HighOperatingCurrentAlarm			DisplayString,
				paEdfaPlusPump2HighOperatingCurrentAlarm			DisplayString,
				paEdfaPlusPump1LowOperatingCurrentAlarm				DisplayString,
				paEdfaPlusPump2LowOperatingCurrentAlarm				DisplayString,
				paEdfaPlusPump1HighOperatingCurrentWarning			DisplayString,
				paEdfaPlusPump2HighOperatingCurrentWarning			DisplayString,
				paEdfaPlusPump1LowOperatingCurrentWarning			DisplayString,
				paEdfaPlusPump2LowOperatingCurrentWarning			DisplayString,
				paEdfaPlusPump1HighThermoElectricCoolerCurrentAlarm		DisplayString,
				paEdfaPlusPump2HighThermoElectricCoolerCurrentAlarm		DisplayString,
				paEdfaPlusPump1LowThermoElectricCoolerCurrentAlarm		DisplayString,
				paEdfaPlusPump2LowThermoElectricCoolerCurrentAlarm		DisplayString,
				paEdfaPlusPump1HighThermoElectricCoolerCurrentWarning		DisplayString,
				paEdfaPlusPump2HighThermoElectricCoolerCurrentWarning		DisplayString,
				paEdfaPlusPump1LowThermoElectricCoolerCurrentWarning		DisplayString,
				paEdfaPlusPump2LowThermoElectricCoolerCurrentWarning		DisplayString,
				paEdfaPlusVariableOpticalAttenuatorHighInputPowerAlarm 		DisplayString,
				paEdfaPlusVariableOpticalAttenuatorLowInputPowerAlarm 		DisplayString,
				paEdfaPlusVariableOpticalAttenuatorHighInputPowerWarning 	DisplayString,
				paEdfaPlusVariableOpticalAttenuatorLowInputPowerWarning 	DisplayString,
				paEdfaPlusInputOutOfRangeAlarm					DisplayString,
				paEdfaPlusOutputOutOfRangeAlarm					DisplayString,
				paEdfaPlusMidInOutOfRangeAlarm					DisplayString,
				paEdfaPlusMidOutOutOfRangeAlarm					DisplayString,			
				paEdfaPlusPumpBiasCurrentAlarm					DisplayString,
				paEdfaPlusPump1CoolingTemperatureAlarm				DisplayString,
				paEdfaPlusPump2CoolingTemperatureAlarm				DisplayString,
				paEdfaPlusPump1LaserPowerAlarm					DisplayString,
				paEdfaPlusPump2LaserPowerAlarm					DisplayString,
				paEdfaPlusAlarmQueryTableRowStatus				RowStatus
			}

	paEdfaPlusOpticalInputPowerFailureAlarmForStage1 OBJECT-TYPE
		SYNTAX  	DisplayString
		MAX-ACCESS  	read-only
		STATUS  	current

		DESCRIPTION
		 " to get PA EDFA PLUS card optical input power failure alarm status for stage 1.
		-----------------------------
		Values :
		If Alarm is Present - Date and Time Stamp
			    eg:2017-5-18,9:47:20.0,+5:30
		If Alarm is Absent  - 0
		-----------------------------"

		::= { paEdfaPlusAlarmQueryEntry 1 }	              

	paEdfaPlusOpticalInputPowerFailureAlarmForStage2 OBJECT-TYPE
		SYNTAX  	DisplayString
		MAX-ACCESS  	read-only
		STATUS  	current

		DESCRIPTION
		 " to get PA EDFA PLUS card optical input power failure alarm status for stage 2.
		-----------------------------
		Values :
		If Alarm is Present - Date and Time Stamp
			    eg:2017-5-18,9:47:20.0,+5:30
		If Alarm is Absent  - 0
		-----------------------------"

		::= { paEdfaPlusAlarmQueryEntry 2 }
		      
	paEdfaPlusOpticalHighInputPowerAlarmForStage1 OBJECT-TYPE
		SYNTAX  	DisplayString
		MAX-ACCESS  	read-only
		STATUS  	current

		DESCRIPTION
		 " to get PA EDFA PLUS card optical high input power alarm status for stage 1.
		-----------------------------
		Values :
		If Alarm is Present - Date and Time Stamp
			    eg:2017-5-18,9:47:20.0,+5:30
		If Alarm is Absent  - 0
		-----------------------------"

		::= { paEdfaPlusAlarmQueryEntry 3 }	              

	paEdfaPlusOpticalHighInputPowerAlarmForStage2 OBJECT-TYPE
		SYNTAX  	DisplayString
		MAX-ACCESS  	read-only
		STATUS  	current

		DESCRIPTION
		 " to get PA EDFA PLUS card optical high input power alarm status for stage 2.
		-----------------------------
		Values :
		If Alarm is Present - Date and Time Stamp
			    eg:2017-5-18,9:47:20.0,+5:30
		If Alarm is Absent  - 0
		-----------------------------"

		::= { paEdfaPlusAlarmQueryEntry 4 }
		      
	paEdfaPlusOpticalLowInputPowerAlarmForStage1 OBJECT-TYPE
		SYNTAX  	DisplayString
		MAX-ACCESS  	read-only
		STATUS  	current

		DESCRIPTION
		 " to get PA EDFA PLUS card optical low input power alarm status for stage 1.
		-----------------------------
		Values :
		If Alarm is Present - Date and Time Stamp
			    eg:2017-5-18,9:47:20.0,+5:30
		If Alarm is Absent  - 0
		-----------------------------"

		::= { paEdfaPlusAlarmQueryEntry 5 }	              

	paEdfaPlusOpticalLowInputPowerAlarmForStage2 OBJECT-TYPE
		SYNTAX  	DisplayString
		MAX-ACCESS  	read-only
		STATUS  	current

		DESCRIPTION
		 " to get PA EDFA PLUS card optical low input power alarm status for stage 2.
		-----------------------------
		Values :
		If Alarm is Present - Date and Time Stamp
			    eg:2017-5-18,9:47:20.0,+5:30
		If Alarm is Absent  - 0
		-----------------------------"

		::= { paEdfaPlusAlarmQueryEntry 6 }
		      
	paEdfaPlusOpticalHighInputPowerWarningForStage1 OBJECT-TYPE
		SYNTAX  	DisplayString
		MAX-ACCESS  	read-only
		STATUS  	current

		DESCRIPTION
		 " to get PA EDFA PLUS card optical high input power warning status for stage 1.
		-----------------------------
		Values :
		If Alarm is Present - Date and Time Stamp
			    eg:2017-5-18,9:47:20.0,+5:30
		If Alarm is Absent  - 0
		-----------------------------"

		::= { paEdfaPlusAlarmQueryEntry 7 }	              

	paEdfaPlusOpticalHighInputPowerWarningForStage2 OBJECT-TYPE
		SYNTAX  	DisplayString
		MAX-ACCESS  	read-only
		STATUS  	current

		DESCRIPTION
		 " to get PA EDFA PLUS card optical high input power warning status for stage 2.
		-----------------------------
		Values :
		If Alarm is Present - Date and Time Stamp
			    eg:2017-5-18,9:47:20.0,+5:30
		If Alarm is Absent  - 0
		-----------------------------"

		::= { paEdfaPlusAlarmQueryEntry 8 }
		      
	paEdfaPlusOpticalLowInputPowerWarningForStage1 OBJECT-TYPE
		SYNTAX  	DisplayString
		MAX-ACCESS  	read-only
		STATUS  	current

		DESCRIPTION
		 " to get PA EDFA PLUS card optical low input power warning status for stage 1.
		-----------------------------
		Values :
		If Alarm is Present - Date and Time Stamp
			    eg:2017-5-18,9:47:20.0,+5:30
		If Alarm is Absent  - 0
		-----------------------------"
	
	      ::= { paEdfaPlusAlarmQueryEntry 9 }	              

	paEdfaPlusOpticalLowInputPowerWarningForStage2 OBJECT-TYPE
		SYNTAX  	DisplayString
		MAX-ACCESS  	read-only
		STATUS  	current

		DESCRIPTION
		 " to get PA EDFA PLUS card optical low input power warning status for stage 2.
		-----------------------------
		Values :
		If Alarm is Present - Date and Time Stamp
			    eg:2017-5-18,9:47:20.0,+5:30
		If Alarm is Absent  - 0
		-----------------------------"
	
	      ::= { paEdfaPlusAlarmQueryEntry 10 }
		      
	paEdfaPlusOpticalOutputPowerFailureAlarmForStage1 OBJECT-TYPE
		SYNTAX  	DisplayString
		MAX-ACCESS  	read-only
		STATUS  	current

		DESCRIPTION
		 " to get PA EDFA PLUS card optical high output power failure alarm status for stage 1.
		-----------------------------
		Values :
		If Alarm is Present - Date and Time Stamp
			    eg:2017-5-18,9:47:20.0,+5:30
		If Alarm is Absent  - 0
		-----------------------------"

		::= { paEdfaPlusAlarmQueryEntry 11 }	              

	paEdfaPlusOpticalOutputPowerFailureAlarmForStage2 OBJECT-TYPE
		SYNTAX  	DisplayString
		MAX-ACCESS  	read-only
		STATUS  	current

		DESCRIPTION
		 " to get PA EDFA PLUS card optical high output power failure alarm status for stage 2.
		-----------------------------
		Values :
		If Alarm is Present - Date and Time Stamp
			    eg:2017-5-18,9:47:20.0,+5:30
		If Alarm is Absent  - 0
		-----------------------------"

		::= { paEdfaPlusAlarmQueryEntry 12 }
		      
	paEdfaPlusOpticalHighOutputPowerAlarmForStage1 OBJECT-TYPE
		SYNTAX  	DisplayString
		MAX-ACCESS  	read-only
		STATUS  	current

		DESCRIPTION
		 " to get PA EDFA PLUS card optical high output power alarm status for stage 1.
		-----------------------------
		Values :
		If Alarm is Present - Date and Time Stamp
			    eg:2017-5-18,9:47:20.0,+5:30
		If Alarm is Absent  - 0
		-----------------------------"

		::= { paEdfaPlusAlarmQueryEntry 13 }

	paEdfaPlusOpticalHighOutputPowerAlarmForStage2 OBJECT-TYPE
		SYNTAX  	DisplayString
		MAX-ACCESS  	read-only
		STATUS  	current

		DESCRIPTION
		 " to get PA EDFA PLUS card optical high output power alarm status for stage 2.
		-----------------------------
		Values :
		If Alarm is Present - Date and Time Stamp
			    eg:2017-5-18,9:47:20.0,+5:30
		If Alarm is Absent  - 0
		-----------------------------"

		::= { paEdfaPlusAlarmQueryEntry 14 }

	paEdfaPlusOpticalLowOutputPowerAlarmForStage1 OBJECT-TYPE
		SYNTAX  	DisplayString
		MAX-ACCESS  	read-only
		STATUS  	current

		DESCRIPTION
		 " to get PA EDFA PLUS card optical low output power alarm status for stage 1.
		-----------------------------
		Values :
		If Alarm is Present - Date and Time Stamp
			    eg:2017-5-18,9:47:20.0,+5:30
		If Alarm is Absent  - 0
		-----------------------------"

		::= { paEdfaPlusAlarmQueryEntry 15 }	              

	paEdfaPlusOpticalLowOutputPowerAlarmForStage2 OBJECT-TYPE
		SYNTAX  	DisplayString
		MAX-ACCESS  	read-only
		STATUS  	current

		DESCRIPTION
		 " to get PA EDFA PLUS card optical low output power alarm status for stage 2.
		-----------------------------
		Values :
		If Alarm is Present - Date and Time Stamp
			    eg:2017-5-18,9:47:20.0,+5:30
		If Alarm is Absent  - 0
		-----------------------------"

		::= { paEdfaPlusAlarmQueryEntry 16 }
		      
	paEdfaPlusOpticalHighOutputPowerWarningForStage1 OBJECT-TYPE
		SYNTAX  	DisplayString
		MAX-ACCESS  	read-only
		STATUS  	current

		DESCRIPTION
		 " to get PA EDFA PLUS card optical high output power warning status for stage 1.
		-----------------------------
		Values :
		If Alarm is Present - Date and Time Stamp
			    eg:2017-5-18,9:47:20.0,+5:30
		If Alarm is Absent  - 0
		-----------------------------"

		::= { paEdfaPlusAlarmQueryEntry 17 }	              

	paEdfaPlusOpticalHighOutputPowerWarningForStage2 OBJECT-TYPE
		SYNTAX  	DisplayString
		MAX-ACCESS  	read-only
		STATUS  	current

		DESCRIPTION
		 " to get PA EDFA PLUS card optical high output power warning status for stage 2.
		-----------------------------
		Values :
		If Alarm is Present - Date and Time Stamp
			    eg:2017-5-18,9:47:20.0,+5:30
		If Alarm is Absent  - 0
		-----------------------------"

		::= { paEdfaPlusAlarmQueryEntry 18 }
		      
	paEdfaPlusOpticalLowOutputPowerWarningForStage1 OBJECT-TYPE
		SYNTAX  	DisplayString
		MAX-ACCESS  	read-only
		STATUS  	current

		DESCRIPTION
		 " to get PA EDFA PLUS card optical low output power warning status for stage 1.
		-----------------------------
		Values :
		If Alarm is Present - Date and Time Stamp
			    eg:2017-5-18,9:47:20.0,+5:30
		If Alarm is Absent  - 0
		-----------------------------"

		::= { paEdfaPlusAlarmQueryEntry 19 }	              

	paEdfaPlusOpticalLowOutputPowerWarningForStage2 OBJECT-TYPE
		SYNTAX  	DisplayString
		MAX-ACCESS  	read-only
		STATUS  	current

		DESCRIPTION
		 " to get PA EDFA PLUS card optical low output power warning status for stage 2.
		-----------------------------
		Values :
		If Alarm is Present - Date and Time Stamp
			    eg:2017-5-18,9:47:20.0,+5:30
		If Alarm is Absent  - 0
		-----------------------------"

		::= { paEdfaPlusAlarmQueryEntry 20 }
		      
	paEdfaPlusModuleHighTemperatureAlarm OBJECT-TYPE
		SYNTAX  	DisplayString
		MAX-ACCESS  	read-only
		STATUS  	current

		DESCRIPTION
		 " to get PA EDFA PLUS card module high temperature alarm status.
		-----------------------------
		Values :
		If Alarm is Present - Date and Time Stamp
			    eg:2017-5-18,9:47:20.0,+5:30
		If Alarm is Absent  - 0
		-----------------------------"

		::= { paEdfaPlusAlarmQueryEntry 21 }	              
		      
	paEdfaPlusModuleLowTemperatureAlarm OBJECT-TYPE
		SYNTAX  	DisplayString
		MAX-ACCESS  	read-only
		STATUS  	current

		DESCRIPTION
		 " to get PA EDFA PLUS card module low temperature alarm status.
		-----------------------------
		Values :
		If Alarm is Present - Date and Time Stamp
			    eg:2017-5-18,9:47:20.0,+5:30
		If Alarm is Absent  - 0
		-----------------------------"
	
	      ::= { paEdfaPlusAlarmQueryEntry 22 }	              
		      
	paEdfaPlusModuleHighTemperatureWarning OBJECT-TYPE
		SYNTAX  	DisplayString
		MAX-ACCESS  	read-only
		STATUS  	current

		DESCRIPTION
		 " to get PA EDFA PLUS card module high temperature warning status.
		-----------------------------
		Values :
		If Alarm is Present - Date and Time Stamp
			    eg:2017-5-18,9:47:20.0,+5:30
		If Alarm is Absent  - 0
		-----------------------------"

		::= { paEdfaPlusAlarmQueryEntry 23 }	              
		      
	paEdfaPlusModuleLowTemperatureWarning OBJECT-TYPE
		SYNTAX  	DisplayString
		MAX-ACCESS  	read-only
		STATUS  	current

		DESCRIPTION
		 " to get PA EDFA PLUS card module low temperature warning status.
		-----------------------------
		Values :
		If Alarm is Present - Date and Time Stamp
			    eg:2017-5-18,9:47:20.0,+5:30
		If Alarm is Absent  - 0
		-----------------------------"

		::= { paEdfaPlusAlarmQueryEntry 24 }

	paEdfaPlusPump1HighTemperatureAlarm OBJECT-TYPE
		SYNTAX  	DisplayString
		MAX-ACCESS  	read-only
		STATUS  	current

		DESCRIPTION
		 " to get PA EDFA PLUS card pump 1 high temperature alarm status.
		-----------------------------
		Values :
		If Alarm is Present - Date and Time Stamp
			    eg:2017-5-18,9:47:20.0,+5:30
		If Alarm is Absent  - 0
		-----------------------------"

		::= { paEdfaPlusAlarmQueryEntry 25 }	              

	paEdfaPlusPump2HighTemperatureAlarm OBJECT-TYPE
		SYNTAX  	DisplayString
		MAX-ACCESS  	read-only
		STATUS  	current

		DESCRIPTION
		 " to get PA EDFA PLUS card pump 2 high temperature alarm status.
		-----------------------------
		Values :
		If Alarm is Present - Date and Time Stamp
			    eg:2017-5-18,9:47:20.0,+5:30
		If Alarm is Absent  - 0
		-----------------------------"

		::= { paEdfaPlusAlarmQueryEntry 26 }
		      
	paEdfaPlusPump1LowTemperatureAlarm OBJECT-TYPE
		SYNTAX  	DisplayString
		MAX-ACCESS  	read-only
		STATUS  	current

		DESCRIPTION
		 " to get PA EDFA PLUS card pump 1 low temperature alarm status.
		-----------------------------
		Values :
		If Alarm is Present - Date and Time Stamp
			    eg:2017-5-18,9:47:20.0,+5:30
		If Alarm is Absent  - 0
		-----------------------------"

		::= { paEdfaPlusAlarmQueryEntry 27 }	              

	paEdfaPlusPump2LowTemperatureAlarm OBJECT-TYPE
		SYNTAX  	DisplayString
		MAX-ACCESS  	read-only
		STATUS  	current

		DESCRIPTION
		 " to get PA EDFA PLUS card pump 2 low temperature alarm status.
		-----------------------------
		Values :
		If Alarm is Present - Date and Time Stamp
			    eg:2017-5-18,9:47:20.0,+5:30
		If Alarm is Absent  - 0
		-----------------------------"

		::= { paEdfaPlusAlarmQueryEntry 28 }
	      
	paEdfaPlusPump1HighTemperatureWarning OBJECT-TYPE
		SYNTAX  	DisplayString
		MAX-ACCESS  	read-only
		STATUS  	current

		DESCRIPTION
		 " to get PA EDFA PLUS card pump 1 high temperature warning status.
		-----------------------------
		Values :
		If Alarm is Present - Date and Time Stamp
			    eg:2017-5-18,9:47:20.0,+5:30
		If Alarm is Absent  - 0
		-----------------------------"

		::= { paEdfaPlusAlarmQueryEntry 29 }	              

	paEdfaPlusPump2HighTemperatureWarning OBJECT-TYPE
		SYNTAX  	DisplayString
		MAX-ACCESS  	read-only
		STATUS  	current

		DESCRIPTION
		 " to get PA EDFA PLUS card pump 2 high temperature warning status.
		-----------------------------
		Values :
		If Alarm is Present - Date and Time Stamp
			    eg:2017-5-18,9:47:20.0,+5:30
		If Alarm is Absent  - 0
		-----------------------------"

		::= { paEdfaPlusAlarmQueryEntry 30 }
		      
	paEdfaPlusPump1LowTemperatureWarning OBJECT-TYPE
		SYNTAX  	DisplayString
		MAX-ACCESS  	read-only
		STATUS  	current

		DESCRIPTION
		 " to get PA EDFA PLUS card pump 1 low temperature warning status.
		-----------------------------
		Values :
		If Alarm is Present - Date and Time Stamp
			    eg:2017-5-18,9:47:20.0,+5:30
		If Alarm is Absent  - 0
		-----------------------------"

		::= { paEdfaPlusAlarmQueryEntry 31 }	              

	paEdfaPlusPump2LowTemperatureWarning OBJECT-TYPE
		SYNTAX  	DisplayString
		MAX-ACCESS  	read-only
		STATUS  	current

		DESCRIPTION
		 " to get PA EDFA PLUS card pump 2 low temperature warning status.
		-----------------------------
		Values :
		If Alarm is Present - Date and Time Stamp
			    eg:2017-5-18,9:47:20.0,+5:30
		If Alarm is Absent  - 0
		-----------------------------"

		::= { paEdfaPlusAlarmQueryEntry 32 }
		      
	paEdfaPlusPump1HighOperatingCurrentAlarm OBJECT-TYPE
		SYNTAX  	DisplayString
		MAX-ACCESS  	read-only
		STATUS  	current

		DESCRIPTION
		 " to get PA EDFA PLUS card pump 1 high operating current alarm status.
		-----------------------------
		Values :
		If Alarm is Present - Date and Time Stamp
			    eg:2017-5-18,9:47:20.0,+5:30
		If Alarm is Absent  - 0
		-----------------------------"
	
	      ::= { paEdfaPlusAlarmQueryEntry 33 }	              

	paEdfaPlusPump2HighOperatingCurrentAlarm OBJECT-TYPE
		SYNTAX  	DisplayString
		MAX-ACCESS  	read-only
		STATUS  	current

		DESCRIPTION
		 " to get PA EDFA PLUS card pump 2 high operating current alarm status.
		-----------------------------
		Values :
		If Alarm is Present - Date and Time Stamp
			    eg:2017-5-18,9:47:20.0,+5:30
		If Alarm is Absent  - 0
		-----------------------------"
	
	      ::= { paEdfaPlusAlarmQueryEntry 34 }
		      
	paEdfaPlusPump1LowOperatingCurrentAlarm OBJECT-TYPE
		SYNTAX  	DisplayString
		MAX-ACCESS  	read-only
		STATUS  	current

		DESCRIPTION
		 " to get PA EDFA PLUS card pump 1 low operating current alarm status.
		-----------------------------
		Values :
		If Alarm is Present - Date and Time Stamp
			    eg:2017-5-18,9:47:20.0,+5:30
		If Alarm is Absent  - 0
		-----------------------------"

		::= { paEdfaPlusAlarmQueryEntry 35 }	              

	paEdfaPlusPump2LowOperatingCurrentAlarm OBJECT-TYPE
		SYNTAX  	DisplayString
		MAX-ACCESS  	read-only
		STATUS  	current

		DESCRIPTION
		 " to get PA EDFA PLUS card pump 2 low operating current alarm status.
		-----------------------------
		Values :
		If Alarm is Present - Date and Time Stamp
			    eg:2017-5-18,9:47:20.0,+5:30
		If Alarm is Absent  - 0
		-----------------------------"

		::= { paEdfaPlusAlarmQueryEntry 36 }
		      
	paEdfaPlusPump1HighOperatingCurrentWarning OBJECT-TYPE
		SYNTAX  	DisplayString
		MAX-ACCESS  	read-only
		STATUS  	current

		DESCRIPTION
		 " to get PA EDFA PLUS card pump 1 high operating current warning status.
		-----------------------------
		Values :
		If Alarm is Present - Date and Time Stamp
			    eg:2017-5-18,9:47:20.0,+5:30
		If Alarm is Absent  - 0
		-----------------------------"

		::= { paEdfaPlusAlarmQueryEntry 37 }

	paEdfaPlusPump2HighOperatingCurrentWarning OBJECT-TYPE
		SYNTAX  	DisplayString
		MAX-ACCESS  	read-only
		STATUS  	current

		DESCRIPTION
		 " to get PA EDFA PLUS card pump 2 high operating current warning status.
		-----------------------------
		Values :
		If Alarm is Present - Date and Time Stamp
			    eg:2017-5-18,9:47:20.0,+5:30
		If Alarm is Absent  - 0
		-----------------------------"

		::= { paEdfaPlusAlarmQueryEntry 38 }

	paEdfaPlusPump1LowOperatingCurrentWarning OBJECT-TYPE
		SYNTAX  	DisplayString
		MAX-ACCESS  	read-only
		STATUS  	current

		DESCRIPTION
		 " to get PA EDFA PLUS card pump 1 low operating current warning status.
		-----------------------------
		Values :
		If Alarm is Present - Date and Time Stamp
			    eg:2017-5-18,9:47:20.0,+5:30
		If Alarm is Absent  - 0
		-----------------------------"

		::= { paEdfaPlusAlarmQueryEntry 39 }

	paEdfaPlusPump2LowOperatingCurrentWarning OBJECT-TYPE
		SYNTAX  	DisplayString
		MAX-ACCESS  	read-only
		STATUS  	current

		DESCRIPTION
		 " to get PA EDFA PLUS card pump 2 low operating current warning status.
		-----------------------------
		Values :
		If Alarm is Present - Date and Time Stamp
			    eg:2017-5-18,9:47:20.0,+5:30
		If Alarm is Absent  - 0
		-----------------------------"

		::= { paEdfaPlusAlarmQueryEntry 40 }

	paEdfaPlusPump1HighThermoElectricCoolerCurrentAlarm OBJECT-TYPE
		SYNTAX  	DisplayString
		MAX-ACCESS  	read-only
		STATUS  	current

		DESCRIPTION
		 " to get PA EDFA PLUS card pump 1 high thermo electric cooler current alarm status.
		-----------------------------
		Values :
		If Alarm is Present - Date and Time Stamp
			    eg:2017-5-18,9:47:20.0,+5:30
		If Alarm is Absent  - 0
		-----------------------------"

		::= { paEdfaPlusAlarmQueryEntry 41 }

	paEdfaPlusPump2HighThermoElectricCoolerCurrentAlarm OBJECT-TYPE
		SYNTAX  	DisplayString
		MAX-ACCESS  	read-only
		STATUS  	current

		DESCRIPTION
		 " to get PA EDFA PLUS card pump 2 high thermo electric cooler current alarm status.
		-----------------------------
		Values :
		If Alarm is Present - Date and Time Stamp
			    eg:2017-5-18,9:47:20.0,+5:30
		If Alarm is Absent  - 0
		-----------------------------"

		::= { paEdfaPlusAlarmQueryEntry 42 }

	paEdfaPlusPump1LowThermoElectricCoolerCurrentAlarm OBJECT-TYPE
		SYNTAX  	DisplayString
		MAX-ACCESS  	read-only
		STATUS  	current

		DESCRIPTION
		 " to get PA EDFA PLUS card pump 1 low thermo electric cooler current alarm status.
		-----------------------------
		Values :
		If Alarm is Present - Date and Time Stamp
			    eg:2017-5-18,9:47:20.0,+5:30
		If Alarm is Absent  - 0
		-----------------------------"

		::= { paEdfaPlusAlarmQueryEntry 43 }

	paEdfaPlusPump2LowThermoElectricCoolerCurrentAlarm OBJECT-TYPE
		SYNTAX  	DisplayString
		MAX-ACCESS  	read-only
		STATUS  	current

		DESCRIPTION
		 " to get PA EDFA PLUS card pump 2 low thermo electric cooler current alarm status.
		-----------------------------
		Values :
		If Alarm is Present - Date and Time Stamp
			    eg:2017-5-18,9:47:20.0,+5:30
		If Alarm is Absent  - 0
		-----------------------------"

		::= { paEdfaPlusAlarmQueryEntry 44 }

	paEdfaPlusPump1HighThermoElectricCoolerCurrentWarning OBJECT-TYPE
		SYNTAX  	DisplayString
		MAX-ACCESS  	read-only
		STATUS  	current

		DESCRIPTION
		 " to get PA EDFA PLUS card pump 1 high thermo electric cooler current warning status.
		-----------------------------
		Values :
		If Alarm is Present - Date and Time Stamp
			    eg:2017-5-18,9:47:20.0,+5:30
		If Alarm is Absent  - 0
		-----------------------------"

		::= { paEdfaPlusAlarmQueryEntry 45 }

	paEdfaPlusPump2HighThermoElectricCoolerCurrentWarning OBJECT-TYPE
		SYNTAX  	DisplayString
		MAX-ACCESS  	read-only
		STATUS  	current

		DESCRIPTION
		 " to get PA EDFA PLUS card pump 2 high thermo electric cooler current warning status.
		-----------------------------
		Values :
		If Alarm is Present - Date and Time Stamp
			    eg:2017-5-18,9:47:20.0,+5:30
		If Alarm is Absent  - 0
		-----------------------------"

		::= { paEdfaPlusAlarmQueryEntry 46 }

	paEdfaPlusPump1LowThermoElectricCoolerCurrentWarning OBJECT-TYPE
		SYNTAX  	DisplayString
		MAX-ACCESS  	read-only
		STATUS  	current

		DESCRIPTION
		 " to get PA EDFA PLUS card pump 1 low thermo electric cooler current warning status.
		-----------------------------
		Values :
		If Alarm is Present - Date and Time Stamp
			    eg:2017-5-18,9:47:20.0,+5:30
		If Alarm is Absent  - 0
		-----------------------------"

		::= { paEdfaPlusAlarmQueryEntry 47 }

	paEdfaPlusPump2LowThermoElectricCoolerCurrentWarning OBJECT-TYPE
		SYNTAX  	DisplayString
		MAX-ACCESS  	read-only
		STATUS  	current

		DESCRIPTION
		 " to get PA EDFA PLUS card pump 2 low thermo electric cooler current warning status.
		-----------------------------
		Values :
		If Alarm is Present - Date and Time Stamp
			    eg:2017-5-18,9:47:20.0,+5:30
		If Alarm is Absent  - 0
		-----------------------------"

		::= { paEdfaPlusAlarmQueryEntry 48 }

	paEdfaPlusVariableOpticalAttenuatorHighInputPowerAlarm OBJECT-TYPE
		SYNTAX  	DisplayString
		MAX-ACCESS  	read-only
		STATUS  	current

		DESCRIPTION
		 " to get PA EDFA PLUS card variable optical attenuator high input power alarm status.
		-----------------------------
		Values :
		If Alarm is Present - Date and Time Stamp
			    eg:2017-5-18,9:47:20.0,+5:30
		If Alarm is Absent  - 0
		-----------------------------"

		::= { paEdfaPlusAlarmQueryEntry 49 }

	paEdfaPlusVariableOpticalAttenuatorLowInputPowerAlarm OBJECT-TYPE
		SYNTAX  	DisplayString
		MAX-ACCESS  	read-only
		STATUS  	current

		DESCRIPTION
		 " to get PA EDFA PLUS card variable optical attenuator low input power alarm status.
		-----------------------------
		Values :
		If Alarm is Present - Date and Time Stamp
			    eg:2017-5-18,9:47:20.0,+5:30
		If Alarm is Absent  - 0
		-----------------------------"

		::= { paEdfaPlusAlarmQueryEntry 50 }

	paEdfaPlusVariableOpticalAttenuatorHighInputPowerWarning OBJECT-TYPE
		SYNTAX  	DisplayString
		MAX-ACCESS  	read-only
		STATUS  	current

		DESCRIPTION
		 " to get PA EDFA PLUS card variable optical attenuator high input power warning status.
		-----------------------------
		Values :
		If Alarm is Present - Date and Time Stamp
			    eg:2017-5-18,9:47:20.0,+5:30
		If Alarm is Absent  - 0
		-----------------------------"

		::= { paEdfaPlusAlarmQueryEntry 51 }

	paEdfaPlusVariableOpticalAttenuatorLowInputPowerWarning OBJECT-TYPE
		SYNTAX  	DisplayString
		MAX-ACCESS  	read-only
		STATUS  	current

		DESCRIPTION
		 " to get PA EDFA PLUS card variable optical attenuator low input power warning status.
		-----------------------------
		Values :
		If Alarm is Present - Date and Time Stamp
			    eg:2017-5-18,9:47:20.0,+5:30
		If Alarm is Absent  - 0
		-----------------------------"

		::= { paEdfaPlusAlarmQueryEntry 52 }	              

	paEdfaPlusInputOutOfRangeAlarm OBJECT-TYPE
		SYNTAX  	DisplayString
		MAX-ACCESS  	read-only
		STATUS  	current

		DESCRIPTION
		 " to get PA EDFA PLUS card input out of range alarm status.
		-----------------------------
		Values :
		If Alarm is Present - Date and Time Stamp
			    eg:2017-5-18,9:47:20.0,+5:30
		If Alarm is Absent  - 0
		-----------------------------"

		::= { paEdfaPlusAlarmQueryEntry 53 }

	paEdfaPlusOutputOutOfRangeAlarm OBJECT-TYPE
		SYNTAX  	DisplayString
		MAX-ACCESS  	read-only
		STATUS  	current

		DESCRIPTION
		 " to get PA EDFA PLUS card output out of range alarm status.
		-----------------------------
		Values :
		If Alarm is Present - Date and Time Stamp
			    eg:2017-5-18,9:47:20.0,+5:30
		If Alarm is Absent  - 0
		-----------------------------"

		::= { paEdfaPlusAlarmQueryEntry 54 }

	paEdfaPlusMidInOutOfRangeAlarm OBJECT-TYPE
		SYNTAX  	DisplayString
		MAX-ACCESS  	read-only
		STATUS  	current

		DESCRIPTION
		 " to get PA EDFA PLUS card stage 2 input out of range alarm status.
		-----------------------------
		Values :
		If Alarm is Present - Date and Time Stamp
			    eg:2017-5-18,9:47:20.0,+5:30
		If Alarm is Absent  - 0
		-----------------------------"

		::= { paEdfaPlusAlarmQueryEntry 55 }

	paEdfaPlusMidOutOutOfRangeAlarm OBJECT-TYPE
		SYNTAX  	DisplayString
		MAX-ACCESS  	read-only
		STATUS  	current

		DESCRIPTION
		 " to get PA EDFA PLUS card stage 1 output out of range alarm status.
		-----------------------------
		Values :
		If Alarm is Present - Date and Time Stamp
			    eg:2017-5-18,9:47:20.0,+5:30
		If Alarm is Absent  - 0
		-----------------------------"

		::= { paEdfaPlusAlarmQueryEntry 56 }

	paEdfaPlusPumpBiasCurrentAlarm OBJECT-TYPE
		SYNTAX  	DisplayString
		MAX-ACCESS  	read-only
		STATUS  	current

		DESCRIPTION
		 " to get PA EDFA PLUS card pump bias current alarm status.
		-----------------------------
		Values :
		If Alarm is Present - Date and Time Stamp
			    eg:2017-5-18,9:47:20.0,+5:30
		If Alarm is Absent  - 0
		-----------------------------"

		::= { paEdfaPlusAlarmQueryEntry 57 }

	paEdfaPlusPump1CoolingTemperatureAlarm OBJECT-TYPE
		SYNTAX  	DisplayString
		MAX-ACCESS  	read-only
		STATUS  	current

		DESCRIPTION
		 " to get PA EDFA PLUS card pump 1 cooling temperature alarm status for stage 1.
		-----------------------------
		Values :
		If Alarm is Present - Date and Time Stamp
			    eg:2017-5-18,9:47:20.0,+5:30
		If Alarm is Absent  - 0
		-----------------------------"

		::= { paEdfaPlusAlarmQueryEntry 58 }

	paEdfaPlusPump2CoolingTemperatureAlarm OBJECT-TYPE
		SYNTAX  	DisplayString
		MAX-ACCESS  	read-only
		STATUS  	current

		DESCRIPTION
		 " to get PA EDFA PLUS card pump 2 cooling temperature alarm status for stage 1.
		-----------------------------
		Values :
		If Alarm is Present - Date and Time Stamp
			    eg:2017-5-18,9:47:20.0,+5:30
		If Alarm is Absent  - 0
		-----------------------------"

		::= { paEdfaPlusAlarmQueryEntry 59 }

	paEdfaPlusPump1LaserPowerAlarm OBJECT-TYPE
		SYNTAX  	DisplayString
		MAX-ACCESS  	read-only
		STATUS  	current

		DESCRIPTION
		 " to get PA EDFA PLUS card pump 1 laser power alarm status for stage 1.
		-----------------------------
		Values :
		If Alarm is Present - Date and Time Stamp
			    eg:2017-5-18,9:47:20.0,+5:30
		If Alarm is Absent  - 0
		-----------------------------"

		::= { paEdfaPlusAlarmQueryEntry 60 }

	paEdfaPlusPump2LaserPowerAlarm OBJECT-TYPE
		SYNTAX  	DisplayString
		MAX-ACCESS  	read-only
		STATUS  	current

		DESCRIPTION
		 " to get PA EDFA PLUS card pump 2 laser power alarm status for stage 1.
		-----------------------------
		Values :
		If Alarm is Present - Date and Time Stamp
			    eg:2017-5-18,9:47:20.0,+5:30
		If Alarm is Absent  - 0
		-----------------------------"

		::= { paEdfaPlusAlarmQueryEntry 61 }

	paEdfaPlusAlarmQueryTableRowStatus OBJECT-TYPE
              SYNTAX      RowStatus
              MAX-ACCESS  read-write
              STATUS      current
              DESCRIPTION
                      "	This is MIB realted property,
			NOT to be considered as a card property"
              ::= { paEdfaPlusAlarmQueryEntry 62 }

--*****************************************************************************
--				PA EDFA PLUS PERFORMANCE
--***************************************************************************** 

	paEdfaPlusPerformanceTable OBJECT-TYPE
		SYNTAX  	SEQUENCE OF PaEdfaPlusPerformanceEntry
		MAX-ACCESS  	not-accessible
		STATUS  	current

		DESCRIPTION
		 "we can get PA EDFA PLUS card performance details "

		::= { paEdfaPlusPerformance 1 }
	      
	paEdfaPlusPerformanceEntry OBJECT-TYPE
		SYNTAX  	PaEdfaPlusPerformanceEntry
		MAX-ACCESS  	not-accessible
		STATUS  	current

		DESCRIPTION 
		 "Enter node rack, subrack, slot and paEdfaPlusInterface numbers"

		INDEX   { node, rack, subRack, slot, paEdfaPlusInterface }

		::= { paEdfaPlusPerformanceTable 1 }
	
	PaEdfaPlusPerformanceEntry ::= 
		SEQUENCE {
				paEdfaPlusModuleTemperature					DisplayString,
				paEdfaPlusInputPowerForStage1					DisplayString,
				paEdfaPlusInputPowerForStage2					DisplayString,
				paEdfaPlusOutputPowerForStage1					DisplayString,
				paEdfaPlusOutputPowerForStage2					DisplayString,
				paEdfaPlusAmplifiedSpontaneousEmmissionPowerForStage1		DisplayString,
				paEdfaPlusAmplifiedSpontaneousEmmissionPowerForStage2		DisplayString,
				paEdfaPlusSignalGainForStage1					DisplayString,
				paEdfaPlusSignalGainForStage2					DisplayString,
				paEdfaPlusSignalOutputPowerForStage1				DisplayString,
				paEdfaPlusSignalOutputPowerForStage2				DisplayString,
				paEdfaPlusPump1LaserPower					DisplayString,
				paEdfaPlusPump2LaserPower					DisplayString,
				paEdfaPlusPump1Temperature					DisplayString,
				paEdfaPlusPump2Temperature					DisplayString,
				paEdfaPlusPump1OperatingCurrent					DisplayString,
				paEdfaPlusPump2OperatingCurrent					DisplayString,
				paEdfaPlusPump1ThermoElectricCoolerCurrent			DisplayString,
				paEdfaPlusPump2ThermoElectricCoolerCurrent			DisplayString,
				paEdfaPlusPump1CoolingTemperature				DisplayString,
				paEdfaPlusPump2CoolingTemperature				DisplayString,
				paEdfaPlusVariableOpticalAttenuatorInputPower			DisplayString,
				paEdfaPlusVariableOpticalAttenuatorOutputPower			DisplayString,
				paEdfaPlusVariableOpticalAttenuatorActualAttenuation		DisplayString,
				paEdfaPlusPerformanceTableRowStatus				RowStatus
			}
	
	paEdfaPlusModuleTemperature OBJECT-TYPE
		SYNTAX  	DisplayString
		MAX-ACCESS  	read-only
		STATUS  	current

		DESCRIPTION
		 " to get PA EDFA PLUS card module temperature.
		-----------------------------
		Values:
		eg: 18.5
		-----------------------------"

		::= { paEdfaPlusPerformanceEntry 1 }

	paEdfaPlusInputPowerForStage1 OBJECT-TYPE
		SYNTAX  	DisplayString
		MAX-ACCESS  	read-only
		STATUS  	current

		DESCRIPTION
		 " to get PA EDFA PLUS card input power for stage 1.
		-----------------------------
		Values:
		eg: 1.5
		-----------------------------"

		::= { paEdfaPlusPerformanceEntry 2 }	 

	paEdfaPlusInputPowerForStage2 OBJECT-TYPE
		SYNTAX  	DisplayString
		MAX-ACCESS  	read-only
		STATUS  	current

		DESCRIPTION
		 " to get PA EDFA PLUS card input power for stage 2.
		-----------------------------
		Values:
		eg: 1.5
		-----------------------------"

		::= { paEdfaPlusPerformanceEntry 3 }
	      
	paEdfaPlusOutputPowerForStage1 OBJECT-TYPE
		SYNTAX  	DisplayString
		MAX-ACCESS  	read-only
		STATUS  	current

		DESCRIPTION
		 " to get PA EDFA PLUS card output power for stage 1.
		-----------------------------
		Values:
		eg: 18.5
		-----------------------------"
	
	      ::= { paEdfaPlusPerformanceEntry 4 }	 

	paEdfaPlusOutputPowerForStage2 OBJECT-TYPE
		SYNTAX  	DisplayString
		MAX-ACCESS  	read-only
		STATUS  	current

		DESCRIPTION
		 " to get PA EDFA PLUS card output power for stage 2.
		-----------------------------
		Values:
		eg: 18.5
		-----------------------------"
	
	      ::= { paEdfaPlusPerformanceEntry 5 }	 

	paEdfaPlusAmplifiedSpontaneousEmmissionPowerForStage1 OBJECT-TYPE
		SYNTAX  	DisplayString
		MAX-ACCESS  	read-only
		STATUS  	current

		DESCRIPTION
		 " to get PA EDFA PLUS card Amplified Spontaneous Emmission power for stage 1.
		-----------------------------
		Values:
		eg: 2.5
		-----------------------------"

		::= { paEdfaPlusPerformanceEntry 6 }

	paEdfaPlusAmplifiedSpontaneousEmmissionPowerForStage2 OBJECT-TYPE
		SYNTAX  	DisplayString
		MAX-ACCESS  	read-only
		STATUS  	current

		DESCRIPTION
		 " to get PA EDFA PLUS card Amplified Spontaneous Emmission power for stage 2.
		-----------------------------
		Values:
		eg: 2.5
		-----------------------------"

		::= { paEdfaPlusPerformanceEntry 7 }

	paEdfaPlusSignalGainForStage1 OBJECT-TYPE
		SYNTAX  	DisplayString
		MAX-ACCESS  	read-only
		STATUS  	current

		DESCRIPTION
		 " to get PA EDFA PLUS signal gain for stage 1.
		-----------------------------
		Values:
		eg: 18.5
		-----------------------------"

		::= { paEdfaPlusPerformanceEntry 8 }

	paEdfaPlusSignalGainForStage2 OBJECT-TYPE
		SYNTAX  	DisplayString
		MAX-ACCESS  	read-only
		STATUS  	current

		DESCRIPTION
		 " to get PA EDFA PLUS signal gain for stage 2.
		-----------------------------
		Values:
		eg: 18.5
		-----------------------------"

		::= { paEdfaPlusPerformanceEntry 9 }

	paEdfaPlusSignalOutputPowerForStage1 OBJECT-TYPE
		SYNTAX  	DisplayString
		MAX-ACCESS  	read-only
		STATUS  	current

		DESCRIPTION
		 " to get PA EDFA PLUS card signal output power for stage 1.
		-----------------------------
		Values:
		eg: 18.5
		-----------------------------"

		::= { paEdfaPlusPerformanceEntry 10 }

	paEdfaPlusSignalOutputPowerForStage2 OBJECT-TYPE
		SYNTAX  	DisplayString
		MAX-ACCESS  	read-only
		STATUS  	current

		DESCRIPTION
		 " to get PA EDFA PLUS card signal output power for stage 2.
		-----------------------------
		Values:
		eg: 18.5
		-----------------------------"

		::= { paEdfaPlusPerformanceEntry 11 }
	      	
	paEdfaPlusPump1LaserPower OBJECT-TYPE
		SYNTAX  	DisplayString
		MAX-ACCESS  	read-only
		STATUS  	current

		DESCRIPTION
		 " to get PA EDFA PLUS card pump 1 laser power.
		-----------------------------
		Values:
		eg: 18.5
		-----------------------------"

		::= { paEdfaPlusPerformanceEntry 21 }	 

	paEdfaPlusPump2LaserPower OBJECT-TYPE
		SYNTAX  	DisplayString
		MAX-ACCESS  	read-only
		STATUS  	current

		DESCRIPTION
		 " to get PA EDFA PLUS card pump 2 laser power.
		-----------------------------
		Values:
		eg: 18.5
		-----------------------------"

		::= { paEdfaPlusPerformanceEntry 22 }
	      
	paEdfaPlusPump1Temperature OBJECT-TYPE
		SYNTAX  	DisplayString
		MAX-ACCESS  	read-only
		STATUS  	current

		DESCRIPTION
		 " to get PA EDFA PLUS card pump 1 temperature.
		-----------------------------
		Values:
		eg: 18.5
		-----------------------------"

		::= { paEdfaPlusPerformanceEntry 23 }	 

	paEdfaPlusPump2Temperature OBJECT-TYPE
		SYNTAX  	DisplayString
		MAX-ACCESS  	read-only
		STATUS  	current

		DESCRIPTION
		 " to get PA EDFA PLUS card pump 2 temperature.
		-----------------------------
		Values:
		eg: 18.5
		-----------------------------"

		::= { paEdfaPlusPerformanceEntry 24 }

	paEdfaPlusPump1OperatingCurrent OBJECT-TYPE
		SYNTAX  	DisplayString
		MAX-ACCESS  	read-only
		STATUS  	current

		DESCRIPTION
		 " to get PA EDFA PLUS card pump 1 operating current.
		-----------------------------
		Values:
		eg: 18.5
		-----------------------------"

		::= { paEdfaPlusPerformanceEntry 25 }	 

	paEdfaPlusPump2OperatingCurrent OBJECT-TYPE
		SYNTAX  	DisplayString
		MAX-ACCESS  	read-only
		STATUS  	current

		DESCRIPTION
		 " to get PA EDFA PLUS card pump 2 operating current.
		-----------------------------
		Values:
		eg: 18.5
		-----------------------------"

		::= { paEdfaPlusPerformanceEntry 26 }
	      
	paEdfaPlusPump1ThermoElectricCoolerCurrent OBJECT-TYPE
		SYNTAX  	DisplayString
		MAX-ACCESS  	read-only
		STATUS  	current

		DESCRIPTION
		 " to get PA EDFA PLUS card pump 1 thermo electric cooler current.
		-----------------------------
		Values:
		eg: 18.5
		-----------------------------"
	
	      ::= { paEdfaPlusPerformanceEntry 27 }

	paEdfaPlusPump2ThermoElectricCoolerCurrent OBJECT-TYPE
		SYNTAX  	DisplayString
		MAX-ACCESS  	read-only
		STATUS  	current

		DESCRIPTION
		 " to get PA EDFA PLUS card pump 2 thermo electric cooler current.
		-----------------------------
		Values:
		eg: 18.5
		-----------------------------"
	
	      ::= { paEdfaPlusPerformanceEntry 28 }	

	paEdfaPlusPump1CoolingTemperature OBJECT-TYPE
		SYNTAX  	DisplayString
		MAX-ACCESS  	read-only
		STATUS  	current

		DESCRIPTION
		 " to get PA EDFA PLUS card pump 1 cooling temperature.
		-----------------------------
		Values:
		eg: 18.5
		-----------------------------"

		::= { paEdfaPlusPerformanceEntry 29 }

	paEdfaPlusPump2CoolingTemperature OBJECT-TYPE
		SYNTAX  	DisplayString
		MAX-ACCESS  	read-only
		STATUS  	current

		DESCRIPTION
		 " to get PA EDFA PLUS card pump 2 cooling temperature.
		-----------------------------
		Values:
		eg: 18.5
		-----------------------------"

		::= { paEdfaPlusPerformanceEntry 30 } 
	      
	paEdfaPlusVariableOpticalAttenuatorInputPower OBJECT-TYPE
		SYNTAX  	DisplayString
		MAX-ACCESS  	read-only
		STATUS  	current

		DESCRIPTION
		 " to get PA EDFA PLUS card variable optical attenuator input power.
		-----------------------------
		Values:
		eg: 18.5
		-----------------------------"

		::= { paEdfaPlusPerformanceEntry 41 }	 
	      		
	paEdfaPlusVariableOpticalAttenuatorOutputPower OBJECT-TYPE
		SYNTAX  	DisplayString
		MAX-ACCESS  	read-only
		STATUS  	current

		DESCRIPTION
		 " to get PA EDFA PLUS card output power.
		-----------------------------
		Values:
		eg: 18.5
		-----------------------------"

		::= { paEdfaPlusPerformanceEntry 42 }	 

	paEdfaPlusVariableOpticalAttenuatorActualAttenuation OBJECT-TYPE
		SYNTAX  	DisplayString
		MAX-ACCESS  	read-only
		STATUS  	current

		DESCRIPTION
		 " to get PA EDFA PLUS card variable optical attenuator actual attenuation.
		-----------------------------
		Values:
		eg: 18.5
		-----------------------------"

		::= { paEdfaPlusPerformanceEntry 43 }

	paEdfaPlusPerformanceTableRowStatus OBJECT-TYPE
              SYNTAX      RowStatus
              MAX-ACCESS  read-write
              STATUS      current
              DESCRIPTION
                      "	This is MIB realted property,
			NOT to be considered as a card property"
              ::= { paEdfaPlusPerformanceEntry 44 }

--*****************************************************************************
--		 	 PA EDFA PLUS Alarm Notification Table
--***************************************************************************** 

	paEdfaPlusOpticalInputPowerFailureAlarmForStage1Trap NOTIFICATION-TYPE
		OBJECTS  { paEdfaPlusOpticalInputPowerFailureAlarmForStage1
			}
		STATUS  current

		DESCRIPTION
		 " This trap is sent when paEdfaPlus optical input power failure alarm for stage 1 state changes "

		::= { paEdfaPlusAlarmNotification 1 }

	paEdfaPlusOpticalInputPowerFailureAlarmForStage2Trap NOTIFICATION-TYPE
		OBJECTS  { paEdfaPlusOpticalInputPowerFailureAlarmForStage2
			}
		STATUS  current

		DESCRIPTION
		 " This trap is sent when paEdfaPlus optical input power failure alarm for stage 2 state changes "

		::= { paEdfaPlusAlarmNotification 2 }
	      
	paEdfaPlusOpticalHighInputPowerAlarmForStage1Trap NOTIFICATION-TYPE
		OBJECTS  { paEdfaPlusOpticalHighInputPowerAlarmForStage1
			}
		STATUS  current

		DESCRIPTION
		 " This trap is sent when paEdfaPlus optical high input power alarm for stage 1 state changes "

		::= { paEdfaPlusAlarmNotification 3 }              

	paEdfaPlusOpticalHighInputPowerAlarmForStage2Trap NOTIFICATION-TYPE
		OBJECTS  { paEdfaPlusOpticalHighInputPowerAlarmForStage2
			}
		STATUS  current

		DESCRIPTION
		 " This trap is sent when paEdfaPlus optical high input power alarm for stage 2 state changes "

		::= { paEdfaPlusAlarmNotification 4 } 
	      
	paEdfaPlusOpticalLowInputPowerAlarmForStage1Trap NOTIFICATION-TYPE
		OBJECTS  { paEdfaPlusOpticalLowInputPowerAlarmForStage1
			}
		STATUS  current

		DESCRIPTION
		 " This trap is sent when paEdfaPlus optical low input power alarm for stage 1 state changes "

		::= { paEdfaPlusAlarmNotification 5 } 
	      
	paEdfaPlusOpticalLowInputPowerAlarmForStage2Trap NOTIFICATION-TYPE
		OBJECTS  { paEdfaPlusOpticalLowInputPowerAlarmForStage2
			}
		STATUS  current

		DESCRIPTION
		 " This trap is sent when paEdfaPlus optical low input power alarm for stage 2 state changes "

		::= { paEdfaPlusAlarmNotification 6 }
	      
	paEdfaPlusOpticalHighInputPowerWarningForStage1Trap NOTIFICATION-TYPE
		OBJECTS  { paEdfaPlusOpticalHighInputPowerWarningForStage1
			}
		STATUS  current

		DESCRIPTION
		 " This trap is sent when paEdfaPlus optical high input power warning for stage 1 state changes "

		::= { paEdfaPlusAlarmNotification 7 } 
	      
	paEdfaPlusOpticalHighInputPowerWarningForStage2Trap NOTIFICATION-TYPE
		OBJECTS  { paEdfaPlusOpticalHighInputPowerWarningForStage2
			}
		STATUS  current

		DESCRIPTION
		 " This trap is sent when paEdfaPlus optical high input power warning for stage 2 state changes "

		::= { paEdfaPlusAlarmNotification 8 } 
	      
	paEdfaPlusOpticalLowInputPowerWarningForStage1Trap NOTIFICATION-TYPE
		OBJECTS  { paEdfaPlusOpticalLowInputPowerWarningForStage1
			}
		STATUS  current

		DESCRIPTION
		 " This trap is sent when paEdfaPlus optical low input power warning for stage 1 state changes "

		::= { paEdfaPlusAlarmNotification 9 }      

	paEdfaPlusOpticalLowInputPowerWarningForStage2Trap NOTIFICATION-TYPE
		OBJECTS  { paEdfaPlusOpticalLowInputPowerWarningForStage2
			}
		STATUS  current

		DESCRIPTION
		 " This trap is sent when paEdfaPlus optical low input power warning for stage 2 state changes "

		::= { paEdfaPlusAlarmNotification 10 } 
	      
	paEdfaPlusOpticalOutputPowerFailureAlarmForStage1Trap NOTIFICATION-TYPE
		OBJECTS  { paEdfaPlusOpticalOutputPowerFailureAlarmForStage1
			}
		STATUS  current

		DESCRIPTION
		 " This trap is sent when paEdfaPlus optical output power failure alarm for stage 1 state changes "

		::= { paEdfaPlusAlarmNotification 11 } 
 
	paEdfaPlusOpticalOutputPowerFailureAlarmForStage2Trap NOTIFICATION-TYPE
		OBJECTS  { paEdfaPlusOpticalOutputPowerFailureAlarmForStage2
			}
		STATUS  current

		DESCRIPTION
		 " This trap is sent when paEdfaPlus optical output power failure alarm for stage 2 state changes "

		::= { paEdfaPlusAlarmNotification 12 } 	
     
	paEdfaPlusOpticalHighOutputPowerAlarmForStage1Trap NOTIFICATION-TYPE
		OBJECTS  { paEdfaPlusOpticalHighOutputPowerAlarmForStage1
			}
		STATUS  current

		DESCRIPTION
		 " This trap is sent when paEdfaPlus optical high output power alarm for stage 1 state changes "

		::= { paEdfaPlusAlarmNotification 13 }  

	paEdfaPlusOpticalHighOutputPowerAlarmForStage2Trap NOTIFICATION-TYPE
		OBJECTS  { paEdfaPlusOpticalHighOutputPowerAlarmForStage2
			}
		STATUS  current

		DESCRIPTION
		 " This trap is sent when paEdfaPlus optical high output power alarm for stage 2 state changes "

		::= { paEdfaPlusAlarmNotification 14 } 

	paEdfaPlusOpticalLowOutputPowerAlarmForStage1Trap NOTIFICATION-TYPE
		OBJECTS  { paEdfaPlusOpticalLowOutputPowerAlarmForStage1
			}
		STATUS  current

		DESCRIPTION
		 " This trap is sent when paEdfaPlus optical low output power alarm for stage 1 state changes "

		::= { paEdfaPlusAlarmNotification 15 }

	paEdfaPlusOpticalLowOutputPowerAlarmForStage2Trap NOTIFICATION-TYPE
		OBJECTS  { paEdfaPlusOpticalLowOutputPowerAlarmForStage2
			}
		STATUS  current

		DESCRIPTION
		 " This trap is sent when paEdfaPlus optical low output power alarm for stage 2 state changes "

		::= { paEdfaPlusAlarmNotification 16 }
	      
	paEdfaPlusOpticalHighOutputPowerWarningForStage1Trap NOTIFICATION-TYPE
		OBJECTS  { paEdfaPlusOpticalHighOutputPowerWarningForStage1
			}
		STATUS  current

		DESCRIPTION
		 " This trap is sent when paEdfaPlus optical high output power warning for stage 1 state changes "

		::= { paEdfaPlusAlarmNotification 17 }              

	paEdfaPlusOpticalHighOutputPowerWarningForStage2Trap NOTIFICATION-TYPE
		OBJECTS  { paEdfaPlusOpticalHighOutputPowerWarningForStage2
			}
		STATUS  current

		DESCRIPTION
		 " This trap is sent when paEdfaPlus optical high output power warning for stage 2 state changes "

		::= { paEdfaPlusAlarmNotification 18 } 
	      
	paEdfaPlusOpticalLowOutputPowerWarningForStage1Trap NOTIFICATION-TYPE
		OBJECTS  { paEdfaPlusOpticalLowOutputPowerWarningForStage1
			}
		STATUS  current

		DESCRIPTION
		 " This trap is sent when paEdfaPlus optical low output power warning for stage 1 state changes "

		::= { paEdfaPlusAlarmNotification 19 } 

	paEdfaPlusOpticalLowOutputPowerWarningForStage2Trap NOTIFICATION-TYPE
		OBJECTS  { paEdfaPlusOpticalLowOutputPowerWarningForStage2
			}
		STATUS  current

		DESCRIPTION
		 " This trap is sent when paEdfaPlus optical low output power warning for stage 2 state changes "

		::= { paEdfaPlusAlarmNotification 20 } 	      
	      
	paEdfaPlusModuleHighTemperatureAlarmTrap NOTIFICATION-TYPE
		OBJECTS  { paEdfaPlusModuleHighTemperatureAlarm
			}
		STATUS  current

		DESCRIPTION
		 " This trap is sent when paEdfaPlus module high temperature alarm state changes "

		::= { paEdfaPlusAlarmNotification 21 } 
	      	      
	paEdfaPlusModuleLowTemperatureAlarmTrap NOTIFICATION-TYPE
		OBJECTS  { paEdfaPlusModuleLowTemperatureAlarm
			}
		STATUS  current

		DESCRIPTION
		 " This trap is sent when paEdfaPlus module low temperature alarm state changes "

		::= { paEdfaPlusAlarmNotification 22 }      
	      
	paEdfaPlusModuleHighTemperatureWarningTrap NOTIFICATION-TYPE
		OBJECTS  { paEdfaPlusModuleHighTemperatureWarning
			}
		STATUS  current

		DESCRIPTION
		 " This trap is sent when paEdfaPlus module high temperature warning state changes "

		::= { paEdfaPlusAlarmNotification 23 }  
	     
	paEdfaPlusModuleLowTemperatureWarningTrap NOTIFICATION-TYPE
		OBJECTS  { paEdfaPlusModuleLowTemperatureWarning
			}
		STATUS  current

		DESCRIPTION
		 " This trap is sent when paEdfaPlus module low temperature warning state changes "

		::= { paEdfaPlusAlarmNotification 24 } 

	paEdfaPlusPump1HighTemperatureAlarmTrap NOTIFICATION-TYPE
		OBJECTS  { paEdfaPlusPump1HighTemperatureAlarm
			}
		STATUS  current

		DESCRIPTION
		 " This trap is sent when paEdfaPlus pump 1 high temperature alarm state changes "

		::= { paEdfaPlusAlarmNotification 25 }

	paEdfaPlusPump2HighTemperatureAlarmTrap NOTIFICATION-TYPE
		OBJECTS  { paEdfaPlusPump2HighTemperatureAlarm
			}
		STATUS  current

		DESCRIPTION
		 " This trap is sent when paEdfaPlus pump 2 high temperature alarm state changes "

		::= { paEdfaPlusAlarmNotification 26 }
	      
	paEdfaPlusPump1LowTemperatureAlarmTrap NOTIFICATION-TYPE
		OBJECTS  { paEdfaPlusPump1LowTemperatureAlarm
			}
		STATUS  current

		DESCRIPTION
		 " This trap is sent when paEdfaPlus pump 1 low temperature alarm state changes "

		::= { paEdfaPlusAlarmNotification 27 }              

	paEdfaPlusPump2LowTemperatureAlarmTrap NOTIFICATION-TYPE
		OBJECTS  { paEdfaPlusPump2LowTemperatureAlarm
			}
		STATUS  current

		DESCRIPTION
		 " This trap is sent when paEdfaPlus pump 2 low temperature alarm state changes "

		::= { paEdfaPlusAlarmNotification 28 }
	      
	paEdfaPlusPump1HighTemperatureWarningTrap NOTIFICATION-TYPE
		OBJECTS  { paEdfaPlusPump1HighTemperatureWarning
			}
		STATUS  current

		DESCRIPTION
		 " This trap is sent when paEdfaPlus pump 1 high temperature warning state changes "

		::= { paEdfaPlusAlarmNotification 29 } 
	      
	paEdfaPlusPump2HighTemperatureWarningTrap NOTIFICATION-TYPE
		OBJECTS  { paEdfaPlusPump2HighTemperatureWarning
			}
		STATUS  current

		DESCRIPTION
		 " This trap is sent when paEdfaPlus pump 2 high temperature warning state changes "

		::= { paEdfaPlusAlarmNotification 30 } 
	      
	paEdfaPlusPump1LowTemperatureWarningTrap NOTIFICATION-TYPE
		OBJECTS  { paEdfaPlusPump1LowTemperatureWarning
			}
		STATUS  current

		DESCRIPTION
		 " This trap is sent when paEdfaPlus pump 1 low temperature warning state changes "

		::= { paEdfaPlusAlarmNotification 31 } 
	      
	paEdfaPlusPump2LowTemperatureWarningTrap NOTIFICATION-TYPE
		OBJECTS  { paEdfaPlusPump2LowTemperatureWarning
			}
		STATUS  current

		DESCRIPTION
		 " This trap is sent when paEdfaPlus pump 2 low temperature warning state changes "

		::= { paEdfaPlusAlarmNotification 32 } 
	      
	paEdfaPlusPump1HighOperatingCurrentAlarmTrap NOTIFICATION-TYPE
		OBJECTS  { paEdfaPlusPump1HighOperatingCurrentAlarm
			}
		STATUS  current

		DESCRIPTION
		 " This trap is sent when paEdfaPlus pump 1 high operating current alarm state changes "

		::= { paEdfaPlusAlarmNotification 33 }      

	paEdfaPlusPump2HighOperatingCurrentAlarmTrap NOTIFICATION-TYPE
		OBJECTS  { paEdfaPlusPump2HighOperatingCurrentAlarm
			}
		STATUS  current

		DESCRIPTION
		 " This trap is sent when paEdfaPlus pump 2 high operating current alarm state changes "

		::= { paEdfaPlusAlarmNotification 34 }
	      
	paEdfaPlusPump1LowOperatingCurrentAlarmTrap NOTIFICATION-TYPE
		OBJECTS  { paEdfaPlusPump1LowOperatingCurrentAlarm
			}
		STATUS  current

		DESCRIPTION
		 " This trap is sent when paEdfaPlus pump 1 low operating current alarm state changes "

		::= { paEdfaPlusAlarmNotification 35 }  
	      
	paEdfaPlusPump2LowOperatingCurrentAlarmTrap NOTIFICATION-TYPE
		OBJECTS  { paEdfaPlusPump2LowOperatingCurrentAlarm
			}
		STATUS  current

		DESCRIPTION
		 " This trap is sent when paEdfaPlus pump 2 low operating current alarm state changes "

		::= { paEdfaPlusAlarmNotification 36 }  
	     
	paEdfaPlusPump1HighOperatingCurrentWarningTrap NOTIFICATION-TYPE
		OBJECTS  { paEdfaPlusPump1HighOperatingCurrentWarning
			}
		STATUS  current

		DESCRIPTION
		 " This trap is sent when paEdfaPlus pump 1 high operating current warning state changes "

		::= { paEdfaPlusAlarmNotification 37 } 
	     
	paEdfaPlusPump2HighOperatingCurrentWarningTrap NOTIFICATION-TYPE
		OBJECTS  { paEdfaPlusPump2HighOperatingCurrentWarning
			}
		STATUS  current

		DESCRIPTION
		 " This trap is sent when paEdfaPlus pump 2 high operating current warning state changes "

		::= { paEdfaPlusAlarmNotification 38 } 

	paEdfaPlusPump1LowOperatingCurrentWarningTrap NOTIFICATION-TYPE
		OBJECTS  { paEdfaPlusPump1LowOperatingCurrentWarning
			}
		STATUS  current

		DESCRIPTION
		 " This trap is sent when paEdfaPlus pump 1 low operating current warning state changes "

		::= { paEdfaPlusAlarmNotification 39 }

	paEdfaPlusPump2LowOperatingCurrentWarningTrap NOTIFICATION-TYPE
		OBJECTS  { paEdfaPlusPump2LowOperatingCurrentWarning
			}
		STATUS  current

		DESCRIPTION
		 " This trap is sent when paEdfaPlus pump 2 low operating current warning state changes "

		::= { paEdfaPlusAlarmNotification 40 }
	      
	paEdfaPlusPump1HighThermoElectricCoolerCurrentAlarmTrap NOTIFICATION-TYPE
		OBJECTS  { paEdfaPlusPump1HighThermoElectricCoolerCurrentAlarm
			}
		STATUS  current

		DESCRIPTION
		 " This trap is sent when paEdfaPlus pump 1 high thermo electric cooler current alarm state changes "

		::= { paEdfaPlusAlarmNotification 41 }              
	      
	paEdfaPlusPump2HighThermoElectricCoolerCurrentAlarmTrap NOTIFICATION-TYPE
		OBJECTS  { paEdfaPlusPump2HighThermoElectricCoolerCurrentAlarm
			}
		STATUS  current

		DESCRIPTION
		 " This trap is sent when paEdfaPlus pump 2 high thermo electric cooler current alarm state changes "

		::= { paEdfaPlusAlarmNotification 42 }
	      
	paEdfaPlusPump1LowThermoElectricCoolerCurrentAlarmTrap NOTIFICATION-TYPE
		OBJECTS  { paEdfaPlusPump1LowThermoElectricCoolerCurrentAlarm
			}
		STATUS  current

		DESCRIPTION
		 " This trap is sent when paEdfaPlus pump 1 low thermo electric cooler current alarm state changes "

		::= { paEdfaPlusAlarmNotification 43 } 
	      
	paEdfaPlusPump2LowThermoElectricCoolerCurrentAlarmTrap NOTIFICATION-TYPE
		OBJECTS  { paEdfaPlusPump2LowThermoElectricCoolerCurrentAlarm
			}
		STATUS  current

		DESCRIPTION
		 " This trap is sent when paEdfaPlus pump 2 low thermo electric cooler current alarm state changes "

		::= { paEdfaPlusAlarmNotification 44 } 	      
	      
	paEdfaPlusPump1HighThermoElectricCoolerCurrentWarningTrap NOTIFICATION-TYPE
		OBJECTS  { paEdfaPlusPump1HighThermoElectricCoolerCurrentWarning
			}
		STATUS  current

		DESCRIPTION
		 " This trap is sent when paEdfaPlus pump 1 high thermo electric cooler current warning state changes "

		::= { paEdfaPlusAlarmNotification 45 } 
	      
	paEdfaPlusPump2HighThermoElectricCoolerCurrentWarningTrap NOTIFICATION-TYPE
		OBJECTS  { paEdfaPlusPump2HighThermoElectricCoolerCurrentWarning
			}
		STATUS  current

		DESCRIPTION
		 " This trap is sent when paEdfaPlus pump 2 high thermo electric cooler current warning state changes "

		::= { paEdfaPlusAlarmNotification 46 } 
	      
	paEdfaPlusPump1LowThermoElectricCoolerCurrentWarningTrap NOTIFICATION-TYPE
		OBJECTS  { paEdfaPlusPump1LowThermoElectricCoolerCurrentWarning
			}
		STATUS  current

		DESCRIPTION
		 " This trap is sent when paEdfaPlus pump 1 low thermo electric cooler current warning state changes "

		::= { paEdfaPlusAlarmNotification 47 }            

	paEdfaPlusPump2LowThermoElectricCoolerCurrentWarningTrap NOTIFICATION-TYPE
		OBJECTS  { paEdfaPlusPump2LowThermoElectricCoolerCurrentWarning
			}
		STATUS  current

		DESCRIPTION
		 " This trap is sent when paEdfaPlus pump 2 low thermo electric cooler current warning state changes "

		::= { paEdfaPlusAlarmNotification 48 }  
	      
	paEdfaPlusVariableOpticalAttenuatorHighInputPowerAlarmTrap NOTIFICATION-TYPE
		OBJECTS  { paEdfaPlusVariableOpticalAttenuatorHighInputPowerAlarm
			}
		STATUS  current

		DESCRIPTION
		 " This trap is sent when paEdfaPlus variable optical attenuator high input power alarm state changes "

		::= { paEdfaPlusAlarmNotification 49 }              
	      
	paEdfaPlusVariableOpticalAttenuatorLowInputPowerAlarmTrap NOTIFICATION-TYPE
		OBJECTS  { paEdfaPlusVariableOpticalAttenuatorLowInputPowerAlarm
			}
		STATUS  current

		DESCRIPTION
		 " This trap is sent when paEdfaPlus variable optical attenuator low input power alarm state changes "

		::= { paEdfaPlusAlarmNotification 50 } 
	      	      
	paEdfaPlusVariableOpticalAttenuatorHighInputPowerWarningTrap NOTIFICATION-TYPE
		OBJECTS  { paEdfaPlusVariableOpticalAttenuatorHighInputPowerWarning
			}
		STATUS  current

		DESCRIPTION
		 " This trap is sent when paEdfaPlus variable optical attenuator high input power warning state changes "

		::= { paEdfaPlusAlarmNotification 51 } 
	            
	paEdfaPlusVariableOpticalAttenuatorLowInputPowerWarningTrap NOTIFICATION-TYPE
		OBJECTS  { paEdfaPlusVariableOpticalAttenuatorLowInputPowerWarning
			}
		STATUS  current

		DESCRIPTION
		 " This trap is sent when paEdfaPlus variable optical attenuator low input power warning state changes "

		::= { paEdfaPlusAlarmNotification 52 } 

	paEdfaPlusInputOutOfRangeAlarmTrap NOTIFICATION-TYPE
		OBJECTS  { paEdfaPlusInputOutOfRangeAlarm
			}
		STATUS  current

		DESCRIPTION
		 " This trap is sent when paEdfaPlus input out of range alarm state changes "

		::= { paEdfaPlusAlarmNotification 53 }

	paEdfaPlusOutputOutOfRangeAlarmTrap NOTIFICATION-TYPE
		OBJECTS  { paEdfaPlusOutputOutOfRangeAlarm
			}
		STATUS  current

		DESCRIPTION
		 " This trap is sent when paEdfaPlus output out of range alarm state changes "

		::= { paEdfaPlusAlarmNotification 54 }

	paEdfaPlusMidInOutOfRangeAlarmTrap NOTIFICATION-TYPE
		OBJECTS  { paEdfaPlusMidInOutOfRangeAlarm
			}
		STATUS  current

		DESCRIPTION
		 " This trap is sent when paEdfaPlus Mid input out of range alarm state changes "

		::= { paEdfaPlusAlarmNotification 55 }

	paEdfaPlusMidOutOutOfRangeAlarmTrap NOTIFICATION-TYPE
		OBJECTS  { paEdfaPlusMidOutOutOfRangeAlarm
			}
		STATUS  current

		DESCRIPTION
		 " This trap is sent when paEdfaPlus Mid output out of range alarm state changes "

		::= { paEdfaPlusAlarmNotification 56 }
	      
	paEdfaPlusPumpBiasCurrentAlarmTrap NOTIFICATION-TYPE
		OBJECTS  { paEdfaPlusPumpBiasCurrentAlarm
			}
		STATUS  current

		DESCRIPTION
		 " This trap is sent when paEdfaPlus pump bias current alarm state changes "

		::= { paEdfaPlusAlarmNotification 57 } 
	
	paEdfaPlusPump1CoolingTemperatureAlarmTrap NOTIFICATION-TYPE
		OBJECTS  { paEdfaPlusPump1CoolingTemperatureAlarm
			}
		STATUS  current

		DESCRIPTION
		 " This trap is sent when paEdfaPlus pump 1 cooling temperature alarm state changes "

		::= { paEdfaPlusAlarmNotification 58 } 

	paEdfaPlusPump2CoolingTemperatureAlarmTrap NOTIFICATION-TYPE
		OBJECTS  { paEdfaPlusPump2CoolingTemperatureAlarm
			}
		STATUS  current

		DESCRIPTION
		 " This trap is sent when paEdfaPlus pump 2 cooling temperature alarm state changes "

		::= { paEdfaPlusAlarmNotification 59 } 

	paEdfaPlusPump1LaserPowerAlarmTrap NOTIFICATION-TYPE
		OBJECTS  { paEdfaPlusPump1LaserPowerAlarm
			}
		STATUS  current

		DESCRIPTION
		 " This trap is sent when paEdfaPlus pump 1 laser power alarm state changes "

		::= { paEdfaPlusAlarmNotification 60 } 

	paEdfaPlusPump2LaserPowerAlarmTrap NOTIFICATION-TYPE
		OBJECTS  { paEdfaPlusPump2LaserPowerAlarm
			}
		STATUS  current

		DESCRIPTION
		 " This trap is sent when paEdfaPlus pump 2 laser power alarm state changes "

		::= { paEdfaPlusAlarmNotification 61 } 
	      
--*****************************************************************************
             
	snmpCurrentNotificationsGroup NOTIFICATION-GROUP
		NOTIFICATIONS 	{ 
					paEdfaPlusOpticalInputPowerFailureAlarmForStage1Trap,
					paEdfaPlusOpticalInputPowerFailureAlarmForStage2Trap,
					paEdfaPlusOpticalHighInputPowerAlarmForStage1Trap,
					paEdfaPlusOpticalHighInputPowerAlarmForStage2Trap,
					paEdfaPlusOpticalLowInputPowerAlarmForStage1Trap,
					paEdfaPlusOpticalLowInputPowerAlarmForStage2Trap,
					paEdfaPlusOpticalHighInputPowerWarningForStage1Trap,
					paEdfaPlusOpticalHighInputPowerWarningForStage2Trap,
					paEdfaPlusOpticalLowInputPowerWarningForStage1Trap,
					paEdfaPlusOpticalLowInputPowerWarningForStage2Trap,
					paEdfaPlusOpticalOutputPowerFailureAlarmForStage1Trap,
					paEdfaPlusOpticalOutputPowerFailureAlarmForStage2Trap,
					paEdfaPlusOpticalHighOutputPowerAlarmForStage1Trap,
					paEdfaPlusOpticalHighOutputPowerAlarmForStage2Trap,
					paEdfaPlusOpticalLowOutputPowerAlarmForStage1Trap,
					paEdfaPlusOpticalLowOutputPowerAlarmForStage2Trap,
					paEdfaPlusOpticalHighOutputPowerWarningForStage1Trap,
					paEdfaPlusOpticalHighOutputPowerWarningForStage2Trap,
					paEdfaPlusOpticalLowOutputPowerWarningForStage1Trap,
					paEdfaPlusOpticalLowOutputPowerWarningForStage2Trap,
					paEdfaPlusModuleHighTemperatureAlarmTrap,
					paEdfaPlusModuleLowTemperatureAlarmTrap,
					paEdfaPlusModuleHighTemperatureWarningTrap,
					paEdfaPlusModuleLowTemperatureWarningTrap,
					paEdfaPlusPump1HighTemperatureAlarmTrap,
					paEdfaPlusPump2HighTemperatureAlarmTrap,
					paEdfaPlusPump1LowTemperatureAlarmTrap,
					paEdfaPlusPump2LowTemperatureAlarmTrap,
					paEdfaPlusPump1HighTemperatureWarningTrap,
					paEdfaPlusPump2HighTemperatureWarningTrap,
					paEdfaPlusPump1LowTemperatureWarningTrap,
					paEdfaPlusPump2LowTemperatureWarningTrap,
					paEdfaPlusPump1HighOperatingCurrentAlarmTrap,
					paEdfaPlusPump2HighOperatingCurrentAlarmTrap,
					paEdfaPlusPump1LowOperatingCurrentAlarmTrap,
					paEdfaPlusPump2LowOperatingCurrentAlarmTrap,
					paEdfaPlusPump1HighOperatingCurrentWarningTrap,
					paEdfaPlusPump2HighOperatingCurrentWarningTrap,
					paEdfaPlusPump1LowOperatingCurrentWarningTrap,
					paEdfaPlusPump2LowOperatingCurrentWarningTrap,
					paEdfaPlusPump1HighThermoElectricCoolerCurrentAlarmTrap,
					paEdfaPlusPump2HighThermoElectricCoolerCurrentAlarmTrap,
					paEdfaPlusPump1LowThermoElectricCoolerCurrentAlarmTrap,
					paEdfaPlusPump2LowThermoElectricCoolerCurrentAlarmTrap,
					paEdfaPlusPump1HighThermoElectricCoolerCurrentWarningTrap,
					paEdfaPlusPump2HighThermoElectricCoolerCurrentWarningTrap,
					paEdfaPlusPump1LowThermoElectricCoolerCurrentWarningTrap,
					paEdfaPlusPump2LowThermoElectricCoolerCurrentWarningTrap,
					paEdfaPlusVariableOpticalAttenuatorHighInputPowerAlarmTrap,
					paEdfaPlusVariableOpticalAttenuatorLowInputPowerAlarmTrap,
					paEdfaPlusVariableOpticalAttenuatorHighInputPowerWarningTrap,
					paEdfaPlusVariableOpticalAttenuatorLowInputPowerWarningTrap,
					paEdfaPlusInputOutOfRangeAlarmTrap,
					paEdfaPlusOutputOutOfRangeAlarmTrap,
					paEdfaPlusMidInOutOfRangeAlarmTrap,
					paEdfaPlusMidOutOutOfRangeAlarmTrap,
					paEdfaPlusPumpBiasCurrentAlarmTrap,
					paEdfaPlusPump1CoolingTemperatureAlarmTrap,
					paEdfaPlusPump2CoolingTemperatureAlarmTrap,
					paEdfaPlusPump1LaserPowerAlarmTrap,
					paEdfaPlusPump2LaserPowerAlarmTrap
				}
		STATUS current

		DESCRIPTION
		"The UTL DWDM current notifications group"

		::= { paEdfaPlus 5 }                           

--***************************************************************************** 

	snmpcurrentGroup OBJECT-GROUP
		OBJECTS {
				paEdfaPlusInterface,
				paEdfaPlusEepromCardId,
				paEdfaPlusEepromCardName,
				paEdfaPlusEepromPartCode,
				paEdfaPlusEepromCardSerialNumber,
				paEdfaPlusEepromHardwareExternalReleaseVersion,
				paEdfaPlusSoftwareExternalReleaseVersion,
				paEdfaPlusEepromHardwareInternalReleaseVersion,
				paEdfaPlusSoftwareInternalReleaseVersion,
				paEdfaPlusEepromCardUidNumber,
				paEdfaPlusEepromCardEUI48Number,
				paEdfaPlusEepromCardEUI64Number,
				paEdfaPlusCardRootFileSystemVersion,
				paEdfaPlusInstallationDate,
				paEdfaPlusCommissionDate,
				paEdfaPlusCardRunningTime,
				paEdfaPlusCardRestartCount,
				paEdfaPlusModuleVendorName,
				paEdfaPlusModuleSerialNumber,
				paEdfaPlusNumberOfChannelsSupported,
				paEdfaPlusNumberOfPumpSupported,
				paEdfaPlusMaxGainSupported,
				paEdfaPlusSaturationOutputPowerSupported,
				paEdfaPlusMidStageAccessSupport,
				paEdfaPlusCardGeneralDetailsTableRowStatus,
				paEdfaPlusCardSoftReset,
				paEdfaPlusCardDefaultFactoryReset,
				paEdfaPlusAlarmMonitoringStatus,
				paEdfaPlusManageUnmanageStatus,
				paEdfaPlusSyncSystemTimeWithNtpServer,
				paEdfaPlusSyncRtcWithNtpServer,
				paEdfaPlusSyncRtcWithSystemTime,
				paEdfaPlusUpdateGivenTimeIntoSystem,
				paEdfaPlusUpdateGivenTimeIntoRtc,
				paEdfaPlusSystemTimeAndRtcTime,
				paEdfaPlusDirection,
				paEdfaPlusStage2VoaPresenceStatus,
				paEdfaPlusVariableOpticalAttenuatorReset,
				paEdfaPlusPump1LaserStatus,
				paEdfaPlusPump2LaserStatus,
				paEdfaPlusAutomaticPowerReductionStatusForStage1,
				paEdfaPlusAutomaticPowerReductionStatusForStage2,
				paEdfaPlusAutomaticLaserShutdownStatusForStage1,
				paEdfaPlusAutomaticLaserShutdownStatusForStage2,
				paEdfaPlusModuleOperatingModeForStage1,
				paEdfaPlusModuleOperatingModeForStage2,
				paEdfaPlusModuleGainInAutomaticGainControlModeForStage2,
				paEdfaPlusModuleGainInAutomaticGainControlModeForStage1,
				paEdfaPlusModuleOutputPowerInAutomaticPowerControlMode,
				paEdfaPlusPump1OperatingCurrentInAutomaticCurrentControlMode,
				paEdfaPlusPump2OperatingCurrentInAutomaticCurrentControlMode,
				paEdfaPlusGainTilt,
				paEdfaPlusVariableOpticalAttenuatorAttenuationForStage2,
				paEdfaPlusOutputPowerLimitFunctionStatusInAutomaticGainControlModeForStage1,
				paEdfaPlusOutputPowerLimitFunctionStatusInAutomaticGainControlModeForStage2,
				paEdfaPlusOutputPowerLimitInAutomaticGainControlModeForStage1,
				paEdfaPlusOutputPowerLimitInAutomaticGainControlModeForStage2,
				paEdfaPlusAutomaticPowerReductionForStage1Threshold,
				paEdfaPlusAutomaticPowerReductionForStage2Threshold,
				paEdfaPlusOpticalInputPowerFailureAlarmForStage1Threshold,
				paEdfaPlusOpticalInputPowerFailureAlarmForStage2Threshold,
				paEdfaPlusOpticalHighInputPowerAlarmForStage1Threshold,
				paEdfaPlusOpticalHighInputPowerAlarmForStage2Threshold,
				paEdfaPlusOpticalLowInputPowerAlarmForStage1Threshold,
				paEdfaPlusOpticalLowInputPowerAlarmForStage2Threshold,
				paEdfaPlusOpticalHighInputPowerWarningForStage1Threshold,
				paEdfaPlusOpticalHighInputPowerWarningForStage2Threshold,
				paEdfaPlusOpticalLowInputPowerWarningForStage1Threshold,
				paEdfaPlusOpticalLowInputPowerWarningForStage2Threshold,
				paEdfaPlusOpticalOutputPowerFailureAlarmForStage1Threshold,
				paEdfaPlusOpticalOutputPowerFailureAlarmForStage2Threshold,
				paEdfaPlusOpticalHighOutputPowerAlarmForStage1Threshold,
				paEdfaPlusOpticalHighOutputPowerAlarmForStage2Threshold,
				paEdfaPlusOpticalLowOutputPowerAlarmForStage1Threshold,
				paEdfaPlusOpticalLowOutputPowerAlarmForStage2Threshold,
				paEdfaPlusOpticalHighOutputPowerWarningForStage1Threshold,
				paEdfaPlusOpticalHighOutputPowerWarningForStage2Threshold,
				paEdfaPlusOpticalLowOutputPowerWarningForStage1Threshold,
				paEdfaPlusOpticalLowOutputPowerWarningForStage2Threshold,
				paEdfaPlusModuleHighTemperatureAlarmThreshold,
				paEdfaPlusModuleLowTemperatureAlarmThreshold,
				paEdfaPlusModuleHighTemperatureWarningThreshold,
				paEdfaPlusModuleLowTemperatureWarningThreshold,
				paEdfaPlusPump1HighTemperatureAlarmThreshold,
				paEdfaPlusPump2HighTemperatureAlarmThreshold,
				paEdfaPlusPump1LowTemperatureAlarmThreshold,
				paEdfaPlusPump2LowTemperatureAlarmThreshold,
				paEdfaPlusPump1HighTemperatureWarningThreshold,
				paEdfaPlusPump2HighTemperatureWarningThreshold,
				paEdfaPlusPump1LowTemperatureWarningThreshold,
				paEdfaPlusPump2LowTemperatureWarningThreshold,
				paEdfaPlusPump1HighOperatingCurrentAlarmThreshold,
				paEdfaPlusPump2HighOperatingCurrentAlarmThreshold,
				paEdfaPlusPump1LowOperatingCurrentAlarmThreshold,
				paEdfaPlusPump2LowOperatingCurrentAlarmThreshold,
				paEdfaPlusPump1HighOperatingCurrentWarningThreshold,
				paEdfaPlusPump2HighOperatingCurrentWarningThreshold,
				paEdfaPlusPump1LowOperatingCurrentWarningThreshold,
				paEdfaPlusPump2LowOperatingCurrentWarningThreshold,
				paEdfaPlusPump1HighThermoElectricCoolerCurrentAlarmThreshold,
				paEdfaPlusPump2HighThermoElectricCoolerCurrentAlarmThreshold,
				paEdfaPlusPump1LowThermoElectricCoolerCurrentAlarmThreshold,
				paEdfaPlusPump2LowThermoElectricCoolerCurrentAlarmThreshold,
				paEdfaPlusPump1HighThermoElectricCoolerCurrentWarningThreshold,
				paEdfaPlusPump2HighThermoElectricCoolerCurrentWarningThreshold,
				paEdfaPlusPump1LowThermoElectricCoolerCurrentWarningThreshold,
				paEdfaPlusPump2LowThermoElectricCoolerCurrentWarningThreshold,
				paEdfaPlusVariableOpticalAttenuatorHighInputPowerAlarmThreshold,
				paEdfaPlusVariableOpticalAttenuatorLowInputPowerAlarmThreshold,
				paEdfaPlusVariableOpticalAttenuatorHighInputPowerWarningThreshold,
				paEdfaPlusVariableOpticalAttenuatorLowInputPowerWarningThreshold,
				paEdfaPlusOpticalInputPowerFailureAlarmForStage1Inhibit,
				paEdfaPlusOpticalInputPowerFailureAlarmForStage2Inhibit,
				paEdfaPlusOpticalHighInputPowerAlarmForStage1Inhibit,
				paEdfaPlusOpticalHighInputPowerAlarmForStage2Inhibit,
				paEdfaPlusOpticalLowInputPowerAlarmForStage1Inhibit,
				paEdfaPlusOpticalLowInputPowerAlarmForStage2Inhibit,
				paEdfaPlusOpticalHighInputPowerWarningForStage1Inhibit,
				paEdfaPlusOpticalHighInputPowerWarningForStage2Inhibit,
				paEdfaPlusOpticalLowInputPowerWarningForStage1Inhibit,
				paEdfaPlusOpticalLowInputPowerWarningForStage2Inhibit,
				paEdfaPlusOpticalOutputPowerFailureAlarmForStage1Inhibit,
				paEdfaPlusOpticalOutputPowerFailureAlarmForStage2Inhibit,
				paEdfaPlusOpticalHighOutputPowerAlarmForStage1Inhibit,
				paEdfaPlusOpticalHighOutputPowerAlarmForStage2Inhibit,
				paEdfaPlusOpticalLowOutputPowerAlarmForStage1Inhibit,
				paEdfaPlusOpticalLowOutputPowerAlarmForStage2Inhibit,
				paEdfaPlusOpticalHighOutputPowerWarningForStage1Inhibit,
				paEdfaPlusOpticalHighOutputPowerWarningForStage2Inhibit,
				paEdfaPlusOpticalLowOutputPowerWarningForStage1Inhibit,
				paEdfaPlusOpticalLowOutputPowerWarningForStage2Inhibit,
				paEdfaPlusModuleHighTemperatureAlarmInhibit,
				paEdfaPlusModuleLowTemperatureAlarmInhibit,
				paEdfaPlusModuleHighTemperatureWarningInhibit,
				paEdfaPlusModuleLowTemperatureWarningInhibit,
				paEdfaPlusPump1HighTemperatureAlarmInhibit,
				paEdfaPlusPump2HighTemperatureAlarmInhibit,
				paEdfaPlusPump1LowTemperatureAlarmInhibit,
				paEdfaPlusPump2LowTemperatureAlarmInhibit,
				paEdfaPlusPump1HighTemperatureWarningInhibit,
				paEdfaPlusPump2HighTemperatureWarningInhibit,
				paEdfaPlusPump1LowTemperatureWarningInhibit,
				paEdfaPlusPump2LowTemperatureWarningInhibit,
				paEdfaPlusPump1HighOperatingCurrentAlarmInhibit,
				paEdfaPlusPump2HighOperatingCurrentAlarmInhibit,
				paEdfaPlusPump1LowOperatingCurrentAlarmInhibit,
				paEdfaPlusPump2LowOperatingCurrentAlarmInhibit,
				paEdfaPlusPump1HighOperatingCurrentWarningInhibit,
				paEdfaPlusPump2HighOperatingCurrentWarningInhibit,
				paEdfaPlusPump1LowOperatingCurrentWarningInhibit,
				paEdfaPlusPump2LowOperatingCurrentWarningInhibit,
				paEdfaPlusPump1HighThermoElectricCoolerCurrentAlarmInhibit,
				paEdfaPlusPump2HighThermoElectricCoolerCurrentAlarmInhibit,
				paEdfaPlusPump1LowThermoElectricCoolerCurrentAlarmInhibit,
				paEdfaPlusPump2LowThermoElectricCoolerCurrentAlarmInhibit,
				paEdfaPlusPump1HighThermoElectricCoolerCurrentWarningInhibit,
				paEdfaPlusPump2HighThermoElectricCoolerCurrentWarningInhibit,
				paEdfaPlusPump1LowThermoElectricCoolerCurrentWarningInhibit,
				paEdfaPlusPump2LowThermoElectricCoolerCurrentWarningInhibit,
				paEdfaPlusVariableOpticalAttenuatorHighInputPowerAlarmInhibit,
				paEdfaPlusVariableOpticalAttenuatorLowInputPowerAlarmInhibit,
				paEdfaPlusVariableOpticalAttenuatorHighInputPowerWarningInhibit,
				paEdfaPlusVariableOpticalAttenuatorLowInputPowerWarningInhibit,
				paEdfaPlusInputOutOfRangeAlarmInhibit,
				paEdfaPlusOutputOutOfRangeAlarmInhibit,
				paEdfaPlusPumpBiasCurrentAlarmInhibit,
				paEdfaPlusPump1CoolingTemperatureAlarmInhibit,
				paEdfaPlusPump2CoolingTemperatureAlarmInhibit,
				paEdfaPlusPump1LaserPowerAlarmInhibit,
				paEdfaPlusPump2LaserPowerAlarmInhibit,
				paEdfaPlusOpticalInputPowerFailureAlarmForStage1Severity,
				paEdfaPlusOpticalInputPowerFailureAlarmForStage2Severity,
				paEdfaPlusOpticalHighInputPowerAlarmForStage1Severity,
				paEdfaPlusOpticalHighInputPowerAlarmForStage2Severity,
				paEdfaPlusOpticalLowInputPowerAlarmForStage1Severity,
				paEdfaPlusOpticalLowInputPowerAlarmForStage2Severity,
				paEdfaPlusOpticalHighInputPowerWarningForStage1Severity,
				paEdfaPlusOpticalHighInputPowerWarningForStage2Severity,
				paEdfaPlusOpticalLowInputPowerWarningForStage1Severity,
				paEdfaPlusOpticalLowInputPowerWarningForStage2Severity,
				paEdfaPlusOpticalOutputPowerFailureAlarmForStage1Severity,
				paEdfaPlusOpticalOutputPowerFailureAlarmForStage2Severity,
				paEdfaPlusOpticalHighOutputPowerAlarmForStage1Severity,
				paEdfaPlusOpticalHighOutputPowerAlarmForStage2Severity,
				paEdfaPlusOpticalLowOutputPowerAlarmForStage1Severity,
				paEdfaPlusOpticalLowOutputPowerAlarmForStage2Severity,
				paEdfaPlusOpticalHighOutputPowerWarningForStage1Severity,
				paEdfaPlusOpticalHighOutputPowerWarningForStage2Severity,
				paEdfaPlusOpticalLowOutputPowerWarningForStage1Severity,
				paEdfaPlusOpticalLowOutputPowerWarningForStage2Severity,
				paEdfaPlusModuleHighTemperatureAlarmSeverity,
				paEdfaPlusModuleLowTemperatureAlarmSeverity,
				paEdfaPlusModuleHighTemperatureWarningSeverity,
				paEdfaPlusModuleLowTemperatureWarningSeverity,
				paEdfaPlusPump1HighTemperatureAlarmSeverity,
				paEdfaPlusPump2HighTemperatureAlarmSeverity,
				paEdfaPlusPump1LowTemperatureAlarmSeverity,
				paEdfaPlusPump2LowTemperatureAlarmSeverity,
				paEdfaPlusPump1HighTemperatureWarningSeverity,
				paEdfaPlusPump2HighTemperatureWarningSeverity,
				paEdfaPlusPump1LowTemperatureWarningSeverity,
				paEdfaPlusPump2LowTemperatureWarningSeverity,
				paEdfaPlusPump1HighOperatingCurrentAlarmSeverity,
				paEdfaPlusPump2HighOperatingCurrentAlarmSeverity,
				paEdfaPlusPump1LowOperatingCurrentAlarmSeverity,
				paEdfaPlusPump2LowOperatingCurrentAlarmSeverity,
				paEdfaPlusPump1HighOperatingCurrentWarningSeverity,
				paEdfaPlusPump2HighOperatingCurrentWarningSeverity,
				paEdfaPlusPump1LowOperatingCurrentWarningSeverity,
				paEdfaPlusPump2LowOperatingCurrentWarningSeverity,
				paEdfaPlusPump1HighThermoElectricCoolerCurrentAlarmSeverity,
				paEdfaPlusPump2HighThermoElectricCoolerCurrentAlarmSeverity,
				paEdfaPlusPump1LowThermoElectricCoolerCurrentAlarmSeverity,
				paEdfaPlusPump2LowThermoElectricCoolerCurrentAlarmSeverity,
				paEdfaPlusPump1HighThermoElectricCoolerCurrentWarningSeverity,
				paEdfaPlusPump2HighThermoElectricCoolerCurrentWarningSeverity,
				paEdfaPlusPump1LowThermoElectricCoolerCurrentWarningSeverity,
				paEdfaPlusPump2LowThermoElectricCoolerCurrentWarningSeverity,
				paEdfaPlusVariableOpticalAttenuatorHighInputPowerAlarmSeverity,
				paEdfaPlusVariableOpticalAttenuatorLowInputPowerAlarmSeverity,
				paEdfaPlusVariableOpticalAttenuatorHighInputPowerWarningSeverity,
				paEdfaPlusVariableOpticalAttenuatorLowInputPowerWarningSeverity,
				paEdfaPlusInputOutOfRangeAlarmSeverity,
				paEdfaPlusOutputOutOfRangeAlarmSeverity,
				paEdfaPlusPumpBiasCurrentAlarmSeverity,
				paEdfaPlusPump1CoolingTemperatureAlarmSeverity,
				paEdfaPlusPump2CoolingTemperatureAlarmSeverity,
				paEdfaPlusPump1LaserPowerAlarmSeverity,
				paEdfaPlusPump2LaserPowerAlarmSeverity,
				paEdfaPlusCardSoftwareUpgrade,
				paEdfaPlusMidInOutOfRangeAlarmInhibit,
				paEdfaPlusMidOutOutOfRangeAlarmInhibit,
				paEdfaPlusMidInOutOfRangeAlarmSeverity,
				paEdfaPlusMidOutOutOfRangeAlarmSeverity,
				paEdfaPlusConfigurationTableRowStatus,
				paEdfaPlusOpticalInputPowerFailureAlarmForStage1,
				paEdfaPlusOpticalInputPowerFailureAlarmForStage2,
				paEdfaPlusOpticalHighInputPowerAlarmForStage1,
				paEdfaPlusOpticalHighInputPowerAlarmForStage2,
				paEdfaPlusOpticalLowInputPowerAlarmForStage1,
				paEdfaPlusOpticalLowInputPowerAlarmForStage2,
				paEdfaPlusOpticalHighInputPowerWarningForStage1,
				paEdfaPlusOpticalHighInputPowerWarningForStage2,
				paEdfaPlusOpticalLowInputPowerWarningForStage1,
				paEdfaPlusOpticalLowInputPowerWarningForStage2,
				paEdfaPlusOpticalOutputPowerFailureAlarmForStage1,
				paEdfaPlusOpticalOutputPowerFailureAlarmForStage2,
				paEdfaPlusOpticalHighOutputPowerAlarmForStage1,
				paEdfaPlusOpticalHighOutputPowerAlarmForStage2,
				paEdfaPlusOpticalLowOutputPowerAlarmForStage1,
				paEdfaPlusOpticalLowOutputPowerAlarmForStage2,
				paEdfaPlusOpticalHighOutputPowerWarningForStage1,
				paEdfaPlusOpticalHighOutputPowerWarningForStage2,
				paEdfaPlusOpticalLowOutputPowerWarningForStage1,
				paEdfaPlusOpticalLowOutputPowerWarningForStage2,
				paEdfaPlusModuleHighTemperatureAlarm,
				paEdfaPlusModuleLowTemperatureAlarm,
				paEdfaPlusModuleHighTemperatureWarning,
				paEdfaPlusModuleLowTemperatureWarning,
				paEdfaPlusPump1HighTemperatureAlarm,
				paEdfaPlusPump2HighTemperatureAlarm,
				paEdfaPlusPump1LowTemperatureAlarm,
				paEdfaPlusPump2LowTemperatureAlarm,
				paEdfaPlusPump1HighTemperatureWarning,
				paEdfaPlusPump2HighTemperatureWarning,
				paEdfaPlusPump1LowTemperatureWarning,
				paEdfaPlusPump2LowTemperatureWarning,
				paEdfaPlusPump1HighOperatingCurrentAlarm,
				paEdfaPlusPump2HighOperatingCurrentAlarm,
				paEdfaPlusPump1LowOperatingCurrentAlarm,
				paEdfaPlusPump2LowOperatingCurrentAlarm,
				paEdfaPlusPump1HighOperatingCurrentWarning,
				paEdfaPlusPump2HighOperatingCurrentWarning,
				paEdfaPlusPump1LowOperatingCurrentWarning,
				paEdfaPlusPump2LowOperatingCurrentWarning,
				paEdfaPlusPump1HighThermoElectricCoolerCurrentAlarm,
				paEdfaPlusPump2HighThermoElectricCoolerCurrentAlarm,
				paEdfaPlusPump1LowThermoElectricCoolerCurrentAlarm,
				paEdfaPlusPump2LowThermoElectricCoolerCurrentAlarm,
				paEdfaPlusPump1HighThermoElectricCoolerCurrentWarning,
				paEdfaPlusPump2HighThermoElectricCoolerCurrentWarning,
				paEdfaPlusPump1LowThermoElectricCoolerCurrentWarning,
				paEdfaPlusPump2LowThermoElectricCoolerCurrentWarning,
				paEdfaPlusVariableOpticalAttenuatorHighInputPowerAlarm,
				paEdfaPlusVariableOpticalAttenuatorLowInputPowerAlarm,
				paEdfaPlusVariableOpticalAttenuatorHighInputPowerWarning,
				paEdfaPlusVariableOpticalAttenuatorLowInputPowerWarning,
				paEdfaPlusInputOutOfRangeAlarm,
				paEdfaPlusOutputOutOfRangeAlarm,
				paEdfaPlusMidInOutOfRangeAlarm,
				paEdfaPlusMidOutOutOfRangeAlarm,			
				paEdfaPlusPumpBiasCurrentAlarm,
				paEdfaPlusPump1CoolingTemperatureAlarm,
				paEdfaPlusPump2CoolingTemperatureAlarm,
				paEdfaPlusPump1LaserPowerAlarm,
				paEdfaPlusPump2LaserPowerAlarm,
				paEdfaPlusAlarmQueryTableRowStatus,
				paEdfaPlusModuleTemperature,
				paEdfaPlusInputPowerForStage1,
				paEdfaPlusInputPowerForStage2,
				paEdfaPlusOutputPowerForStage1,
				paEdfaPlusOutputPowerForStage2,
				paEdfaPlusAmplifiedSpontaneousEmmissionPowerForStage1,
				paEdfaPlusAmplifiedSpontaneousEmmissionPowerForStage2,
				paEdfaPlusSignalGainForStage1,
				paEdfaPlusSignalGainForStage2,
				paEdfaPlusSignalOutputPowerForStage1,
				paEdfaPlusSignalOutputPowerForStage2,
				paEdfaPlusPump1LaserPower,
				paEdfaPlusPump2LaserPower,
				paEdfaPlusPump1Temperature,
				paEdfaPlusPump2Temperature,
				paEdfaPlusPump1OperatingCurrent,
				paEdfaPlusPump2OperatingCurrent,
				paEdfaPlusPump1ThermoElectricCoolerCurrent,
				paEdfaPlusPump2ThermoElectricCoolerCurrent,
				paEdfaPlusPump1CoolingTemperature,
				paEdfaPlusPump2CoolingTemperature,
				paEdfaPlusVariableOpticalAttenuatorInputPower,
				paEdfaPlusVariableOpticalAttenuatorOutputPower,
				paEdfaPlusVariableOpticalAttenuatorActualAttenuation,
				paEdfaPlusPerformanceTableRowStatus
													
			}
		STATUS	current

		DESCRIPTION
		"A collection of objects from RFC 1213 made current by this MIB module."

		::= { utlrnd 2 }
	
END

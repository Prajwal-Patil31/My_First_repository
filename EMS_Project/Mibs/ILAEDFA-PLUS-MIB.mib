--*****************************************************************************
--				UTL ILA EDFA PLUS MIB
--*****************************************************************************

ILAEDFA-PLUS-MIB DEFINITIONS ::= BEGIN
 
		IMPORTS
		RowStatus				FROM STANDARD-MIB

		DisplayString				FROM RFC1213-MIB       

		OBJECT-IDENTITY, 
		NOTIFICATION-TYPE, 
		MODULE-IDENTITY, 
		Integer32, 
		Unsigned32, 
		IpAddress, 
		TimeTicks				FROM SNMPv2-SMI

		OBJECT-TYPE				FROM RFC-1212

		MODULE-COMPLIANCE, 
		OBJECT-GROUP, 
		NOTIFICATION-GROUP			FROM SNMPv2-CONF
		
		node, 
		rack, 
		subRack, 
		slot 					FROM SCC-MIB

		enterprises 				FROM RFC1155-SMI		

	;

	utl   	MODULE-IDENTITY
		LAST-UPDATED    	"1807130630Z"
		ORGANIZATION    	"United Telecoms Limited, Bangalore-560048."
		CONTACT-INFO    	"Website: http://www.utlindia.com."                                           
		DESCRIPTION     	"MIB module for UTL DWDM."
		REVISION 	    	"1807130630Z"

		DESCRIPTION    	 	"MIB module for ILA EDFA Plus Card."

		::= { enterprises 18036 }

	utlrnd  OBJECT-IDENTITY
		STATUS  current

		DESCRIPTION "UTL R and D."

		::= { utl 1 }

	dwdm 				OBJECT IDENTIFIER	::=   { utlrnd 1 }
	indus 				OBJECT IDENTIFIER	::=   { dwdm 1 }
	ilaEdfaPlus 			OBJECT IDENTIFIER 	::=   { indus 151 }

	ilaEdfaPlusCardGeneralDetails 	OBJECT IDENTIFIER 	::=   { ilaEdfaPlus 1 }
	ilaEdfaPlusConfiguration 	OBJECT IDENTIFIER 	::=   { ilaEdfaPlus 2 }
	ilaEdfaPlusAlarm 		OBJECT IDENTIFIER 	::=   { ilaEdfaPlus 3 }
	ilaEdfaPlusPerformance 		OBJECT IDENTIFIER 	::=   { ilaEdfaPlus 4 }	

	ilaEdfaPlusAlarmQuery 		OBJECT IDENTIFIER 	::=   { ilaEdfaPlusAlarm 1 }
	ilaEdfaPlusAlarmNotification 	OBJECT IDENTIFIER 	::=   { ilaEdfaPlusAlarm 2 }

--*****************************************************************************
--			ILA EDFA PLUS CARD GENERAL DETAILS
--*****************************************************************************

	ilaEdfaPlusCardGeneralDetailsTable OBJECT-TYPE
		SYNTAX  	SEQUENCE OF IlaEdfaPlusCardGeneralDetailsEntry
		MAX-ACCESS	not-accessible
		STATUS		current

		DESCRIPTION
		 " we can get ILA EDFA PLUS card general details "

		::= { ilaEdfaPlusCardGeneralDetails 1 }

	ilaEdfaPlusCardGeneralDetailsEntry OBJECT-TYPE
		SYNTAX  	IlaEdfaPlusCardGeneralDetailsEntry
		MAX-ACCESS  	not-accessible
		STATUS  	current

		DESCRIPTION 
		 "Enter node rack, subrack, slot and ilaEdfaPlusInterface numbers"

		INDEX   { node, rack, subRack, slot, ilaEdfaPlusInterface }

		::= { ilaEdfaPlusCardGeneralDetailsTable 1 }

	IlaEdfaPlusCardGeneralDetailsEntry ::=
		SEQUENCE {
				ilaEdfaPlusInterface					INTEGER,
				ilaEdfaPlusEepromCardId					INTEGER,
				ilaEdfaPlusEepromCardName				DisplayString,
				ilaEdfaPlusEepromPartCode				DisplayString,
				ilaEdfaPlusEepromCardSerialNumber			DisplayString,
				ilaEdfaPlusEepromHardwareExternalReleaseVersion		DisplayString,
				ilaEdfaPlusSoftwareExternalReleaseVersion		DisplayString,
				ilaEdfaPlusEepromHardwareInternalReleaseVersion		DisplayString,
				ilaEdfaPlusSoftwareInternalReleaseVersion		DisplayString,
				ilaEdfaPlusEepromCardUidNumber				DisplayString,
				ilaEdfaPlusEepromCardEUI48Number			DisplayString,
				ilaEdfaPlusEepromCardEUI64Number			DisplayString,
				ilaEdfaPlusCardRootFileSystemVersion			DisplayString,
				ilaEdfaPlusInstallationDate				DisplayString,
				ilaEdfaPlusCommissionDate				DisplayString,
				ilaEdfaPlusCardRunningTime				DisplayString,
				ilaEdfaPlusCardRestartCount				INTEGER,
				ilaEdfaPlusModuleVendorName				DisplayString,
				ilaEdfaPlusModuleSerialNumber				DisplayString,
				ilaEdfaPlusNumberOfChannelsSupported			INTEGER,
				ilaEdfaPlusNumberOfPumpSupported			INTEGER,
				ilaEdfaPlusMaxGainSupported				DisplayString,
				ilaEdfaPlusSaturationOutputPowerSupported		DisplayString,
				ilaEdfaPlusMidStageAccessSupport			INTEGER,
				ilaEdfaPlusDirection					INTEGER,
				ilaEdfaPlusStage2VoaPresenceStatus			INTEGER,
				ilaEdfaPlusModuleType					INTEGER,
				ilaEdfaPlusCardGeneralDetailsTableRowStatus		RowStatus
			}

	ilaEdfaPlusInterface 	OBJECT-TYPE
		SYNTAX  	INTEGER
		MAX-ACCESS  not-accessible
		STATUS  	current
		DESCRIPTION	
			"ila edfa plus interface number should be 0 always"

		::= { ilaEdfaPlusCardGeneralDetailsEntry 1 }

	ilaEdfaPlusEepromCardId OBJECT-TYPE
		SYNTAX  	INTEGER
		MAX-ACCESS  	read-only
		STATUS  	current

		DESCRIPTION
		 " Tells the card ID of the ILAEDFA-PLUS card, present in the EEPROM "

		::= { ilaEdfaPlusCardGeneralDetailsEntry 2 }

	ilaEdfaPlusEepromCardName OBJECT-TYPE
		SYNTAX  	DisplayString (SIZE (0..255))
		MAX-ACCESS  	read-only
		STATUS		current

		DESCRIPTION
		 " Tells the card name of the ILAEDFA-PLUS card, present in the EEPROM "

		::= { ilaEdfaPlusCardGeneralDetailsEntry 3 }

	ilaEdfaPlusEepromPartCode OBJECT-TYPE
		SYNTAX  	DisplayString (SIZE (0..255))
		MAX-ACCESS  	read-only
		STATUS		current

		DESCRIPTION
		 " Tells the part code of the ILAEDFA-PLUS card, present in the EEPROM "

		::= { ilaEdfaPlusCardGeneralDetailsEntry 4 }

	ilaEdfaPlusEepromCardSerialNumber OBJECT-TYPE
		SYNTAX  	DisplayString (SIZE (0..255))
		MAX-ACCESS  	read-write
		STATUS		current

		DESCRIPTION
		 " This property get / set the information about ILAEDFA-PLUS 
		 Card's Serial Number.
		-----------------------------
		Values:
		eg: 123456
		-----------------------------"

		::= { ilaEdfaPlusCardGeneralDetailsEntry 5 }

	ilaEdfaPlusEepromHardwareExternalReleaseVersion OBJECT-TYPE
		SYNTAX  	DisplayString (SIZE (0..255))
		MAX-ACCESS  	read-only
		STATUS		current

		DESCRIPTION
		 " To get the Card's Hardware External Release Version. This detail 
		 will be displayed to the customer. This version will increment 
		 only if there are significant architectural changes in the product.
		-----------------------------
		Value:
		eg: 0.1
		-----------------------------"

		::= { ilaEdfaPlusCardGeneralDetailsEntry 6 }

	ilaEdfaPlusSoftwareExternalReleaseVersion OBJECT-TYPE
		SYNTAX  	DisplayString (SIZE (0..255))
		MAX-ACCESS  	read-only
		STATUS		current

		DESCRIPTION
		 " To get the Card's Software External Release Version.  This detail 
		 will be displayed to the customer. This version will increment 
		 only if there are significant architectural changes in the product.
		-----------------------------
		Value:
		eg: 0.1
		-----------------------------"

		::= { ilaEdfaPlusCardGeneralDetailsEntry 7 }

	ilaEdfaPlusEepromHardwareInternalReleaseVersion OBJECT-TYPE
		SYNTAX  	DisplayString (SIZE (0..255))
		MAX-ACCESS  	read-only
		STATUS		current

		DESCRIPTION
		 " To get the Card's Hardware Internal Release Version. This detail 
		 is used for development purposes only. It differs from the external 
		 hardware version.
		-----------------------------
		Value:
		eg: 4.1
		-----------------------------"

		::= { ilaEdfaPlusCardGeneralDetailsEntry 8 }

	ilaEdfaPlusSoftwareInternalReleaseVersion OBJECT-TYPE
		SYNTAX  	DisplayString (SIZE (0..255))
		MAX-ACCESS  	read-only
		STATUS		current

		DESCRIPTION
		 " To get the Card's Software Internal Release Version.  This detail 
		 is used for development purposes only. It differs from the external 
		 software version.
		-----------------------------
		Value:
		eg: 5.1
		-----------------------------"

		::= { ilaEdfaPlusCardGeneralDetailsEntry 9 }

	ilaEdfaPlusEepromCardUidNumber OBJECT-TYPE
		SYNTAX  	DisplayString (SIZE (0..255))
		MAX-ACCESS  	read-only
		STATUS		current

		DESCRIPTION
		 " Tells the Card Unique Identifier It is a 4 byte address used to 
		 uniquely identify a card.
		------------------------------
		Value:
	      	eg: 12345678
		-----------------------------"

		::= { ilaEdfaPlusCardGeneralDetailsEntry 10 }

	ilaEdfaPlusEepromCardEUI48Number OBJECT-TYPE
		SYNTAX  	DisplayString (SIZE (0..255))
		MAX-ACCESS  	read-only
		STATUS		current

		DESCRIPTION
		 " Tells the Card EUI-48 Number. It’s a 6 byte address used to 
		 uniquely identify a card.
		-----------------------------
		Value:
	      	eg: 0004A3123456
		-----------------------------"

		::= { ilaEdfaPlusCardGeneralDetailsEntry 11 }

	ilaEdfaPlusEepromCardEUI64Number OBJECT-TYPE
		SYNTAX  	DisplayString (SIZE (0..255))
		MAX-ACCESS  	read-only
		STATUS		current

		DESCRIPTION
		 " Tells the Card EUI-64 Number. It’s a 8 byte address
		used to uniquely identify a card.
		-----------------------------
		Value:
	      	eg: 0004A31234567890
		-----------------------------"

		::= { ilaEdfaPlusCardGeneralDetailsEntry 12 }
		
        ilaEdfaPlusCardRootFileSystemVersion OBJECT-TYPE		 
		SYNTAX  DisplayString
		MAX-ACCESS  read-only
		STATUS current
		DESCRIPTION
			"Tells the Card's Root File System Version
			-----------------------------
			ilaEdfaPlusInterface: 0
			-----------------------------
			Value:
		      	eg: 8
			-----------------------------"
		::= { ilaEdfaPlusCardGeneralDetailsEntry 13 }

	ilaEdfaPlusInstallationDate OBJECT-TYPE
		SYNTAX  	DisplayString (SIZE (0..255))
		MAX-ACCESS  	read-write
		STATUS		current

		DESCRIPTION
		 " To get the card's installation date in dd/mm/yyyy format.
		-----------------------------
		Value:
	      	eg: 12/03/2016
		-----------------------------"

		::= { ilaEdfaPlusCardGeneralDetailsEntry 21 }

	ilaEdfaPlusCommissionDate OBJECT-TYPE
		SYNTAX  	DisplayString (SIZE (0..255))
		MAX-ACCESS  	read-write
		STATUS		current

		DESCRIPTION
		 " To get the card's commission date in  dd/mm/yyyy format.
		-----------------------------
		Value:
	      	eg: 20/03/2016
		-----------------------------"

		::= { ilaEdfaPlusCardGeneralDetailsEntry 22 }

	ilaEdfaPlusCardRunningTime OBJECT-TYPE
		SYNTAX  	DisplayString (SIZE (0..255))
		MAX-ACCESS  	read-only
		STATUS		current

		DESCRIPTION
		 " To get the duration of time for which the card is operational/running.
		-----------------------------
		Values:
	      	eg: 3d 2h 1m
		-----------------------------"

		::= { ilaEdfaPlusCardGeneralDetailsEntry 23 }

	ilaEdfaPlusCardRestartCount OBJECT-TYPE
		SYNTAX  	INTEGER
		MAX-ACCESS  	read-only
		STATUS		current

		DESCRIPTION
		 " To get the number of times the card has been soft reset. This value 
		 will get reset to 0 on factory reset.
		-----------------------------
		Values:
	      	eg: 10
		-----------------------------"

		::= { ilaEdfaPlusCardGeneralDetailsEntry 24 }

	ilaEdfaPlusModuleVendorName OBJECT-TYPE
		SYNTAX  	DisplayString (SIZE (0..255))
		MAX-ACCESS  	read-only
		STATUS		current

		DESCRIPTION
		 " to get ILA EDFA PLUS card module vendor name.
		-----------------------------
		Values:
	      	eg: ACCELINK
		-----------------------------"

		::= { ilaEdfaPlusCardGeneralDetailsEntry 31 }

	ilaEdfaPlusModuleSerialNumber OBJECT-TYPE
		SYNTAX  	DisplayString (SIZE (0..255))
		MAX-ACCESS  	read-only
		STATUS		current

		DESCRIPTION
		 " to get ILA EDFA PLUS card module serial number.
		-----------------------------
		Values:
	      	eg: 12345
		-----------------------------"

		::= { ilaEdfaPlusCardGeneralDetailsEntry 32 }

	ilaEdfaPlusNumberOfChannelsSupported OBJECT-TYPE
		SYNTAX  	INTEGER
		MAX-ACCESS  	read-only
		STATUS  	current

		DESCRIPTION
		 " to get ILA EDFA PLUS card supports how many number of channels.
		-----------------------------
		Values:
	      	eg: 30
		-----------------------------"

		::= { ilaEdfaPlusCardGeneralDetailsEntry 33 }

	ilaEdfaPlusNumberOfPumpSupported OBJECT-TYPE
		SYNTAX  	INTEGER
		MAX-ACCESS  	read-only
		STATUS  	current

		DESCRIPTION
		 " to get ILA EDFA PLUS card supports how many number of pumps.
		-----------------------------
		Values:
	      	eg: 2
		-----------------------------"

		::= { ilaEdfaPlusCardGeneralDetailsEntry 34 }

	ilaEdfaPlusMaxGainSupported OBJECT-TYPE
		SYNTAX  	DisplayString (SIZE (0..255))
		MAX-ACCESS  	read-only
		STATUS		current

		DESCRIPTION
		 " to get ILA EDFA PLUS card supports maximum gain supported.
		-----------------------------
		Values:
	      	eg: 25.0
		-----------------------------"

		::= { ilaEdfaPlusCardGeneralDetailsEntry 35 }

	ilaEdfaPlusSaturationOutputPowerSupported OBJECT-TYPE
		SYNTAX  	DisplayString (SIZE (0..255))
		MAX-ACCESS  	read-only
		STATUS		current

		DESCRIPTION
		 " to get ILA EDFA PLUS card supports saturation power.
		-----------------------------
		Values:
	      	eg: 19.0
		-----------------------------"

		::= { ilaEdfaPlusCardGeneralDetailsEntry 36 }

	ilaEdfaPlusMidStageAccessSupport OBJECT-TYPE
		SYNTAX  	INTEGER
		MAX-ACCESS  	read-only
		STATUS  	current

		DESCRIPTION
		 " to get ILA EDFA PLUS card supoort status of mid stage access.
		-----------------------------
		Values:
	      	1 - MSA supported
		0 - MSA not supported
		-----------------------------"

		::= { ilaEdfaPlusCardGeneralDetailsEntry 37 }
		
	ilaEdfaPlusDirection	OBJECT-TYPE
		SYNTAX  	INTEGER
		MAX-ACCESS  read-only
		STATUS  	current
		DESCRIPTION	
		" to get ILA EDFA card Direction.
		-----------------------------
		Values:
		1 - Direction 1
		2 - Direction 2
		3 - Direction 3
		4 - Direction 4
		-----------------------------"
		::= { ilaEdfaPlusCardGeneralDetailsEntry 38 }

	ilaEdfaPlusStage2VoaPresenceStatus	OBJECT-TYPE
		SYNTAX  	INTEGER
		MAX-ACCESS  read-only
		STATUS  	current
		DESCRIPTION	" to get ILA EDFA PLUS inbuilt voa presence status.
		-----------------------------
		Values:
		1 - VOA present stage 2
		0 - VOA absent
		-----------------------------"
		::= { ilaEdfaPlusCardGeneralDetailsEntry 39 }

	ilaEdfaPlusModuleType OBJECT-TYPE
		SYNTAX  	INTEGER
		MAX-ACCESS  	read-only
		STATUS  	current

		DESCRIPTION
		 " to get ILA EDFA PLUS card type (in Km).
		-----------------------------
		Values:
	      	eg: 40, 60, 80, 100 
		-----------------------------"

		::= { ilaEdfaPlusCardGeneralDetailsEntry 40 }

	ilaEdfaPlusCardGeneralDetailsTableRowStatus OBJECT-TYPE
	      SYNTAX      RowStatus
	      MAX-ACCESS  read-write
	      STATUS      current
	      DESCRIPTION
		      "	This is MIB realted property,
			NOT to be considered as a card property"
	      ::= { ilaEdfaPlusCardGeneralDetailsEntry 41 }

--*****************************************************************************
--			ILA EDFA PLUS CONFIGURATION
--***************************************************************************** 

	ilaEdfaPlusConfigurationTable OBJECT-TYPE
		SYNTAX  	SEQUENCE OF IlaEdfaPlusConfigurationEntry
		MAX-ACCESS  	not-accessible
		STATUS  	current

		DESCRIPTION
		 " we can get ILA EDFA PLUS configuration details "

		::= { ilaEdfaPlusConfiguration 1 }
              
        ilaEdfaPlusConfigurationEntry OBJECT-TYPE
		SYNTAX  	IlaEdfaPlusConfigurationEntry
		MAX-ACCESS  	not-accessible
		STATUS  	current

		DESCRIPTION 
		 "Enter node rack, subrack, slot and ilaEdfaPlusInterface numbers"

		INDEX   { node, rack, subRack, slot, ilaEdfaPlusInterface }

		::= { ilaEdfaPlusConfigurationTable 1 }
	
	IlaEdfaPlusConfigurationEntry ::= 
		SEQUENCE {
				ilaEdfaPlusCardSoftReset	 							INTEGER,
				ilaEdfaPlusCardDefaultFactoryReset							INTEGER,
				ilaEdfaPlusAlarmMonitoringStatus	 						INTEGER,
				ilaEdfaPlusManageUnmanageStatus								INTEGER,
				ilaEdfaPlusSyncSystemTimeWithNtpServer				DisplayString,
				ilaEdfaPlusSyncRtcWithNtpServer						DisplayString,
				ilaEdfaPlusSyncRtcWithSystemTime					DisplayString,
				ilaEdfaPlusUpdateGivenTimeIntoSystem				DisplayString,
				ilaEdfaPlusUpdateGivenTimeIntoRtc					DisplayString,
				ilaEdfaPlusSystemTimeAndRtcTime						DisplayString,
				ilaEdfaPlusVariableOpticalAttenuatorReset						INTEGER,
				ilaEdfaPlusPump1LaserStatus	 							INTEGER,
				ilaEdfaPlusPump2LaserStatus	 							INTEGER,
				ilaEdfaPlusAutomaticPowerReductionStatusForStage1					INTEGER,
				ilaEdfaPlusAutomaticPowerReductionStatusForStage2					INTEGER,
				ilaEdfaPlusAutomaticLaserShutdownStatusForStage1					INTEGER,
				ilaEdfaPlusAutomaticLaserShutdownStatusForStage2					INTEGER,
				ilaEdfaPlusModuleOperatingModeForStage1							DisplayString,
				ilaEdfaPlusModuleOperatingModeForStage2							DisplayString,
				ilaEdfaPlusModuleGainInAutomaticGainControlModeForStage1				DisplayString,
				ilaEdfaPlusModuleGainInAutomaticGainControlModeForStage2				DisplayString,
				ilaEdfaPlusModuleOutputPowerInAutomaticPowerControlMode					DisplayString,
				ilaEdfaPlusPump1OperatingCurrentInAutomaticCurrentControlMode				DisplayString,
				ilaEdfaPlusPump2OperatingCurrentInAutomaticCurrentControlMode				DisplayString,
				ilaEdfaPlusGainTilt	 								DisplayString,
				ilaEdfaPlusVariableOpticalAttenuatorAttenuationForStage2					DisplayString,
				ilaEdfaPlusOutputPowerLimitFunctionStatusInAutomaticGainControlModeForStage1		INTEGER,
				ilaEdfaPlusOutputPowerLimitFunctionStatusInAutomaticGainControlModeForStage2		INTEGER,
				ilaEdfaPlusOutputPowerLimitInAutomaticGainControlModeForStage1				DisplayString,
				ilaEdfaPlusOutputPowerLimitInAutomaticGainControlModeForStage2				DisplayString,
				ilaEdfaPlusAutomaticPowerReductionForStage1Threshold					DisplayString,
				ilaEdfaPlusAutomaticPowerReductionForStage2Threshold					DisplayString,
				ilaEdfaPlusOpticalInputPowerFailureAlarmForStage1Threshold				DisplayString,
				ilaEdfaPlusOpticalInputPowerFailureAlarmForStage2Threshold				DisplayString,
				ilaEdfaPlusOpticalHighInputPowerAlarmForStage1Threshold					DisplayString,
				ilaEdfaPlusOpticalHighInputPowerAlarmForStage2Threshold					DisplayString,
				ilaEdfaPlusOpticalLowInputPowerAlarmForStage1Threshold					DisplayString,
				ilaEdfaPlusOpticalLowInputPowerAlarmForStage2Threshold					DisplayString,
				ilaEdfaPlusOpticalHighInputPowerWarningForStage1Threshold				DisplayString,
				ilaEdfaPlusOpticalHighInputPowerWarningForStage2Threshold				DisplayString,
				ilaEdfaPlusOpticalLowInputPowerWarningForStage1Threshold				DisplayString,
				ilaEdfaPlusOpticalLowInputPowerWarningForStage2Threshold				DisplayString,
				ilaEdfaPlusOpticalOutputPowerFailureAlarmForStage1Threshold				DisplayString,
				ilaEdfaPlusOpticalOutputPowerFailureAlarmForStage2Threshold				DisplayString,
				ilaEdfaPlusOpticalHighOutputPowerAlarmForStage1Threshold				DisplayString,
				ilaEdfaPlusOpticalHighOutputPowerAlarmForStage2Threshold				DisplayString,
				ilaEdfaPlusOpticalLowOutputPowerAlarmForStage1Threshold					DisplayString,
				ilaEdfaPlusOpticalLowOutputPowerAlarmForStage2Threshold					DisplayString,
				ilaEdfaPlusOpticalHighOutputPowerWarningForStage1Threshold				DisplayString,
				ilaEdfaPlusOpticalHighOutputPowerWarningForStage2Threshold				DisplayString,
				ilaEdfaPlusOpticalLowOutputPowerWarningForStage1Threshold				DisplayString,
				ilaEdfaPlusOpticalLowOutputPowerWarningForStage2Threshold				DisplayString,
				ilaEdfaPlusModuleHighTemperatureAlarmThreshold						DisplayString,
				ilaEdfaPlusModuleLowTemperatureAlarmThreshold						DisplayString,
				ilaEdfaPlusModuleHighTemperatureWarningThreshold					DisplayString,
				ilaEdfaPlusModuleLowTemperatureWarningThreshold						DisplayString,
				ilaEdfaPlusPump1HighTemperatureAlarmThreshold						DisplayString,
				ilaEdfaPlusPump2HighTemperatureAlarmThreshold						DisplayString,
				ilaEdfaPlusPump1LowTemperatureAlarmThreshold						DisplayString,
				ilaEdfaPlusPump2LowTemperatureAlarmThreshold						DisplayString,
				ilaEdfaPlusPump1HighTemperatureWarningThreshold						DisplayString,
				ilaEdfaPlusPump2HighTemperatureWarningThreshold						DisplayString,
				ilaEdfaPlusPump1LowTemperatureWarningThreshold						DisplayString,
				ilaEdfaPlusPump2LowTemperatureWarningThreshold						DisplayString,
				ilaEdfaPlusPump1HighOperatingCurrentAlarmThreshold					DisplayString,
				ilaEdfaPlusPump2HighOperatingCurrentAlarmThreshold					DisplayString,
				ilaEdfaPlusPump1LowOperatingCurrentAlarmThreshold					DisplayString,
				ilaEdfaPlusPump2LowOperatingCurrentAlarmThreshold					DisplayString,
				ilaEdfaPlusPump1HighOperatingCurrentWarningThreshold					DisplayString,
				ilaEdfaPlusPump2HighOperatingCurrentWarningThreshold					DisplayString,
				ilaEdfaPlusPump1LowOperatingCurrentWarningThreshold					DisplayString,
				ilaEdfaPlusPump2LowOperatingCurrentWarningThreshold					DisplayString,
				ilaEdfaPlusPump1HighThermoElectricCoolerCurrentAlarmThreshold				DisplayString,
				ilaEdfaPlusPump2HighThermoElectricCoolerCurrentAlarmThreshold				DisplayString,
				ilaEdfaPlusPump1LowThermoElectricCoolerCurrentAlarmThreshold				DisplayString,
				ilaEdfaPlusPump2LowThermoElectricCoolerCurrentAlarmThreshold				DisplayString,
				ilaEdfaPlusPump1HighThermoElectricCoolerCurrentWarningThreshold				DisplayString,
				ilaEdfaPlusPump2HighThermoElectricCoolerCurrentWarningThreshold				DisplayString,
				ilaEdfaPlusPump1LowThermoElectricCoolerCurrentWarningThreshold				DisplayString,
				ilaEdfaPlusPump2LowThermoElectricCoolerCurrentWarningThreshold				DisplayString,
				ilaEdfaPlusVariableOpticalAttenuatorHighInputPowerAlarmThreshold 			DisplayString,
				ilaEdfaPlusVariableOpticalAttenuatorLowInputPowerAlarmThreshold 			DisplayString,
				ilaEdfaPlusVariableOpticalAttenuatorHighInputPowerWarningThreshold 			DisplayString,
				ilaEdfaPlusVariableOpticalAttenuatorLowInputPowerWarningThreshold 			DisplayString,
				ilaEdfaPlusOpticalInputPowerFailureAlarmForStage1Inhibit 				INTEGER,
				ilaEdfaPlusOpticalInputPowerFailureAlarmForStage2Inhibit 				INTEGER,
				ilaEdfaPlusOpticalHighInputPowerAlarmForStage1Inhibit					INTEGER,
				ilaEdfaPlusOpticalHighInputPowerAlarmForStage2Inhibit					INTEGER,
				ilaEdfaPlusOpticalLowInputPowerAlarmForStage1Inhibit	 				INTEGER,
				ilaEdfaPlusOpticalLowInputPowerAlarmForStage2Inhibit	 				INTEGER,
				ilaEdfaPlusOpticalHighInputPowerWarningForStage1Inhibit	 				INTEGER,
				ilaEdfaPlusOpticalHighInputPowerWarningForStage2Inhibit	 				INTEGER,
				ilaEdfaPlusOpticalLowInputPowerWarningForStage1Inhibit 					INTEGER,
				ilaEdfaPlusOpticalLowInputPowerWarningForStage2Inhibit 					INTEGER,
				ilaEdfaPlusOpticalOutputPowerFailureAlarmForStage1Inhibit				INTEGER,
				ilaEdfaPlusOpticalOutputPowerFailureAlarmForStage2Inhibit				INTEGER,
				ilaEdfaPlusOpticalHighOutputPowerAlarmForStage1Inhibit					INTEGER,
				ilaEdfaPlusOpticalHighOutputPowerAlarmForStage2Inhibit					INTEGER,
				ilaEdfaPlusOpticalLowOutputPowerAlarmForStage1Inhibit					INTEGER,
				ilaEdfaPlusOpticalLowOutputPowerAlarmForStage2Inhibit					INTEGER,
				ilaEdfaPlusOpticalHighOutputPowerWarningForStage1Inhibit				INTEGER,
				ilaEdfaPlusOpticalHighOutputPowerWarningForStage2Inhibit				INTEGER,
				ilaEdfaPlusOpticalLowOutputPowerWarningForStage1Inhibit					INTEGER,
				ilaEdfaPlusOpticalLowOutputPowerWarningForStage2Inhibit					INTEGER,
				ilaEdfaPlusModuleHighTemperatureAlarmInhibit						INTEGER,
				ilaEdfaPlusModuleLowTemperatureAlarmInhibit						INTEGER,
				ilaEdfaPlusModuleHighTemperatureWarningInhibit						INTEGER,
				ilaEdfaPlusModuleLowTemperatureWarningInhibit						INTEGER,
				ilaEdfaPlusPump1HighTemperatureAlarmInhibit						INTEGER,
				ilaEdfaPlusPump2HighTemperatureAlarmInhibit						INTEGER,
				ilaEdfaPlusPump1LowTemperatureAlarmInhibit						INTEGER,
				ilaEdfaPlusPump2LowTemperatureAlarmInhibit						INTEGER,
				ilaEdfaPlusPump1HighTemperatureWarningInhibit						INTEGER,
				ilaEdfaPlusPump2HighTemperatureWarningInhibit						INTEGER,
				ilaEdfaPlusPump1LowTemperatureWarningInhibit						INTEGER,
				ilaEdfaPlusPump2LowTemperatureWarningInhibit						INTEGER,
				ilaEdfaPlusPump1HighOperatingCurrentAlarmInhibit					INTEGER,
				ilaEdfaPlusPump2HighOperatingCurrentAlarmInhibit					INTEGER,
				ilaEdfaPlusPump1LowOperatingCurrentAlarmInhibit						INTEGER,
				ilaEdfaPlusPump2LowOperatingCurrentAlarmInhibit						INTEGER,
				ilaEdfaPlusPump1HighOperatingCurrentWarningInhibit					INTEGER,
				ilaEdfaPlusPump2HighOperatingCurrentWarningInhibit					INTEGER,
				ilaEdfaPlusPump1LowOperatingCurrentWarningInhibit					INTEGER,
				ilaEdfaPlusPump2LowOperatingCurrentWarningInhibit					INTEGER,
				ilaEdfaPlusPump1HighThermoElectricCoolerCurrentAlarmInhibit				INTEGER,
				ilaEdfaPlusPump2HighThermoElectricCoolerCurrentAlarmInhibit				INTEGER,
				ilaEdfaPlusPump1LowThermoElectricCoolerCurrentAlarmInhibit				INTEGER,
				ilaEdfaPlusPump2LowThermoElectricCoolerCurrentAlarmInhibit				INTEGER,
				ilaEdfaPlusPump1HighThermoElectricCoolerCurrentWarningInhibit				INTEGER,
				ilaEdfaPlusPump2HighThermoElectricCoolerCurrentWarningInhibit				INTEGER,
				ilaEdfaPlusPump1LowThermoElectricCoolerCurrentWarningInhibit				INTEGER,
				ilaEdfaPlusPump2LowThermoElectricCoolerCurrentWarningInhibit				INTEGER,
				ilaEdfaPlusVariableOpticalAttenuatorHighInputPowerAlarmInhibit				INTEGER,
				ilaEdfaPlusVariableOpticalAttenuatorLowInputPowerAlarmInhibit				INTEGER,
				ilaEdfaPlusVariableOpticalAttenuatorHighInputPowerWarningInhibit			INTEGER,
				ilaEdfaPlusVariableOpticalAttenuatorLowInputPowerWarningInhibit				INTEGER,
				ilaEdfaPlusInputOutOfRangeAlarmInhibit							INTEGER,
				ilaEdfaPlusOutputOutOfRangeAlarmInhibit							INTEGER,
				ilaEdfaPlusPumpBiasCurrentAlarmInhibit							INTEGER,
				ilaEdfaPlusPump1CoolingTemperatureAlarmInhibit						INTEGER,
				ilaEdfaPlusPump2CoolingTemperatureAlarmInhibit						INTEGER,
				ilaEdfaPlusPump1LaserPowerAlarmInhibit							INTEGER,
				ilaEdfaPlusPump2LaserPowerAlarmInhibit							INTEGER,
				ilaEdfaPlusOpticalInputPowerFailureAlarmForStage1Severity 				DisplayString,
				ilaEdfaPlusOpticalInputPowerFailureAlarmForStage2Severity 				DisplayString,
				ilaEdfaPlusOpticalHighInputPowerAlarmForStage1Severity 					DisplayString,
				ilaEdfaPlusOpticalHighInputPowerAlarmForStage2Severity 					DisplayString,
				ilaEdfaPlusOpticalLowInputPowerAlarmForStage1Severity 					DisplayString,
				ilaEdfaPlusOpticalLowInputPowerAlarmForStage2Severity 					DisplayString,
				ilaEdfaPlusOpticalHighInputPowerWarningForStage1Severity 				DisplayString,
				ilaEdfaPlusOpticalHighInputPowerWarningForStage2Severity 				DisplayString,
				ilaEdfaPlusOpticalLowInputPowerWarningForStage1Severity 				DisplayString,
				ilaEdfaPlusOpticalLowInputPowerWarningForStage2Severity 				DisplayString,
				ilaEdfaPlusOpticalOutputPowerFailureAlarmForStage1Severity 				DisplayString,
				ilaEdfaPlusOpticalOutputPowerFailureAlarmForStage2Severity 				DisplayString,
				ilaEdfaPlusOpticalHighOutputPowerAlarmForStage1Severity 				DisplayString,
				ilaEdfaPlusOpticalHighOutputPowerAlarmForStage2Severity 				DisplayString,
				ilaEdfaPlusOpticalLowOutputPowerAlarmForStage1Severity 					DisplayString,
				ilaEdfaPlusOpticalLowOutputPowerAlarmForStage2Severity	 				DisplayString,
				ilaEdfaPlusOpticalHighOutputPowerWarningForStage1Severity 				DisplayString,
				ilaEdfaPlusOpticalHighOutputPowerWarningForStage2Severity 				DisplayString,
				ilaEdfaPlusOpticalLowOutputPowerWarningForStage1Severity 				DisplayString,
				ilaEdfaPlusOpticalLowOutputPowerWarningForStage2Severity 				DisplayString,
				ilaEdfaPlusModuleHighTemperatureAlarmSeverity 						DisplayString,
				ilaEdfaPlusModuleLowTemperatureAlarmSeverity 						DisplayString,
				ilaEdfaPlusModuleHighTemperatureWarningSeverity 					DisplayString,
				ilaEdfaPlusModuleLowTemperatureWarningSeverity 						DisplayString,
				ilaEdfaPlusPump1HighTemperatureAlarmSeverity 						DisplayString,
				ilaEdfaPlusPump2HighTemperatureAlarmSeverity 						DisplayString,
				ilaEdfaPlusPump1LowTemperatureAlarmSeverity 						DisplayString,
				ilaEdfaPlusPump2LowTemperatureAlarmSeverity 						DisplayString,
				ilaEdfaPlusPump1HighTemperatureWarningSeverity 						DisplayString,
				ilaEdfaPlusPump2HighTemperatureWarningSeverity 						DisplayString,
				ilaEdfaPlusPump1LowTemperatureWarningSeverity 						DisplayString,
				ilaEdfaPlusPump2LowTemperatureWarningSeverity 						DisplayString,
				ilaEdfaPlusPump1HighOperatingCurrentAlarmSeverity 					DisplayString,
				ilaEdfaPlusPump2HighOperatingCurrentAlarmSeverity 					DisplayString,
				ilaEdfaPlusPump1LowOperatingCurrentAlarmSeverity 					DisplayString,
				ilaEdfaPlusPump2LowOperatingCurrentAlarmSeverity 					DisplayString,
				ilaEdfaPlusPump1HighOperatingCurrentWarningSeverity 					DisplayString,
				ilaEdfaPlusPump2HighOperatingCurrentWarningSeverity 					DisplayString,
				ilaEdfaPlusPump1LowOperatingCurrentWarningSeverity 					DisplayString,
				ilaEdfaPlusPump2LowOperatingCurrentWarningSeverity 					DisplayString,
				ilaEdfaPlusPump1HighThermoElectricCoolerCurrentAlarmSeverity				DisplayString,
				ilaEdfaPlusPump2HighThermoElectricCoolerCurrentAlarmSeverity 				DisplayString,
				ilaEdfaPlusPump1LowThermoElectricCoolerCurrentAlarmSeverity 				DisplayString,
				ilaEdfaPlusPump2LowThermoElectricCoolerCurrentAlarmSeverity 				DisplayString,
				ilaEdfaPlusPump1HighThermoElectricCoolerCurrentWarningSeverity 				DisplayString,
				ilaEdfaPlusPump2HighThermoElectricCoolerCurrentWarningSeverity 				DisplayString,
				ilaEdfaPlusPump1LowThermoElectricCoolerCurrentWarningSeverity 				DisplayString,
				ilaEdfaPlusPump2LowThermoElectricCoolerCurrentWarningSeverity 				DisplayString,
				ilaEdfaPlusVariableOpticalAttenuatorHighInputPowerAlarmSeverity 			DisplayString,
				ilaEdfaPlusVariableOpticalAttenuatorLowInputPowerAlarmSeverity 				DisplayString,
				ilaEdfaPlusVariableOpticalAttenuatorHighInputPowerWarningSeverity 			DisplayString,
				ilaEdfaPlusVariableOpticalAttenuatorLowInputPowerWarningSeverity 			DisplayString,
				ilaEdfaPlusInputOutOfRangeAlarmSeverity 						DisplayString,
				ilaEdfaPlusOutputOutOfRangeAlarmSeverity 						DisplayString,
				ilaEdfaPlusPumpBiasCurrentAlarmSeverity 						DisplayString,
				ilaEdfaPlusPump1CoolingTemperatureAlarmSeverity						DisplayString,
				ilaEdfaPlusPump2CoolingTemperatureAlarmSeverity						DisplayString,
				ilaEdfaPlusPump1LaserPowerAlarmSeverity							DisplayString,
				ilaEdfaPlusPump2LaserPowerAlarmSeverity							DisplayString,
				ilaEdfaPlusCardSoftwareUpgrade								DisplayString,
				ilaEdfaPlusMidInOutOfRangeAlarmInhibit							INTEGER,
				ilaEdfaPlusMidOutOutOfRangeAlarmInhibit							INTEGER,
				ilaEdfaPlusMidInOutOfRangeAlarmSeverity							DisplayString,
				ilaEdfaPlusMidOutOutOfRangeAlarmSeverity						DisplayString,
				ilaEdfaPlusConfigurationTableRowStatus							RowStatus
			}
		
	ilaEdfaPlusCardSoftReset OBJECT-TYPE
		SYNTAX  	INTEGER
		MAX-ACCESS  	read-write
		STATUS  	current

		DESCRIPTION
		"Valid only as a SET command.
		Reboots the Card, Reconfigures the Card 
		i.e All Configuration Parameter	like Laser State,
		thresholds, operating mode & gain will be restored to 
		previous state.
		-----------------------------
		Values:
		Dont care, any value
		eg: 0
		-----------------------------"

		::= { ilaEdfaPlusConfigurationEntry 1 }		
	
	ilaEdfaPlusCardDefaultFactoryReset OBJECT-TYPE
		SYNTAX  	INTEGER
		MAX-ACCESS  	read-write
		STATUS  	current

		DESCRIPTION
		"Valid only as a SET command.
		Sets the Card To Factory Default State
		i.e All Configuration Parameter	like Laser State,
		thresholds, operating mode & gain will be set to 
		default state. "

		::= { ilaEdfaPlusConfigurationEntry 2 }

	ilaEdfaPlusAlarmMonitoringStatus OBJECT-TYPE
		SYNTAX  	INTEGER
		MAX-ACCESS  	read-write
		STATUS  	current

		DESCRIPTION
		"This property sets or gets the card's Alarm
		monitoring state. Disabling card alarm monitoring 
		will not provide any alarms and performances
		information to the user.
		-----------------------------
		Values:
		1 - Card Alarm Monitoring is enabled
		0 - Card Alarm Monitoring is disabled
		-----------------------------"

		::= { ilaEdfaPlusConfigurationEntry 3 }

	ilaEdfaPlusManageUnmanageStatus OBJECT-TYPE
		SYNTAX  	INTEGER
		MAX-ACCESS  	read-write
		STATUS  	current

		DESCRIPTION
		"This property will tell whether the card is 
		accessible from EMS/LCT or not. Turning off the
		accessbility to the card, will not allow the user
		to access any configuration, alarm or performance
		of the card and also turns off fast alarm
		triggering, global alarm led indication
		-----------------------------
		Values:
		1 - Card is accessible from EMS/LCT
		0 - Card is inaccessible from EMS/LCT
		-----------------------------"

		::= { ilaEdfaPlusConfigurationEntry 4 }

	ilaEdfaPlusSyncSystemTimeWithNtpServer	 OBJECT-TYPE
		SYNTAX  		DisplayString
  		MAX-ACCESS  		read-write
  		STATUS  		current
  		DESCRIPTION	 	" when we want to manually sync the time value
					present in linux kernel with the NTP server
					we can use this OID. We can provide NTP server
					ip address as a value to this OID and the time
					will be synced to that particular server. 
					If we are not providing NTP server IP address 
					then the system will be synced with the NTP server 
					which is already been registered with card. 
					If both are absent then error message will be returned
					-----------------------------
						Interface : 0
					-----------------------------
						If we want to provide NTP server IP address then
						Value should be a valid IP address as shown below
						: 192.168.21.25
						
						If we don't want to provide NTP server address then no
						need to pass any value. 
					---------------------------"
  						
  		::= { ilaEdfaPlusConfigurationEntry 5 }
  		
  	ilaEdfaPlusSyncRtcWithNtpServer	 OBJECT-TYPE
		SYNTAX  		DisplayString
  		MAX-ACCESS  		read-write
  		STATUS  		current
  		DESCRIPTION	 	" when we want to manually sync the time value
  						present in RTC with the NTP server
  						we can use this OID. We can provide NTP server
  						ip address as a value to this OID and the time
  						will be synced to that particular server. 
  						If we are not providing NTP server IP address 
  						then the system will be synced with the NTP server 
  						which is already been registered with card. 
  						If both are absent then error message will be returned.
  						-----------------------------
						Interface : 0
						-----------------------------
						If we want to provide NTP server IP address then
						Value should be a valid IP address as shown below
						: 192.168.21.25
							
						If we don't want to provide NTP server address, then no
						need to ilass any value. 
						---------------------------"
  						
  		::= { ilaEdfaPlusConfigurationEntry 6 }
  		
  	ilaEdfaPlusSyncRtcWithSystemTime	 OBJECT-TYPE
		SYNTAX  		DisplayString
  		MAX-ACCESS  	read-write
  		STATUS  		current
  		DESCRIPTION	 	" when we want to manually sync the time value
  						present in RTC with the time value in linux kernel
  						we can use this OID. With this set operation, 
  						the time available with linux kernel will be updated
  						into RTC. It is not required to provide any value for 
  						this operation"
  						
  		::= { ilaEdfaPlusConfigurationEntry 7 }
  		
  	ilaEdfaPlusUpdateGivenTimeIntoSystem	 OBJECT-TYPE
		SYNTAX  		DisplayString
  		MAX-ACCESS  	read-write
  		STATUS  		current
  		DESCRIPTION	 	" when we want to manually update system time
  						with the user provided time, we can use this OID.
  						With OID we need to provide time value which we
  						want to update in the system.
  						-----------------------------
						Interface : 0
						-----------------------------
						Value should be of given format:
						YYYY-MM-DD H:M:S
						
						Example: 2017-10-31 15:20:44
						---------------------------"
						
  		::= { ilaEdfaPlusConfigurationEntry 8 }
  		
  	ilaEdfaPlusUpdateGivenTimeIntoRtc	 OBJECT-TYPE
		SYNTAX  		DisplayString
  		MAX-ACCESS  	read-write
  		STATUS  		current
  		DESCRIPTION	 	" when we want to manually update RTC time
  						with the user provided time, we can use this OID.
  						With OID we need to provide time value which we
  						want to update in RTC.
  						-----------------------------
						Interface : 0
						-----------------------------
						Value should be of given format:
						YYYY-MM-DD H:M:S
						
						Example: 2017-10-31 15:20:44
						---------------------------"
						
  		::= { ilaEdfaPlusConfigurationEntry 9 }
  		
  	ilaEdfaPlusSystemTimeAndRtcTime	 OBJECT-TYPE
		SYNTAX  		DisplayString
  		MAX-ACCESS  		read-only
  		STATUS  		current
  		DESCRIPTION	 	" get the system time and time value present in RTC.
  						-----------------------------
						Interface : 0
						-----------------------------"
						
  		::= { ilaEdfaPlusConfigurationEntry 10 }

	ilaEdfaPlusVariableOpticalAttenuatorReset OBJECT-TYPE
		SYNTAX  	INTEGER
		MAX-ACCESS  	read-write
		STATUS  	current

		DESCRIPTION
		 " to reset variable optical attenuator of ILA EDFA PLUS card.
		-----------------------------
		Values:
		Dont care, any value
		eg: 0
		-----------------------------"

		::= { ilaEdfaPlusConfigurationEntry 21 }

	ilaEdfaPlusPump1LaserStatus OBJECT-TYPE
		SYNTAX  	INTEGER
		MAX-ACCESS  	read-write
		STATUS  	current

		DESCRIPTION
		 " to set/get ILA EDFA PLUS card pump 1 laser status.
		-----------------------------
		Values:
		1 - Laser ON
		0 - Laser OFF
		-----------------------------"

		::= { ilaEdfaPlusConfigurationEntry 22 }

	ilaEdfaPlusPump2LaserStatus OBJECT-TYPE
		SYNTAX  	INTEGER
		MAX-ACCESS  	read-write
		STATUS  	current

		DESCRIPTION
		 " to set/get ILA EDFA PLUS card pump 2 laser status.
		-----------------------------
		Values:
		1 - Laser ON
		0 - Laser OFF
		-----------------------------"

		::= { ilaEdfaPlusConfigurationEntry 23 }

	ilaEdfaPlusAutomaticPowerReductionStatusForStage1 OBJECT-TYPE
		SYNTAX  	INTEGER
		MAX-ACCESS  	read-write
		STATUS  	current

		DESCRIPTION
		 " to set/get ILA EDFA PLUS card automatic power reduction status for stage 1.
		-----------------------------
		Values:
		1 - Automatic power reduction function ON
		0 - Automatic power reduction function OFF
		-----------------------------"

		::= { ilaEdfaPlusConfigurationEntry 24 }

	ilaEdfaPlusAutomaticPowerReductionStatusForStage2 OBJECT-TYPE
		SYNTAX  	INTEGER
		MAX-ACCESS  	read-write
		STATUS  	current

		DESCRIPTION
		 " to set/get ILA EDFA PLUS card automatic power reduction status for stage 2.
		-----------------------------
		Values:
		1 - Automatic power reduction function ON
		0 - Automatic power reduction function OFF
		-----------------------------"

		::= { ilaEdfaPlusConfigurationEntry 25 }

	ilaEdfaPlusAutomaticLaserShutdownStatusForStage1 OBJECT-TYPE
		SYNTAX  	INTEGER
		MAX-ACCESS  	read-write
		STATUS  	current

		DESCRIPTION
		 " to set/get ILA EDFA PLUS card automatic laser shutdown status for stage 1.
		-----------------------------
		Values:
		1 - Automatic laser shutdown function ON
		0 - Automatic laser shutdown function OFF
		-----------------------------"

		::= { ilaEdfaPlusConfigurationEntry 26 }

	ilaEdfaPlusAutomaticLaserShutdownStatusForStage2 OBJECT-TYPE
		SYNTAX  	INTEGER
		MAX-ACCESS  	read-write
		STATUS  	current

		DESCRIPTION
		 " to set/get ILA EDFA PLUS card automatic laser shutdown status for stage 2.
		-----------------------------
		Values:
		1 - Automatic laser shutdown function ON
		0 - Automatic laser shutdown function OFF
		-----------------------------"

		::= { ilaEdfaPlusConfigurationEntry 27 }

	ilaEdfaPlusModuleOperatingModeForStage1	OBJECT-TYPE
		SYNTAX  	DisplayString (SIZE (0..255))
		MAX-ACCESS  	read-write
		STATUS  	current

		DESCRIPTION
		 "To set/get ILA EDFA PLUS card module operating mode of Stage 1.
		-----------------------------
		Values:
		APC - Automatic power control mode
		AGC - Automatic gain control mode
		ACC - Automatic current control mode
		-----------------------------"

		::= { ilaEdfaPlusConfigurationEntry 28 }

	ilaEdfaPlusModuleOperatingModeForStage2	OBJECT-TYPE
		SYNTAX  	DisplayString (SIZE (0..255))
		MAX-ACCESS  	read-write
		STATUS  	current

		DESCRIPTION
		 " to set/get ILA EDFA PLUS card module operating mode of Stage 2.
		-----------------------------
		Values:
		APC - Automatic power control mode
		AGC - Automatic gain control mode
		ACC - Automatic current control mode
		-----------------------------"

		::= { ilaEdfaPlusConfigurationEntry 29 }		
      
	ilaEdfaPlusModuleGainInAutomaticGainControlModeForStage1 OBJECT-TYPE
		SYNTAX  	DisplayString (SIZE (0..255))
		MAX-ACCESS  	read-write
		STATUS  	current

		DESCRIPTION
		 " to set/get ILA EDFA PLUS card module gain in automatic gain control mode for stage 1.
		-----------------------------
		Values:
		eg. : 15.5
		-----------------------------"

		::= { ilaEdfaPlusConfigurationEntry 30 }
		
	ilaEdfaPlusModuleGainInAutomaticGainControlModeForStage2 OBJECT-TYPE
		SYNTAX  	DisplayString (SIZE (0..255))
		MAX-ACCESS  	read-write
		STATUS  	current

		DESCRIPTION
		 " to set/get ILA EDFA PLUS card module gain in automatic gain control mode for stage 2.
		-----------------------------
		Values:
		eg. : 15.5
		-----------------------------"

		::= { ilaEdfaPlusConfigurationEntry 31 }			
     
	ilaEdfaPlusModuleOutputPowerInAutomaticPowerControlMode OBJECT-TYPE
		SYNTAX  	DisplayString (SIZE (0..255))
		MAX-ACCESS  	read-write
		STATUS  	current

		DESCRIPTION
		 " to set/get ILA EDFA PLUS card module output power in automatic power control mode.
		-----------------------------
		Values:
		eg. : 15.5
		-----------------------------"

		::= { ilaEdfaPlusConfigurationEntry 32 }		
    
	ilaEdfaPlusPump1OperatingCurrentInAutomaticCurrentControlMode OBJECT-TYPE
		SYNTAX  	DisplayString (SIZE (0..255))
		MAX-ACCESS  	read-write
		STATUS  	current

		DESCRIPTION
		 " to set/get ILA EDFA PLUS card pump 1 operating current in automatic current control mode.
		-----------------------------
		Values:
		eg. : 15.5
		-----------------------------"

		::= { ilaEdfaPlusConfigurationEntry 33 }

	ilaEdfaPlusPump2OperatingCurrentInAutomaticCurrentControlMode OBJECT-TYPE
		SYNTAX  	DisplayString (SIZE (0..255))
		MAX-ACCESS  	read-write
		STATUS  	current

		DESCRIPTION
		 " to set/get ILA EDFA PLUS card pump 2 operating current in automatic current control mode.
		-----------------------------
		Values:
		eg. : 15.5
		-----------------------------"

		::= { ilaEdfaPlusConfigurationEntry 34 }
              
    	ilaEdfaPlusGainTilt OBJECT-TYPE
		SYNTAX  	DisplayString (SIZE (0..255))
		MAX-ACCESS  	read-write
		STATUS  	current

		DESCRIPTION
		 " to set/get ILA EDFA PLUS card gain tilt.
		-----------------------------
		Values:
		eg. : 15.5
		-----------------------------"

		::= { ilaEdfaPlusConfigurationEntry 35 } 
      
	ilaEdfaPlusVariableOpticalAttenuatorAttenuationForStage2 OBJECT-TYPE
		SYNTAX  	DisplayString (SIZE (0..255))
		MAX-ACCESS  	read-write
		STATUS  	current

		DESCRIPTION
		 " to set/get ILA EDFA PLUS card variable optical attenuator attenuation.
		-----------------------------
		Values:
		eg. : 15.5
		-----------------------------"

		::= { ilaEdfaPlusConfigurationEntry 36 }	

	ilaEdfaPlusOutputPowerLimitFunctionStatusInAutomaticGainControlModeForStage1 OBJECT-TYPE
		SYNTAX  	INTEGER
		MAX-ACCESS  	read-write
		STATUS  	current

		DESCRIPTION
		 " to set/get ILA EDFA PLUS card output power limit function enable/disable status in automatic gain control mode for stage 1.
		-----------------------------
		Values:
		1 - Output power limit function will be enabled 
		0 - Output power limit function will be disabled 
		-----------------------------"

		::= { ilaEdfaPlusConfigurationEntry 37 }

	ilaEdfaPlusOutputPowerLimitFunctionStatusInAutomaticGainControlModeForStage2 OBJECT-TYPE
		SYNTAX  	INTEGER
		MAX-ACCESS  	read-write
		STATUS  	current

		DESCRIPTION
		 " to set/get ILA EDFA PLUS card output power limit function enable/disable status in automatic gain control mode for stage 2.
		-----------------------------
		Values:
		1 - Output power limit function will be enabled 
		0 - Output power limit function will be disabled 
		-----------------------------"

		::= { ilaEdfaPlusConfigurationEntry 38 }

	ilaEdfaPlusOutputPowerLimitInAutomaticGainControlModeForStage1 OBJECT-TYPE
		SYNTAX  	DisplayString (SIZE (0..255))
		MAX-ACCESS  	read-write
		STATUS  	current

		DESCRIPTION
		 " to set/get ILA EDFA PLUS card output power limit in automatic gain control mode for stage 1.
		-----------------------------
		Values:
		eg. : 15.5
		-----------------------------"

		::= { ilaEdfaPlusConfigurationEntry 39 }

	ilaEdfaPlusOutputPowerLimitInAutomaticGainControlModeForStage2 OBJECT-TYPE
		SYNTAX  	DisplayString (SIZE (0..255))
		MAX-ACCESS  	read-write
		STATUS  	current

		DESCRIPTION
		 " to set/get ILA EDFA PLUS card output power limit in automatic gain control mode for stage 2.
		-----------------------------
		Values:
		eg. : 15.5
		-----------------------------"

		::= { ilaEdfaPlusConfigurationEntry 40 }	
      
	ilaEdfaPlusAutomaticPowerReductionForStage1Threshold OBJECT-TYPE
		SYNTAX  	DisplayString (SIZE (0..255))
		MAX-ACCESS  	read-write
		STATUS  	current

		DESCRIPTION
		 " to set/get ILA EDFA PLUS card automatic power reduction threshold for Stage 1.
		-----------------------------
		Values:
		eg. : 15.5
		-----------------------------"

		::= { ilaEdfaPlusConfigurationEntry 51 }		

	ilaEdfaPlusAutomaticPowerReductionForStage2Threshold OBJECT-TYPE
		SYNTAX  	DisplayString (SIZE (0..255))
		MAX-ACCESS  	read-write
		STATUS  	current

		DESCRIPTION
		 " to set/get ILA EDFA PLUS card automatic power reduction threshold for Stage 2.
		-----------------------------
		Values:
		eg. : 15.5
		-----------------------------"

		::= { ilaEdfaPlusConfigurationEntry 52 }	
              
	ilaEdfaPlusOpticalInputPowerFailureAlarmForStage1Threshold OBJECT-TYPE
		SYNTAX  	DisplayString (SIZE (0..255))
		MAX-ACCESS  	read-write
		STATUS  	current

		DESCRIPTION
		 " to set/get ILA EDFA PLUS card optical input power failure alarm threshold for stage 1.
		-----------------------------
		Values:
		eg. : -21.0
		-----------------------------"

		::= { ilaEdfaPlusConfigurationEntry 53 }	
   
	ilaEdfaPlusOpticalInputPowerFailureAlarmForStage2Threshold OBJECT-TYPE
		SYNTAX  	DisplayString (SIZE (0..255))
		MAX-ACCESS  	read-write
		STATUS  	current

		DESCRIPTION
		 " to set/get ILA EDFA PLUS card optical input power failure alarm threshold for stage 2.
		-----------------------------
		Values:
		eg. : -21.0
		-----------------------------"

		::= { ilaEdfaPlusConfigurationEntry 54 }	
           
     	ilaEdfaPlusOpticalHighInputPowerAlarmForStage1Threshold OBJECT-TYPE
		SYNTAX  	DisplayString (SIZE (0..255))
		MAX-ACCESS  	read-write
		STATUS  	current

		DESCRIPTION
		 " to set/get ILA EDFA PLUS card optical high input power alarm threshold for stage 1.
		-----------------------------
		Values:
		eg. : 3.0
		-----------------------------"

		::= { ilaEdfaPlusConfigurationEntry 55 }         

     	ilaEdfaPlusOpticalHighInputPowerAlarmForStage2Threshold OBJECT-TYPE
		SYNTAX  	DisplayString (SIZE (0..255))
		MAX-ACCESS  	read-write
		STATUS  	current

		DESCRIPTION
		 " to set/get ILA EDFA PLUS card optical high input power alarm threshold for stage 2.
		-----------------------------
		Values:
		eg. : 3.0
		-----------------------------"

		::= { ilaEdfaPlusConfigurationEntry 56 } 
         
      	ilaEdfaPlusOpticalLowInputPowerAlarmForStage1Threshold  OBJECT-TYPE
		SYNTAX  	DisplayString (SIZE (0..255))
		MAX-ACCESS  	read-write
		STATUS  	current

		DESCRIPTION
		 " to set/get ILA EDFA PLUS card optical low input power alarm threshold for stage 1.
		-----------------------------
		Values:
		eg. : -18.0
		-----------------------------"

		::= { ilaEdfaPlusConfigurationEntry 57 }

      	ilaEdfaPlusOpticalLowInputPowerAlarmForStage2Threshold  OBJECT-TYPE
		SYNTAX  	DisplayString (SIZE (0..255))
		MAX-ACCESS  	read-write
		STATUS  	current

		DESCRIPTION
		 " to set/get ILA EDFA PLUS card optical low input power alarm threshold for stage 2.
		-----------------------------
		Values:
		eg. : -18.0
		-----------------------------"

		::= { ilaEdfaPlusConfigurationEntry 58 }

	ilaEdfaPlusOpticalHighInputPowerWarningForStage1Threshold OBJECT-TYPE
		SYNTAX  	DisplayString (SIZE (0..255))
		MAX-ACCESS  	read-write
		STATUS  	current

		DESCRIPTION
		 " to set/get ILA EDFA PLUS card optical high input power warning threshold for stage 1.
		-----------------------------
		Values:
		eg. : 2.0
		-----------------------------"

		::= { ilaEdfaPlusConfigurationEntry 59 }         

	ilaEdfaPlusOpticalHighInputPowerWarningForStage2Threshold OBJECT-TYPE
		SYNTAX  	DisplayString (SIZE (0..255))
		MAX-ACCESS  	read-write
		STATUS  	current

		DESCRIPTION
		 " to set/get ILA EDFA PLUS card optical high input power warning threshold for stage 2.
		-----------------------------
		Values:
		eg. : 2.0
		-----------------------------"

		::= { ilaEdfaPlusConfigurationEntry 60 }
         
      	ilaEdfaPlusOpticalLowInputPowerWarningForStage1Threshold  OBJECT-TYPE
		SYNTAX  	DisplayString (SIZE (0..255))
		MAX-ACCESS  	read-write
		STATUS  	current

		DESCRIPTION
		 " to set/get ILA EDFA PLUS card optical low input power warning threshold for stage 1.
		-----------------------------
		Values:
		eg. : -19.0
		-----------------------------"

		::= { ilaEdfaPlusConfigurationEntry 61 } 

      	ilaEdfaPlusOpticalLowInputPowerWarningForStage2Threshold  OBJECT-TYPE
		SYNTAX  	DisplayString (SIZE (0..255))
		MAX-ACCESS  	read-write
		STATUS  	current

		DESCRIPTION
		 " to set/get ILA EDFA PLUS card optical low input power warning threshold for stage 2.
		-----------------------------
		Values:
		eg. : -19.0
		-----------------------------"

		::= { ilaEdfaPlusConfigurationEntry 62 }

	ilaEdfaPlusOpticalOutputPowerFailureAlarmForStage1Threshold OBJECT-TYPE
		SYNTAX  	DisplayString (SIZE (0..255))
		MAX-ACCESS  	read-write
		STATUS  	current

		DESCRIPTION
		 " to set/get ILA EDFA PLUS card optical output power failure alarm threshold for stage 1.
		-----------------------------
		Values:
		eg. : 5.0
		-----------------------------"

		::= { ilaEdfaPlusConfigurationEntry 63 }         
 
	ilaEdfaPlusOpticalOutputPowerFailureAlarmForStage2Threshold OBJECT-TYPE
		SYNTAX  	DisplayString (SIZE (0..255))
		MAX-ACCESS  	read-write
		STATUS  	current

		DESCRIPTION
		 " to set/get ILA EDFA PLUS card optical output power failure alarm threshold for stage 2.
		-----------------------------
		Values:
		eg. : 5.0
		-----------------------------"

		::= { ilaEdfaPlusConfigurationEntry 64 }
        
      	ilaEdfaPlusOpticalHighOutputPowerAlarmForStage1Threshold  OBJECT-TYPE
		SYNTAX  	DisplayString (SIZE (0..255))
		MAX-ACCESS  	read-write
		STATUS  	current

		DESCRIPTION
		 " to set/get ILA EDFA PLUS card optical high output power alarm threshold for stage 1.
		-----------------------------
		Values:
		eg. : 19.0
		-----------------------------"

		::= { ilaEdfaPlusConfigurationEntry 65 }

      	ilaEdfaPlusOpticalHighOutputPowerAlarmForStage2Threshold  OBJECT-TYPE
		SYNTAX  	DisplayString (SIZE (0..255))
		MAX-ACCESS  	read-write
		STATUS  	current

		DESCRIPTION
		 " to set/get ILA EDFA PLUS card optical high output power alarm threshold for stage 2.
		-----------------------------
		Values:
		eg. : 19.0
		-----------------------------"

		::= { ilaEdfaPlusConfigurationEntry 66 } 

	ilaEdfaPlusOpticalLowOutputPowerAlarmForStage1Threshold OBJECT-TYPE
		SYNTAX  	DisplayString (SIZE (0..255))
		MAX-ACCESS  	read-write
		STATUS  	current

		DESCRIPTION
		 " to set/get ILA EDFA PLUS card optical low output power alarm threshold for stage 1.
		-----------------------------
		Values:
		eg. : 10.0
		-----------------------------"

		::= { ilaEdfaPlusConfigurationEntry 67 }         

	ilaEdfaPlusOpticalLowOutputPowerAlarmForStage2Threshold OBJECT-TYPE
		SYNTAX  	DisplayString (SIZE (0..255))
		MAX-ACCESS  	read-write
		STATUS  	current

		DESCRIPTION
		 " to set/get ILA EDFA PLUS card optical low output power alarm threshold for stage 2.
		-----------------------------
		Values:
		eg. : 10.0
		-----------------------------"

		::= { ilaEdfaPlusConfigurationEntry 68 }  
         
      	ilaEdfaPlusOpticalHighOutputPowerWarningForStage1Threshold  OBJECT-TYPE
		SYNTAX  	DisplayString (SIZE (0..255))
		MAX-ACCESS  	read-write
		STATUS  	current

		DESCRIPTION
		 " to set/get ILA EDFA PLUS card optical high output power warning threshold for stage 1.
		-----------------------------
		Values:
		eg. : 18.0
		-----------------------------"

		::= { ilaEdfaPlusConfigurationEntry 69 } 

      	ilaEdfaPlusOpticalHighOutputPowerWarningForStage2Threshold  OBJECT-TYPE
		SYNTAX  	DisplayString (SIZE (0..255))
		MAX-ACCESS  	read-write
		STATUS  	current

		DESCRIPTION
		 " to set/get ILA EDFA PLUS card optical high output power warning threshold for stage 2.
		-----------------------------
		Values:
		eg. : 18.0
		-----------------------------"

		::= { ilaEdfaPlusConfigurationEntry 70 } 

	ilaEdfaPlusOpticalLowOutputPowerWarningForStage1Threshold OBJECT-TYPE
		SYNTAX  	DisplayString (SIZE (0..255))
		MAX-ACCESS  	read-write
		STATUS  	current

		DESCRIPTION
		 " to set/get ILA EDFA PLUS card optical low output power warning threshold for stage 1.
		-----------------------------
		Values:
		eg. : 1.0
		-----------------------------"

		::= { ilaEdfaPlusConfigurationEntry 71 }         

	ilaEdfaPlusOpticalLowOutputPowerWarningForStage2Threshold OBJECT-TYPE
		SYNTAX  	DisplayString (SIZE (0..255))
		MAX-ACCESS  	read-write
		STATUS  	current

		DESCRIPTION
		 " to set/get ILA EDFA PLUS card optical low output power warning threshold for stage 2.
		-----------------------------
		Values:
		eg. : 1.0
		-----------------------------"

		::= { ilaEdfaPlusConfigurationEntry 72 }
         
      	ilaEdfaPlusModuleHighTemperatureAlarmThreshold  OBJECT-TYPE
		SYNTAX  	DisplayString (SIZE (0..255))
		MAX-ACCESS  	read-write
		STATUS  	current

		DESCRIPTION
		 " to set/get ILA EDFA PLUS card module high temperature alarm threshold.
		-----------------------------
		Values:
		eg. : 75.0
		-----------------------------"

		::= { ilaEdfaPlusConfigurationEntry 73 } 

	ilaEdfaPlusModuleLowTemperatureAlarmThreshold OBJECT-TYPE
		SYNTAX  	DisplayString (SIZE (0..255))
		MAX-ACCESS  	read-write
		STATUS  	current

		DESCRIPTION
		 " to set/get ILA EDFA PLUS card module low temperature alarm threshold.
		-----------------------------
		Values:
		eg. : 5.0
		-----------------------------"

		::= { ilaEdfaPlusConfigurationEntry 74 }         
         
      	ilaEdfaPlusModuleHighTemperatureWarningThreshold  OBJECT-TYPE
		SYNTAX  	DisplayString (SIZE (0..255))
		MAX-ACCESS  	read-write
		STATUS  	current

		DESCRIPTION
		 " to set/get ILA EDFA PLUS card module high temperature warning threshold.
		-----------------------------
		Values:
		eg. : 60.0
		-----------------------------"

		::= { ilaEdfaPlusConfigurationEntry 75 }             

	ilaEdfaPlusModuleLowTemperatureWarningThreshold  OBJECT-TYPE
		SYNTAX  	DisplayString (SIZE (0..255))
		MAX-ACCESS  	read-write
		STATUS  	current

		DESCRIPTION
		 " to set/get ILA EDFA PLUS card module low temperature warning threshold.
		-----------------------------
		Values:
		eg. : 8.0
		-----------------------------"

		::= { ilaEdfaPlusConfigurationEntry 76 }

	ilaEdfaPlusPump1HighTemperatureAlarmThreshold  OBJECT-TYPE
		SYNTAX  	DisplayString (SIZE (0..255))
		MAX-ACCESS  	read-write
		STATUS  	current

		DESCRIPTION
		 " to set/get ILA EDFA PLUS card pump 1 high temperature alarm threshold.
		-----------------------------
		Values:
		eg. : 75.0
		-----------------------------"

		::= { ilaEdfaPlusConfigurationEntry 77 }

	ilaEdfaPlusPump2HighTemperatureAlarmThreshold  OBJECT-TYPE
		SYNTAX  	DisplayString (SIZE (0..255))
		MAX-ACCESS  	read-write
		STATUS  	current

		DESCRIPTION
		 " to set/get ILA EDFA PLUS card pump 2 high temperature alarm threshold.
		-----------------------------
		Values:
		eg. : 75.0
		-----------------------------"

		::= { ilaEdfaPlusConfigurationEntry 78 }

	ilaEdfaPlusPump1LowTemperatureAlarmThreshold  OBJECT-TYPE
		SYNTAX  	DisplayString (SIZE (0..255))
		MAX-ACCESS  	read-write
		STATUS  	current

		DESCRIPTION
		 " to set/get ILA EDFA PLUS card pump 1 low temperature alarm threshold.
		-----------------------------
		Values:
		eg. : 5.0
		-----------------------------"

		::= { ilaEdfaPlusConfigurationEntry 79 }

	ilaEdfaPlusPump2LowTemperatureAlarmThreshold  OBJECT-TYPE
		SYNTAX  	DisplayString (SIZE (0..255))
		MAX-ACCESS  	read-write
		STATUS  	current

		DESCRIPTION
		 " to set/get ILA EDFA PLUS card pump 2 low temperature alarm threshold.
		-----------------------------
		Values:
		eg. : 5.0
		-----------------------------"

		::= { ilaEdfaPlusConfigurationEntry 80 }

	ilaEdfaPlusPump1HighTemperatureWarningThreshold  OBJECT-TYPE
		SYNTAX  	DisplayString (SIZE (0..255))
		MAX-ACCESS  	read-write
		STATUS  	current

		DESCRIPTION
		 " to set/get ILA EDFA PLUS card pump 1 high temperature warning threshold.
		-----------------------------
		Values:
		eg. : 60.0
		-----------------------------"

		::= { ilaEdfaPlusConfigurationEntry 81 }

	ilaEdfaPlusPump2HighTemperatureWarningThreshold  OBJECT-TYPE
		SYNTAX  	DisplayString (SIZE (0..255))
		MAX-ACCESS  	read-write
		STATUS  	current

		DESCRIPTION
		 " to set/get ILA EDFA PLUS card pump 2 high temperature warning threshold.
		-----------------------------
		Values:
		eg. : 60.0
		-----------------------------"

		::= { ilaEdfaPlusConfigurationEntry 82 }

	ilaEdfaPlusPump1LowTemperatureWarningThreshold  OBJECT-TYPE
		SYNTAX  	DisplayString (SIZE (0..255))
		MAX-ACCESS  	read-write
		STATUS  	current

		DESCRIPTION
		 " to set/get ILA EDFA PLUS card pump 1 low temperature warning threshold.
		-----------------------------
		Values:
		eg. : 8.0
		-----------------------------"

		::= { ilaEdfaPlusConfigurationEntry 83 }

	ilaEdfaPlusPump2LowTemperatureWarningThreshold  OBJECT-TYPE
		SYNTAX  	DisplayString (SIZE (0..255))
		MAX-ACCESS  	read-write
		STATUS  	current

		DESCRIPTION
		 " to set/get ILA EDFA PLUS card pump 2 low temperature warning threshold.
		-----------------------------
		Values:
		eg. : 8.0
		-----------------------------"

		::= { ilaEdfaPlusConfigurationEntry 84 }

	ilaEdfaPlusPump1HighOperatingCurrentAlarmThreshold  OBJECT-TYPE
		SYNTAX  	DisplayString (SIZE (0..255))
		MAX-ACCESS  	read-write
		STATUS  	current

		DESCRIPTION
		 " to set/get ILA EDFA PLUS card pump 1 high operating current alarm threshold.
		-----------------------------
		Values:
		eg. : 15.5
		-----------------------------"

		::= { ilaEdfaPlusConfigurationEntry 85 }

	ilaEdfaPlusPump2HighOperatingCurrentAlarmThreshold  OBJECT-TYPE
		SYNTAX  	DisplayString (SIZE (0..255))
		MAX-ACCESS  	read-write
		STATUS  	current

		DESCRIPTION
		 " to set/get ILA EDFA PLUS card pump 2 high operating current alarm threshold.
		-----------------------------
		Values:
		eg. : 15.5
		-----------------------------"

		::= { ilaEdfaPlusConfigurationEntry 86 }

	ilaEdfaPlusPump1LowOperatingCurrentAlarmThreshold  OBJECT-TYPE
		SYNTAX  	DisplayString (SIZE (0..255))
		MAX-ACCESS  	read-write
		STATUS  	current

		DESCRIPTION
		 " to set/get ILA EDFA PLUS card pump 1 low operating current alarm threshold.
		-----------------------------
		Values:
		eg. : 15.5
		-----------------------------"

		::= { ilaEdfaPlusConfigurationEntry 87 }

	ilaEdfaPlusPump2LowOperatingCurrentAlarmThreshold  OBJECT-TYPE
		SYNTAX  	DisplayString (SIZE (0..255))
		MAX-ACCESS  	read-write
		STATUS  	current

		DESCRIPTION
		 " to set/get ILA EDFA PLUS card pump 2 low operating current alarm threshold.
		-----------------------------
		Values:
		eg. : 15.5
		-----------------------------"

		::= { ilaEdfaPlusConfigurationEntry 88 }
	
	ilaEdfaPlusPump1HighOperatingCurrentWarningThreshold  OBJECT-TYPE
		SYNTAX  	DisplayString (SIZE (0..255))
		MAX-ACCESS  	read-write
		STATUS  	current

		DESCRIPTION
		 " to set/get ILA EDFA PLUS card pump 1 high operating current warning threshold.
		-----------------------------
		Values:
		eg. : 15.5
		-----------------------------"

		::= { ilaEdfaPlusConfigurationEntry 89 }

	ilaEdfaPlusPump2HighOperatingCurrentWarningThreshold  OBJECT-TYPE
		SYNTAX  	DisplayString (SIZE (0..255))
		MAX-ACCESS  	read-write
		STATUS  	current

		DESCRIPTION
		 " to set/get ILA EDFA PLUS card pump 2 high operating current warning threshold.
		-----------------------------
		Values:
		eg. : 15.5
		-----------------------------"

		::= { ilaEdfaPlusConfigurationEntry 90 }

	ilaEdfaPlusPump1LowOperatingCurrentWarningThreshold  OBJECT-TYPE
		SYNTAX  	DisplayString (SIZE (0..255))
		MAX-ACCESS  	read-write
		STATUS  	current

		DESCRIPTION
		 " to set/get ILA EDFA PLUS card pump 1 high operating current warning threshold.
		-----------------------------
		Values:
		eg. : 15.5
		-----------------------------"

		::= { ilaEdfaPlusConfigurationEntry 91 }

	ilaEdfaPlusPump2LowOperatingCurrentWarningThreshold  OBJECT-TYPE
		SYNTAX  	DisplayString (SIZE (0..255))
		MAX-ACCESS  	read-write
		STATUS  	current

		DESCRIPTION
		 " to set/get ILA EDFA PLUS card pump 2 high operating current warning threshold.
		-----------------------------
		Values:
		eg. : 15.5
		-----------------------------"

		::= { ilaEdfaPlusConfigurationEntry 92 }

	ilaEdfaPlusPump1HighThermoElectricCoolerCurrentAlarmThreshold  OBJECT-TYPE
		SYNTAX  	DisplayString (SIZE (0..255))
		MAX-ACCESS  	read-write
		STATUS  	current

		DESCRIPTION
		 " to set/get ILA EDFA PLUS card pump 1 high thermo electric cooler current alarm threshold.
		-----------------------------
		Values:
		eg. : 15.5
		-----------------------------"

		::= { ilaEdfaPlusConfigurationEntry 93 }

	ilaEdfaPlusPump2HighThermoElectricCoolerCurrentAlarmThreshold  OBJECT-TYPE
		SYNTAX  	DisplayString (SIZE (0..255))
		MAX-ACCESS  	read-write
		STATUS  	current

		DESCRIPTION
		 " to set/get ILA EDFA PLUS card pump 2 high thermo electric cooler current alarm threshold.
		-----------------------------
		Values:
		eg. : 15.5
		-----------------------------"

		::= { ilaEdfaPlusConfigurationEntry 94 }

	ilaEdfaPlusPump1LowThermoElectricCoolerCurrentAlarmThreshold  OBJECT-TYPE
		SYNTAX  	DisplayString (SIZE (0..255))
		MAX-ACCESS  	read-write
		STATUS  	current

		DESCRIPTION
		 " to set/get ILA EDFA PLUS card pump 1 low thermo electric cooler current alarm threshold.
		-----------------------------
		Values:
		eg. : 15.5
		-----------------------------"

		::= { ilaEdfaPlusConfigurationEntry 95 }

	ilaEdfaPlusPump2LowThermoElectricCoolerCurrentAlarmThreshold  OBJECT-TYPE
		SYNTAX  	DisplayString (SIZE (0..255))
		MAX-ACCESS  	read-write
		STATUS  	current

		DESCRIPTION
		 " to set/get ILA EDFA PLUS card pump 2 low thermo electric cooler current alarm threshold.
		-----------------------------
		Values:
		eg. : 15.5
		-----------------------------"

		::= { ilaEdfaPlusConfigurationEntry 96 }

	ilaEdfaPlusPump1HighThermoElectricCoolerCurrentWarningThreshold  OBJECT-TYPE
		SYNTAX  	DisplayString (SIZE (0..255))
		MAX-ACCESS  	read-write
		STATUS  	current

		DESCRIPTION
		 " to set/get ILA EDFA PLUS card pump 1 high thermo electric cooler current warning threshold.
		-----------------------------
		Values:
		eg. : 15.5
		-----------------------------"

		::= { ilaEdfaPlusConfigurationEntry 97 }

	ilaEdfaPlusPump2HighThermoElectricCoolerCurrentWarningThreshold  OBJECT-TYPE
		SYNTAX  	DisplayString (SIZE (0..255))
		MAX-ACCESS  	read-write
		STATUS  	current

		DESCRIPTION
		 " to set/get ILA EDFA PLUS card pump 2 high thermo electric cooler current warning threshold.
		-----------------------------
		Values:
		eg. : 15.5
		-----------------------------"

		::= { ilaEdfaPlusConfigurationEntry 98 }

	ilaEdfaPlusPump1LowThermoElectricCoolerCurrentWarningThreshold  OBJECT-TYPE
		SYNTAX  	DisplayString (SIZE (0..255))
		MAX-ACCESS  	read-write
		STATUS  	current

		DESCRIPTION
		 " to set/get ILA EDFA PLUS card pump 1 low thermo electric cooler current warning threshold.
		-----------------------------
		Values:
		eg. : 15.5
		-----------------------------"

		::= { ilaEdfaPlusConfigurationEntry 99 }

	ilaEdfaPlusPump2LowThermoElectricCoolerCurrentWarningThreshold  OBJECT-TYPE
		SYNTAX  	DisplayString (SIZE (0..255))
		MAX-ACCESS  	read-write
		STATUS  	current

		DESCRIPTION
		 " to set/get ILA EDFA PLUS card pump 2 low thermo electric cooler current warning threshold.
		-----------------------------
		Values:
		eg. : 15.5
		-----------------------------"

		::= { ilaEdfaPlusConfigurationEntry 100 }

	ilaEdfaPlusVariableOpticalAttenuatorHighInputPowerAlarmThreshold  OBJECT-TYPE
		SYNTAX  	DisplayString (SIZE (0..255))
		MAX-ACCESS  	read-write
		STATUS  	current

		DESCRIPTION
		 " to set/get ILA EDFA PLUS card variable optical attenuator high input power alarm threshold.
		-----------------------------
		Values:
		eg. : 15.5
		-----------------------------"

		::= { ilaEdfaPlusConfigurationEntry 101 }

	ilaEdfaPlusVariableOpticalAttenuatorLowInputPowerAlarmThreshold  OBJECT-TYPE
		SYNTAX  	DisplayString (SIZE (0..255))
		MAX-ACCESS  	read-write
		STATUS  	current

		DESCRIPTION
		 " to set/get ILA EDFA PLUS card variable optical attenuator low input power alarm threshold.
		-----------------------------
		Values:
		eg. : 15.5
		-----------------------------"

		::= { ilaEdfaPlusConfigurationEntry 102 }

	ilaEdfaPlusVariableOpticalAttenuatorHighInputPowerWarningThreshold  OBJECT-TYPE
		SYNTAX  	DisplayString (SIZE (0..255))
		MAX-ACCESS  	read-write
		STATUS  	current

		DESCRIPTION
		 " to set/get ILA EDFA PLUS card variable optical attenuator high input power warning threshold.
		-----------------------------
		Values:
		eg. : 15.5
		-----------------------------"

		::= { ilaEdfaPlusConfigurationEntry 103 }

	ilaEdfaPlusVariableOpticalAttenuatorLowInputPowerWarningThreshold  OBJECT-TYPE
		SYNTAX  	DisplayString (SIZE (0..255))
		MAX-ACCESS  	read-write
		STATUS  	current

		DESCRIPTION
		 " to set/get ILA EDFA PLUS card variable optical attenuator low input power alarm threshold.
		-----------------------------
		Values:
		eg. : 15.5
		-----------------------------"

		::= { ilaEdfaPlusConfigurationEntry 104 }

	ilaEdfaPlusOpticalInputPowerFailureAlarmForStage1Inhibit OBJECT-TYPE
		SYNTAX  	INTEGER
		MAX-ACCESS  	read-write
		STATUS  	current

		DESCRIPTION
		 " to set/get ILA EDFA PLUS card optical input power failure alarm inhibit status for stage 1.
		-----------------------------
		Value:
		1 - Inhibit
		0 - Do Not Inhibit
		-----------------------------"

		::= { ilaEdfaPlusConfigurationEntry 131 }	                                              

	ilaEdfaPlusOpticalInputPowerFailureAlarmForStage2Inhibit OBJECT-TYPE
		SYNTAX  	INTEGER
		MAX-ACCESS  	read-write
		STATUS  	current

		DESCRIPTION
		 " to set/get ILA EDFA PLUS card optical input power failure alarm inhibit status for stage 2.
		-----------------------------
		Value:
		1 - Inhibit
		0 - Do Not Inhibit
		-----------------------------"

		::= { ilaEdfaPlusConfigurationEntry 132 }
                      
	ilaEdfaPlusOpticalHighInputPowerAlarmForStage1Inhibit OBJECT-TYPE
		SYNTAX  	INTEGER
		MAX-ACCESS  	read-write
		STATUS  	current

		DESCRIPTION
		 " to set/get ILA EDFA PLUS card optical high input power alarm inhibit status for stage 1.
		-----------------------------
		Value:
		1 - Inhibit
		0 - Do Not Inhibit
		-----------------------------"

		::= { ilaEdfaPlusConfigurationEntry 133 }	              

	ilaEdfaPlusOpticalHighInputPowerAlarmForStage2Inhibit OBJECT-TYPE
		SYNTAX  	INTEGER
		MAX-ACCESS  	read-write
		STATUS  	current

		DESCRIPTION
		 " to set/get ILA EDFA PLUS card optical high input power alarm inhibit status for stage 2.
		-----------------------------
		Value:
		1 - Inhibit
		0 - Do Not Inhibit
		-----------------------------"

		::= { ilaEdfaPlusConfigurationEntry 134 }
                      
	ilaEdfaPlusOpticalLowInputPowerAlarmForStage1Inhibit OBJECT-TYPE
		SYNTAX  	INTEGER
		MAX-ACCESS  	read-write
		STATUS  	current

		DESCRIPTION
		 " to set/get ILA EDFA PLUS card optical low input power alarm inhibit status for stage 1.
		-----------------------------
		Value:
		1 - Inhibit
		0 - Do Not Inhibit
		-----------------------------"

		::= { ilaEdfaPlusConfigurationEntry 135 }	              

	ilaEdfaPlusOpticalLowInputPowerAlarmForStage2Inhibit OBJECT-TYPE
		SYNTAX  	INTEGER
		MAX-ACCESS  	read-write
		STATUS  	current

		DESCRIPTION
		 " to set/get ILA EDFA PLUS card optical low input power alarm inhibit status for stage 2.
		-----------------------------
		Value:
		1 - Inhibit
		0 - Do Not Inhibit
		-----------------------------"

		::= { ilaEdfaPlusConfigurationEntry 136 }
                      
	ilaEdfaPlusOpticalHighInputPowerWarningForStage1Inhibit OBJECT-TYPE
		SYNTAX  	INTEGER
		MAX-ACCESS  	read-write
		STATUS  	current

		DESCRIPTION
		 " to set/get ILA EDFA PLUS card optical high input power warning inhibit status for stage 1.
		-----------------------------
		Value:
		1 - Inhibit
		0 - Do Not Inhibit
		-----------------------------"

		::= { ilaEdfaPlusConfigurationEntry 137 }	              

	ilaEdfaPlusOpticalHighInputPowerWarningForStage2Inhibit OBJECT-TYPE
		SYNTAX  	INTEGER
		MAX-ACCESS  	read-write
		STATUS  	current

		DESCRIPTION
		 " to set/get ILA EDFA PLUS card optical high input power warning inhibit status for stage 2.
		-----------------------------
		Value:
		1 - Inhibit
		0 - Do Not Inhibit
		-----------------------------"

		::= { ilaEdfaPlusConfigurationEntry 138 }
                      
	ilaEdfaPlusOpticalLowInputPowerWarningForStage1Inhibit OBJECT-TYPE
		SYNTAX  	INTEGER
		MAX-ACCESS  	read-write
		STATUS  	current

		DESCRIPTION
		 " to set/get ILA EDFA PLUS card optical low input power warning inhibit status for stage 1.
		-----------------------------
		Value:
		1 - Inhibit
		0 - Do Not Inhibit
		-----------------------------"

		::= { ilaEdfaPlusConfigurationEntry 139 }              

	ilaEdfaPlusOpticalLowInputPowerWarningForStage2Inhibit OBJECT-TYPE
		SYNTAX  	INTEGER
		MAX-ACCESS  	read-write
		STATUS  	current

		DESCRIPTION
		 " to set/get ILA EDFA PLUS card optical low input power warning inhibit status for stage 2.
		-----------------------------
		Value:
		1 - Inhibit
		0 - Do Not Inhibit
		-----------------------------"

		::= { ilaEdfaPlusConfigurationEntry 140 } 
                    
	ilaEdfaPlusOpticalOutputPowerFailureAlarmForStage1Inhibit OBJECT-TYPE
		SYNTAX  	INTEGER
		MAX-ACCESS  	read-write
		STATUS  	current

		DESCRIPTION
		 " to set/get ILA EDFA PLUS card optical output power failure alarm inhibit status for stage 1.
		-----------------------------
		Value:
		1 - Inhibit
		0 - Do Not Inhibit
		-----------------------------"

		::= { ilaEdfaPlusConfigurationEntry 141 }

	ilaEdfaPlusOpticalOutputPowerFailureAlarmForStage2Inhibit OBJECT-TYPE
		SYNTAX  	INTEGER
		MAX-ACCESS  	read-write
		STATUS  	current

		DESCRIPTION
		 " to set/get ILA EDFA PLUS card optical output power failure alarm inhibit status for stage 2.
		-----------------------------
		Value:
		1 - Inhibit
		0 - Do Not Inhibit
		-----------------------------"

		::= { ilaEdfaPlusConfigurationEntry 142 }


	ilaEdfaPlusOpticalHighOutputPowerAlarmForStage1Inhibit OBJECT-TYPE
		SYNTAX  	INTEGER
		MAX-ACCESS  	read-write
		STATUS  	current

		DESCRIPTION
		 " to set/get ILA EDFA PLUS card optical high output power alarm inhibit status for stage 1.
		-----------------------------
		Value:
		1 - Inhibit
		0 - Do Not Inhibit
		-----------------------------"

		::= { ilaEdfaPlusConfigurationEntry 143 }

	ilaEdfaPlusOpticalHighOutputPowerAlarmForStage2Inhibit OBJECT-TYPE
		SYNTAX  	INTEGER
		MAX-ACCESS  	read-write
		STATUS  	current

		DESCRIPTION
		 " to set/get ILA EDFA PLUS card optical high output power alarm inhibit status for stage 2.
		-----------------------------
		Value:
		1 - Inhibit
		0 - Do Not Inhibit
		-----------------------------"

		::= { ilaEdfaPlusConfigurationEntry 144 }

	ilaEdfaPlusOpticalLowOutputPowerAlarmForStage1Inhibit OBJECT-TYPE
		SYNTAX  	INTEGER
		MAX-ACCESS  	read-write
		STATUS  	current

		DESCRIPTION
		 " to set/get ILA EDFA PLUS card optical low output power alarm inhibit status for stage 1.
		-----------------------------
		Value:
		1 - Inhibit
		0 - Do Not Inhibit
		-----------------------------"

		::= { ilaEdfaPlusConfigurationEntry 145 }

	ilaEdfaPlusOpticalLowOutputPowerAlarmForStage2Inhibit OBJECT-TYPE
		SYNTAX  	INTEGER
		MAX-ACCESS  	read-write
		STATUS  	current

		DESCRIPTION
		 " to set/get ILA EDFA PLUS card optical low output power alarm inhibit status for stage 2.
		-----------------------------
		Value:
		1 - Inhibit
		0 - Do Not Inhibit
		-----------------------------"

		::= { ilaEdfaPlusConfigurationEntry 146 }

	ilaEdfaPlusOpticalHighOutputPowerWarningForStage1Inhibit OBJECT-TYPE
		SYNTAX  	INTEGER
		MAX-ACCESS  	read-write
		STATUS  	current

		DESCRIPTION
		 " to set/get ILA EDFA PLUS card optical high output power warning inhibit status for stage 1.
		-----------------------------
		Value:
		1 - Inhibit
		0 - Do Not Inhibit
		-----------------------------"

		::= { ilaEdfaPlusConfigurationEntry 147 }

	ilaEdfaPlusOpticalHighOutputPowerWarningForStage2Inhibit OBJECT-TYPE
		SYNTAX  	INTEGER
		MAX-ACCESS  	read-write
		STATUS  	current

		DESCRIPTION
		 " to set/get ILA EDFA PLUS card optical high output power warning inhibit status for stage 2.
		-----------------------------
		Value:
		1 - Inhibit
		0 - Do Not Inhibit
		-----------------------------"

		::= { ilaEdfaPlusConfigurationEntry 148 }

	ilaEdfaPlusOpticalLowOutputPowerWarningForStage1Inhibit OBJECT-TYPE
		SYNTAX  	INTEGER
		MAX-ACCESS  	read-write
		STATUS  	current

		DESCRIPTION
		 " to set/get ILA EDFA PLUS card optical low output power warning inhibit status for stage 1.
		-----------------------------
		Value:
		1 - Inhibit
		0 - Do Not Inhibit
		-----------------------------"

		::= { ilaEdfaPlusConfigurationEntry 149 }

	ilaEdfaPlusOpticalLowOutputPowerWarningForStage2Inhibit OBJECT-TYPE
		SYNTAX  	INTEGER
		MAX-ACCESS  	read-write
		STATUS  	current

		DESCRIPTION
		 " to set/get ILA EDFA PLUS card optical low output power warning inhibit status for stage 2.
		-----------------------------
		Value:
		1 - Inhibit
		0 - Do Not Inhibit
		-----------------------------"

		::= { ilaEdfaPlusConfigurationEntry 150 }

	ilaEdfaPlusModuleHighTemperatureAlarmInhibit OBJECT-TYPE
		SYNTAX  	INTEGER
		MAX-ACCESS  	read-write
		STATUS  	current

		DESCRIPTION
		 " to set/get ILA EDFA PLUS card module high temperature alarm inhibit status.
		-----------------------------
		Value:
		1 - Inhibit
		0 - Do Not Inhibit
		-----------------------------"

		::= { ilaEdfaPlusConfigurationEntry 151 }

	ilaEdfaPlusModuleLowTemperatureAlarmInhibit OBJECT-TYPE
		SYNTAX  	INTEGER
		MAX-ACCESS  	read-write
		STATUS  	current

		DESCRIPTION
		 " to set/get ILA EDFA PLUS card module low temperature alarm inhibit status.
		-----------------------------
		Value:
		1 - Inhibit
		0 - Do Not Inhibit
		-----------------------------"

		::= { ilaEdfaPlusConfigurationEntry 152 }

	ilaEdfaPlusModuleHighTemperatureWarningInhibit OBJECT-TYPE
		SYNTAX  	INTEGER
		MAX-ACCESS  	read-write
		STATUS  	current

		DESCRIPTION
		 " to set/get ILA EDFA PLUS card module high temperature warning inhibit status.
		-----------------------------
		Value:
		1 - Inhibit
		0 - Do Not Inhibit
		-----------------------------"

		::= { ilaEdfaPlusConfigurationEntry 153 }

	ilaEdfaPlusModuleLowTemperatureWarningInhibit OBJECT-TYPE
		SYNTAX  	INTEGER
		MAX-ACCESS  	read-write
		STATUS  	current

		DESCRIPTION
		 " to set/get ILA EDFA PLUS card module low temperature warning inhibit status.
		-----------------------------
		Value:
		1 - Inhibit
		0 - Do Not Inhibit
		-----------------------------"

		::= { ilaEdfaPlusConfigurationEntry 154 }

	ilaEdfaPlusPump1HighTemperatureAlarmInhibit OBJECT-TYPE
		SYNTAX  	INTEGER
		MAX-ACCESS  	read-write
		STATUS  	current

		DESCRIPTION
		 " to set/get ILA EDFA PLUS card pump 1 high temperature alarm inhibit status.
		-----------------------------
		Value:
		1 - Inhibit
		0 - Do Not Inhibit
		-----------------------------"

		::= { ilaEdfaPlusConfigurationEntry 155 }

	ilaEdfaPlusPump2HighTemperatureAlarmInhibit OBJECT-TYPE
		SYNTAX  	INTEGER
		MAX-ACCESS  	read-write
		STATUS  	current

		DESCRIPTION
		 " to set/get ILA EDFA PLUS card pump 2 high temperature alarm inhibit status.
		-----------------------------
		Value:
		1 - Inhibit
		0 - Do Not Inhibit
		-----------------------------"

		::= { ilaEdfaPlusConfigurationEntry 156 }

	ilaEdfaPlusPump1LowTemperatureAlarmInhibit OBJECT-TYPE
		SYNTAX  	INTEGER
		MAX-ACCESS  	read-write
		STATUS  	current

		DESCRIPTION
		 " to set/get ILA EDFA PLUS card pump 1 low temperature alarm inhibit status.
		-----------------------------
		Value:
		1 - Inhibit
		0 - Do Not Inhibit
		-----------------------------"

		::= { ilaEdfaPlusConfigurationEntry 157 }

	ilaEdfaPlusPump2LowTemperatureAlarmInhibit OBJECT-TYPE
		SYNTAX  	INTEGER
		MAX-ACCESS  	read-write
		STATUS  	current

		DESCRIPTION
		 " to set/get ILA EDFA PLUS card pump 2 low temperature alarm inhibit status.
		-----------------------------
		Value:
		1 - Inhibit
		0 - Do Not Inhibit
		-----------------------------"

		::= { ilaEdfaPlusConfigurationEntry 158 }

	ilaEdfaPlusPump1HighTemperatureWarningInhibit OBJECT-TYPE
		SYNTAX  	INTEGER
		MAX-ACCESS  	read-write
		STATUS  	current

		DESCRIPTION
		 " to set/get ILA EDFA PLUS card pump 1 high temperature warning inhibit status.
		-----------------------------
		Value:
		1 - Inhibit
		0 - Do Not Inhibit
		-----------------------------"

		::= { ilaEdfaPlusConfigurationEntry 159 }

	ilaEdfaPlusPump2HighTemperatureWarningInhibit OBJECT-TYPE
		SYNTAX  	INTEGER
		MAX-ACCESS  	read-write
		STATUS  	current

		DESCRIPTION
		 " to set/get ILA EDFA PLUS card pump 2 high temperature warning inhibit status.
		-----------------------------
		Value:
		1 - Inhibit
		0 - Do Not Inhibit
		-----------------------------"

		::= { ilaEdfaPlusConfigurationEntry 160 }

	ilaEdfaPlusPump1LowTemperatureWarningInhibit OBJECT-TYPE
		SYNTAX  	INTEGER
		MAX-ACCESS  	read-write
		STATUS  	current

		DESCRIPTION
		 " to set/get ILA EDFA PLUS card pump 1 low temperature warning inhibit status.
		-----------------------------
		Value:
		1 - Inhibit
		0 - Do Not Inhibit
		-----------------------------"

		::= { ilaEdfaPlusConfigurationEntry 161 }

	ilaEdfaPlusPump2LowTemperatureWarningInhibit OBJECT-TYPE
		SYNTAX  	INTEGER
		MAX-ACCESS  	read-write
		STATUS  	current

		DESCRIPTION
		 " to set/get ILA EDFA PLUS card pump 2 low temperature warning inhibit status.
		-----------------------------
		Value:
		1 - Inhibit
		0 - Do Not Inhibit
		-----------------------------"

		::= { ilaEdfaPlusConfigurationEntry 162 }

	ilaEdfaPlusPump1HighOperatingCurrentAlarmInhibit OBJECT-TYPE
		SYNTAX  	INTEGER
		MAX-ACCESS  	read-write
		STATUS  	current

		DESCRIPTION
		 " to set/get ILA EDFA PLUS card pump 1 high operating current alarm inhibit status.
		-----------------------------
		Value:
		1 - Inhibit
		0 - Do Not Inhibit
		-----------------------------"

		::= { ilaEdfaPlusConfigurationEntry 163 }

	ilaEdfaPlusPump2HighOperatingCurrentAlarmInhibit OBJECT-TYPE
		SYNTAX  	INTEGER
		MAX-ACCESS  	read-write
		STATUS  	current

		DESCRIPTION
		 " to set/get ILA EDFA PLUS card pump 2 high operating current alarm inhibit status.
		-----------------------------
		Value:
		1 - Inhibit
		0 - Do Not Inhibit
		-----------------------------"

		::= { ilaEdfaPlusConfigurationEntry 164 }

	ilaEdfaPlusPump1LowOperatingCurrentAlarmInhibit OBJECT-TYPE
		SYNTAX  	INTEGER
		MAX-ACCESS  	read-write
		STATUS  	current

		DESCRIPTION
		 " to set/get ILA EDFA PLUS card pump 1 low operating current alarm inhibit status.
		-----------------------------
		Value:
		1 - Inhibit
		0 - Do Not Inhibit
		-----------------------------"

		::= { ilaEdfaPlusConfigurationEntry 165 }

	ilaEdfaPlusPump2LowOperatingCurrentAlarmInhibit OBJECT-TYPE
		SYNTAX  	INTEGER
		MAX-ACCESS  	read-write
		STATUS  	current

		DESCRIPTION
		 " to set/get ILA EDFA PLUS card pump 2 low operating current alarm inhibit status.
		-----------------------------
		Value:
		1 - Inhibit
		0 - Do Not Inhibit
		-----------------------------"

		::= { ilaEdfaPlusConfigurationEntry 166 }

	ilaEdfaPlusPump1HighOperatingCurrentWarningInhibit OBJECT-TYPE
		SYNTAX  	INTEGER
		MAX-ACCESS  	read-write
		STATUS  	current

		DESCRIPTION
		 " to set/get ILA EDFA PLUS card pump 1 high operating current warning inhibit status.
		-----------------------------
		Value:
		1 - Inhibit
		0 - Do Not Inhibit
		-----------------------------"

		::= { ilaEdfaPlusConfigurationEntry 167 }

	ilaEdfaPlusPump2HighOperatingCurrentWarningInhibit OBJECT-TYPE
		SYNTAX  	INTEGER
		MAX-ACCESS  	read-write
		STATUS  	current

		DESCRIPTION
		 " to set/get ILA EDFA PLUS card pump 2 high operating current warning inhibit status.
		-----------------------------
		Value:
		1 - Inhibit
		0 - Do Not Inhibit
		-----------------------------"

		::= { ilaEdfaPlusConfigurationEntry 168 }

	ilaEdfaPlusPump1LowOperatingCurrentWarningInhibit OBJECT-TYPE
		SYNTAX  	INTEGER
		MAX-ACCESS  	read-write
		STATUS  	current

		DESCRIPTION
		 " to set/get ILA EDFA PLUS card pump 1 low operating current warning inhibit status.
		-----------------------------
		Value:
		1 - Inhibit
		0 - Do Not Inhibit
		-----------------------------"

		::= { ilaEdfaPlusConfigurationEntry 169 }

	ilaEdfaPlusPump2LowOperatingCurrentWarningInhibit OBJECT-TYPE
		SYNTAX  	INTEGER
		MAX-ACCESS  	read-write
		STATUS  	current

		DESCRIPTION
		 " to set/get ILA EDFA PLUS card pump 2 low operating current warning inhibit status.
		-----------------------------
		Value:
		1 - Inhibit
		0 - Do Not Inhibit
		-----------------------------"

		::= { ilaEdfaPlusConfigurationEntry 170 }

	ilaEdfaPlusPump1HighThermoElectricCoolerCurrentAlarmInhibit OBJECT-TYPE
		SYNTAX  	INTEGER
		MAX-ACCESS  	read-write
		STATUS  	current

		DESCRIPTION
		 " to set/get ILA EDFA PLUS card pump 1 high thermo electric cooler current alarm inhibit status.
		-----------------------------
		Value:
		1 - Inhibit
		0 - Do Not Inhibit
		-----------------------------"

		::= { ilaEdfaPlusConfigurationEntry 171 }

	ilaEdfaPlusPump2HighThermoElectricCoolerCurrentAlarmInhibit OBJECT-TYPE
		SYNTAX  	INTEGER
		MAX-ACCESS  	read-write
		STATUS  	current

		DESCRIPTION
		 " to set/get ILA EDFA PLUS card pump 2 high thermo electric cooler current alarm inhibit status.
		-----------------------------
		Value:
		1 - Inhibit
		0 - Do Not Inhibit
		-----------------------------"

		::= { ilaEdfaPlusConfigurationEntry 172 }


	ilaEdfaPlusPump1LowThermoElectricCoolerCurrentAlarmInhibit OBJECT-TYPE
		SYNTAX  	INTEGER
		MAX-ACCESS  	read-write
		STATUS  	current

		DESCRIPTION
		 " to set/get ILA EDFA PLUS card pump 1 low thermo electric cooler current alarm inhibit status.
		-----------------------------
		Value:
		1 - Inhibit
		0 - Do Not Inhibit
		-----------------------------"

		::= { ilaEdfaPlusConfigurationEntry 173 }

	ilaEdfaPlusPump2LowThermoElectricCoolerCurrentAlarmInhibit OBJECT-TYPE
		SYNTAX  	INTEGER
		MAX-ACCESS  	read-write
		STATUS  	current

		DESCRIPTION
		 " to set/get ILA EDFA PLUS card pump 2 low thermo electric cooler current alarm inhibit status.
		-----------------------------
		Value:
		1 - Inhibit
		0 - Do Not Inhibit
		-----------------------------"

		::= { ilaEdfaPlusConfigurationEntry 174 }

	ilaEdfaPlusPump1HighThermoElectricCoolerCurrentWarningInhibit OBJECT-TYPE
		SYNTAX  	INTEGER
		MAX-ACCESS  	read-write
		STATUS  	current

		DESCRIPTION
		 " to set/get ILA EDFA PLUS card pump 1 high thermo electric cooler current warning inhibit status.
		-----------------------------
		Value:
		1 - Inhibit
		0 - Do Not Inhibit
		-----------------------------"

		::= { ilaEdfaPlusConfigurationEntry 175 }

	ilaEdfaPlusPump2HighThermoElectricCoolerCurrentWarningInhibit OBJECT-TYPE
		SYNTAX  	INTEGER
		MAX-ACCESS  	read-write
		STATUS  	current

		DESCRIPTION
		 " to set/get ILA EDFA PLUS card pump 2 high thermo electric cooler current warning inhibit status.
		-----------------------------
		Value:
		1 - Inhibit
		0 - Do Not Inhibit
		-----------------------------"

		::= { ilaEdfaPlusConfigurationEntry 176 }

	ilaEdfaPlusPump1LowThermoElectricCoolerCurrentWarningInhibit OBJECT-TYPE
		SYNTAX  	INTEGER
		MAX-ACCESS  	read-write
		STATUS  	current

		DESCRIPTION
		 " to set/get ILA EDFA PLUS card pump 1 low thermo electric cooler current warning inhibit status.
		-----------------------------
		Value:
		1 - Inhibit
		0 - Do Not Inhibit
		-----------------------------"

		::= { ilaEdfaPlusConfigurationEntry 177 } 

	ilaEdfaPlusPump2LowThermoElectricCoolerCurrentWarningInhibit OBJECT-TYPE
		SYNTAX  	INTEGER
		MAX-ACCESS  	read-write
		STATUS  	current

		DESCRIPTION
		 " to set/get ILA EDFA PLUS card pump 2 low thermo electric cooler current warning inhibit status.
		-----------------------------
		Value:
		1 - Inhibit
		0 - Do Not Inhibit
		-----------------------------"

		::= { ilaEdfaPlusConfigurationEntry 178 } 
                               	
	ilaEdfaPlusVariableOpticalAttenuatorHighInputPowerAlarmInhibit OBJECT-TYPE
		SYNTAX  	INTEGER
		MAX-ACCESS  	read-write
		STATUS  	current

		DESCRIPTION
		 " to set/get ILA EDFA PLUS card variable optical attenuator high input power alarm inhibit status.
		-----------------------------
		Value:
		1 - Inhibit
		0 - Do Not Inhibit
		-----------------------------"

		::= { ilaEdfaPlusConfigurationEntry 179 }

	ilaEdfaPlusVariableOpticalAttenuatorLowInputPowerAlarmInhibit OBJECT-TYPE
		SYNTAX  	INTEGER
		MAX-ACCESS  	read-write
		STATUS  	current

		DESCRIPTION
		 " to set/get ILA EDFA PLUS card variable optical attenuator low input power alarm inhibit status.
		-----------------------------
		Value:
		1 - Inhibit
		0 - Do Not Inhibit
		-----------------------------"

		::= { ilaEdfaPlusConfigurationEntry 180 }

	ilaEdfaPlusVariableOpticalAttenuatorHighInputPowerWarningInhibit OBJECT-TYPE
		SYNTAX  	INTEGER
		MAX-ACCESS  	read-write
		STATUS  	current

		DESCRIPTION
		 " to set/get ILA EDFA PLUS card variable optical attenuator high input power warning inhibit status.
		-----------------------------
		Value:
		1 - Inhibit
		0 - Do Not Inhibit
		-----------------------------"

		::= { ilaEdfaPlusConfigurationEntry 181 }

	ilaEdfaPlusVariableOpticalAttenuatorLowInputPowerWarningInhibit OBJECT-TYPE
		SYNTAX  	INTEGER
		MAX-ACCESS  	read-write
		STATUS  	current

		DESCRIPTION
		 " to set/get ILA EDFA PLUS card variable optical attenuator low input power warning inhibit status.
		-----------------------------
		Value:
		1 - Inhibit
		0 - Do Not Inhibit
		-----------------------------"

		::= { ilaEdfaPlusConfigurationEntry 182 }

	ilaEdfaPlusInputOutOfRangeAlarmInhibit OBJECT-TYPE
		SYNTAX  	INTEGER
		MAX-ACCESS  	read-write
		STATUS  	current

		DESCRIPTION
		 " to set/get ILA EDFA PLUS card Input Out Of Range Alarm Inhibit status.
		-----------------------------
		Value:
		1 - Inhibit
		0 - Do Not Inhibit
		-----------------------------"

		::= { ilaEdfaPlusConfigurationEntry 183 }

	ilaEdfaPlusOutputOutOfRangeAlarmInhibit OBJECT-TYPE
		SYNTAX  	INTEGER
		MAX-ACCESS  	read-write
		STATUS  	current

		DESCRIPTION
		 " to set/get ILA EDFA PLUS card Output Out Of Range Alarm Inhibit status.
		-----------------------------
		Value:
		1 - Inhibit
		0 - Do Not Inhibit
		-----------------------------"

		::= { ilaEdfaPlusConfigurationEntry 184 }

	ilaEdfaPlusPumpBiasCurrentAlarmInhibit OBJECT-TYPE
		SYNTAX  	INTEGER
		MAX-ACCESS  	read-write
		STATUS  	current

		DESCRIPTION
		 " to set/get ILA EDFA PLUS card Pump Bias Current Alarm Inhibit status.
		-----------------------------
		Value:
		1 - Inhibit
		0 - Do Not Inhibit
		-----------------------------"

		::= { ilaEdfaPlusConfigurationEntry 185 }

	ilaEdfaPlusPump1CoolingTemperatureAlarmInhibit OBJECT-TYPE
		SYNTAX  	INTEGER
		MAX-ACCESS  	read-write
		STATUS  	current

		DESCRIPTION
		 " to set/get ILA EDFA PLUS card Pump 1 cooling temperature Alarm Inhibit status.
		-----------------------------
		Value:
		1 - Inhibit
		0 - Do Not Inhibit
		-----------------------------"

		::= { ilaEdfaPlusConfigurationEntry 186 }

	ilaEdfaPlusPump2CoolingTemperatureAlarmInhibit OBJECT-TYPE
		SYNTAX  	INTEGER
		MAX-ACCESS  	read-write
		STATUS  	current

		DESCRIPTION
		 " to set/get ILA EDFA PLUS card Pump 2 cooling temperature Alarm Inhibit status.
		-----------------------------
		Value:
		1 - Inhibit
		0 - Do Not Inhibit
		-----------------------------"

		::= { ilaEdfaPlusConfigurationEntry 187 }

	ilaEdfaPlusPump1LaserPowerAlarmInhibit OBJECT-TYPE
		SYNTAX  	INTEGER
		MAX-ACCESS  	read-write
		STATUS  	current

		DESCRIPTION
		 " to set/get ILA EDFA PLUS card Pump 1 laser power Alarm Inhibit status.
		-----------------------------
		Value:
		1 - Inhibit
		0 - Do Not Inhibit
		-----------------------------"

		::= { ilaEdfaPlusConfigurationEntry 188 }

	ilaEdfaPlusPump2LaserPowerAlarmInhibit OBJECT-TYPE
		SYNTAX  	INTEGER
		MAX-ACCESS  	read-write
		STATUS  	current

		DESCRIPTION
		 " to set/get ILA EDFA PLUS card Pump 2 laser power Alarm Inhibit status.
		-----------------------------
		Value:
		1 - Inhibit
		0 - Do Not Inhibit
		-----------------------------"

		::= { ilaEdfaPlusConfigurationEntry 189 }

	ilaEdfaPlusOpticalInputPowerFailureAlarmForStage1Severity OBJECT-TYPE
		SYNTAX  	DisplayString
		MAX-ACCESS  	read-write
		STATUS  	current

		DESCRIPTION
		 " to set/get ILA EDFA PLUS card optical input power failure alarm severity level for stage 1.
		-----------------------------
		Value:
		critical
		major
		minor
		deferred
		---------------------------"

		::= { ilaEdfaPlusConfigurationEntry 221 }	                                              

	ilaEdfaPlusOpticalInputPowerFailureAlarmForStage2Severity OBJECT-TYPE
		SYNTAX  	DisplayString
		MAX-ACCESS  	read-write
		STATUS  	current

		DESCRIPTION
		 " to set/get ILA EDFA PLUS card optical input power failure alarm severity level for stage 2.
		-----------------------------
		Value:
		critical
		major
		minor
		deferred
		---------------------------"

		::= { ilaEdfaPlusConfigurationEntry 222 }
                      
	ilaEdfaPlusOpticalHighInputPowerAlarmForStage1Severity OBJECT-TYPE
		SYNTAX  	DisplayString
		MAX-ACCESS  	read-write
		STATUS  	current

		DESCRIPTION
		 " to set/get ILA EDFA PLUS card optical high input power alarm severity level for stage 1.
		-----------------------------
		Value:
		critical
		major
		minor
		deferred
		---------------------------"

		::= { ilaEdfaPlusConfigurationEntry 223 }	              

	ilaEdfaPlusOpticalHighInputPowerAlarmForStage2Severity OBJECT-TYPE
		SYNTAX  	DisplayString
		MAX-ACCESS  	read-write
		STATUS  	current

		DESCRIPTION
		 " to set/get ILA EDFA PLUS card optical high input power alarm severity level for stage 2.
		-----------------------------
		Value:
		critical
		major
		minor
		deferred
		---------------------------"

		::= { ilaEdfaPlusConfigurationEntry 224 }
                      
	ilaEdfaPlusOpticalLowInputPowerAlarmForStage1Severity OBJECT-TYPE
		SYNTAX  	DisplayString
		MAX-ACCESS  	read-write
		STATUS  	current

		DESCRIPTION
		 " to set/get ILA EDFA PLUS card optical low input power alarm severity level for stage 1.
		-----------------------------
		Value:
		critical
		major
		minor
		deferred
		---------------------------"

		::= { ilaEdfaPlusConfigurationEntry 225 }	              

	ilaEdfaPlusOpticalLowInputPowerAlarmForStage2Severity OBJECT-TYPE
		SYNTAX  	DisplayString
		MAX-ACCESS  	read-write
		STATUS  	current

		DESCRIPTION
		 " to set/get ILA EDFA PLUS card optical low input power alarm severity level for stage 2.
		-----------------------------
		Value:
		critical
		major
		minor
		deferred
		---------------------------"

		::= { ilaEdfaPlusConfigurationEntry 226 }
                      
	ilaEdfaPlusOpticalHighInputPowerWarningForStage1Severity OBJECT-TYPE
		SYNTAX  	DisplayString
		MAX-ACCESS  	read-write
		STATUS  	current

		DESCRIPTION
		 " to set/get ILA EDFA PLUS card optical high input power warning severity level for stage 1.
		-----------------------------
		Value:
		critical
		major
		minor
		deferred
		---------------------------"

		::= { ilaEdfaPlusConfigurationEntry 227 }	              

	ilaEdfaPlusOpticalHighInputPowerWarningForStage2Severity OBJECT-TYPE
		SYNTAX  	DisplayString
		MAX-ACCESS  	read-write
		STATUS  	current

		DESCRIPTION
		 " to set/get ILA EDFA PLUS card optical high input power warning severity level for stage 2.
		-----------------------------
		Value:
		critical
		major
		minor
		deferred
		---------------------------"

		::= { ilaEdfaPlusConfigurationEntry 228 }
                      
	ilaEdfaPlusOpticalLowInputPowerWarningForStage1Severity OBJECT-TYPE
		SYNTAX  	DisplayString
		MAX-ACCESS  	read-write
		STATUS  	current

		DESCRIPTION
		 " to set/get ILA EDFA PLUS card optical low input power warning severity level for stage 1.
		-----------------------------
		Value:
		critical
		major
		minor
		deferred
		---------------------------"

		::= { ilaEdfaPlusConfigurationEntry 229 }              

	ilaEdfaPlusOpticalLowInputPowerWarningForStage2Severity OBJECT-TYPE
		SYNTAX  	DisplayString
		MAX-ACCESS  	read-write
		STATUS  	current

		DESCRIPTION
		 " to set/get ILA EDFA PLUS card optical low input power warning severity level for stage 2.
		-----------------------------
		Value:
		critical
		major
		minor
		deferred
		---------------------------"

		::= { ilaEdfaPlusConfigurationEntry 230 } 
                    
	ilaEdfaPlusOpticalOutputPowerFailureAlarmForStage1Severity OBJECT-TYPE
		SYNTAX  	DisplayString
		MAX-ACCESS  	read-write
		STATUS  	current

		DESCRIPTION
		 " to set/get ILA EDFA PLUS card optical output power failure alarm severity level for stage 1.
		-----------------------------
		Value:
		critical
		major
		minor
		deferred
		---------------------------"

		::= { ilaEdfaPlusConfigurationEntry 231 }

	ilaEdfaPlusOpticalOutputPowerFailureAlarmForStage2Severity OBJECT-TYPE
		SYNTAX  	DisplayString
		MAX-ACCESS  	read-write
		STATUS  	current

		DESCRIPTION
		 " to set/get ILA EDFA PLUS card optical output power failure alarm severity level for stage 2.
		-----------------------------
		Value:
		critical
		major
		minor
		deferred
		---------------------------"

		::= { ilaEdfaPlusConfigurationEntry 232 }


	ilaEdfaPlusOpticalHighOutputPowerAlarmForStage1Severity OBJECT-TYPE
		SYNTAX  	DisplayString
		MAX-ACCESS  	read-write
		STATUS  	current

		DESCRIPTION
		 " to set/get ILA EDFA PLUS card optical high output power alarm severity level for stage 1.
		-----------------------------
		Value:
		critical
		major
		minor
		deferred
		---------------------------"

		::= { ilaEdfaPlusConfigurationEntry 233 }

	ilaEdfaPlusOpticalHighOutputPowerAlarmForStage2Severity OBJECT-TYPE
		SYNTAX  	DisplayString
		MAX-ACCESS  	read-write
		STATUS  	current

		DESCRIPTION
		 " to set/get ILA EDFA PLUS card optical high output power alarm severity level for stage 2.
		-----------------------------
		Value:
		critical
		major
		minor
		deferred
		---------------------------"

		::= { ilaEdfaPlusConfigurationEntry 234 }

	ilaEdfaPlusOpticalLowOutputPowerAlarmForStage1Severity OBJECT-TYPE
		SYNTAX  	DisplayString
		MAX-ACCESS  	read-write
		STATUS  	current

		DESCRIPTION
		 " to set/get ILA EDFA PLUS card optical low output power alarm severity level for stage 1.
		-----------------------------
		Value:
		critical
		major
		minor
		deferred
		---------------------------"

		::= { ilaEdfaPlusConfigurationEntry 235 }

	ilaEdfaPlusOpticalLowOutputPowerAlarmForStage2Severity OBJECT-TYPE
		SYNTAX  	DisplayString
		MAX-ACCESS  	read-write
		STATUS  	current

		DESCRIPTION
		 " to set/get ILA EDFA PLUS card optical low output power alarm severity level for stage 2.
		-----------------------------
		Value:
		critical
		major
		minor
		deferred
		---------------------------"

		::= { ilaEdfaPlusConfigurationEntry 236 }

	ilaEdfaPlusOpticalHighOutputPowerWarningForStage1Severity OBJECT-TYPE
		SYNTAX  	DisplayString
		MAX-ACCESS  	read-write
		STATUS  	current

		DESCRIPTION
		 " to set/get ILA EDFA PLUS card optical high output power warning severity level for stage 1.
		-----------------------------
		Value:
		critical
		major
		minor
		deferred
		---------------------------"

		::= { ilaEdfaPlusConfigurationEntry 237 }

	ilaEdfaPlusOpticalHighOutputPowerWarningForStage2Severity OBJECT-TYPE
		SYNTAX  	DisplayString
		MAX-ACCESS  	read-write
		STATUS  	current

		DESCRIPTION
		 " to set/get ILA EDFA PLUS card optical high output power warning severity level for stage 2.
		-----------------------------
		Value:
		critical
		major
		minor
		deferred
		---------------------------"

		::= { ilaEdfaPlusConfigurationEntry 238 }

	ilaEdfaPlusOpticalLowOutputPowerWarningForStage1Severity OBJECT-TYPE
		SYNTAX  	DisplayString
		MAX-ACCESS  	read-write
		STATUS  	current

		DESCRIPTION
		 " to set/get ILA EDFA PLUS card optical low output power warning severity level for stage 1.
		-----------------------------
		Value:
		critical
		major
		minor
		deferred
		---------------------------"

		::= { ilaEdfaPlusConfigurationEntry 239 }

	ilaEdfaPlusOpticalLowOutputPowerWarningForStage2Severity OBJECT-TYPE
		SYNTAX  	DisplayString
		MAX-ACCESS  	read-write
		STATUS  	current

		DESCRIPTION
		 " to set/get ILA EDFA PLUS card optical low output power warning severity level for stage 2.
		-----------------------------
		Value:
		critical
		major
		minor
		deferred
		---------------------------"

		::= { ilaEdfaPlusConfigurationEntry 240 }

	ilaEdfaPlusModuleHighTemperatureAlarmSeverity OBJECT-TYPE
		SYNTAX  	DisplayString
		MAX-ACCESS  	read-write
		STATUS  	current

		DESCRIPTION
		 " to set/get ILA EDFA PLUS card module high temperature alarm severity level.
		-----------------------------
		Value:
		critical
		major
		minor
		deferred
		---------------------------"

		::= { ilaEdfaPlusConfigurationEntry 241 }

	ilaEdfaPlusModuleLowTemperatureAlarmSeverity OBJECT-TYPE
		SYNTAX  	DisplayString
		MAX-ACCESS  	read-write
		STATUS  	current

		DESCRIPTION
		 " to set/get ILA EDFA PLUS card module low temperature alarm severity level.
		-----------------------------
		Value:
		critical
		major
		minor
		deferred
		---------------------------"

		::= { ilaEdfaPlusConfigurationEntry 242 }

	ilaEdfaPlusModuleHighTemperatureWarningSeverity OBJECT-TYPE
		SYNTAX  	DisplayString
		MAX-ACCESS  	read-write
		STATUS  	current

		DESCRIPTION
		 " to set/get ILA EDFA PLUS card module high temperature warning severity level.
		-----------------------------
		Value:
		critical
		major
		minor
		deferred
		---------------------------"

		::= { ilaEdfaPlusConfigurationEntry 243 }

	ilaEdfaPlusModuleLowTemperatureWarningSeverity OBJECT-TYPE
		SYNTAX  	DisplayString
		MAX-ACCESS  	read-write
		STATUS  	current

		DESCRIPTION
		 " to set/get ILA EDFA PLUS card module low temperature warning severity level.
		-----------------------------
		Value:
		critical
		major
		minor
		deferred
		---------------------------"

		::= { ilaEdfaPlusConfigurationEntry 244 }

	ilaEdfaPlusPump1HighTemperatureAlarmSeverity OBJECT-TYPE
		SYNTAX  	DisplayString
		MAX-ACCESS  	read-write
		STATUS  	current

		DESCRIPTION
		 " to set/get ILA EDFA PLUS card pump 1 high temperature alarm severity level.
		-----------------------------
		Value:
		critical
		major
		minor
		deferred
		---------------------------"

		::= { ilaEdfaPlusConfigurationEntry 245 }

	ilaEdfaPlusPump2HighTemperatureAlarmSeverity OBJECT-TYPE
		SYNTAX  	DisplayString
		MAX-ACCESS  	read-write
		STATUS  	current

		DESCRIPTION
		 " to set/get ILA EDFA PLUS card pump 2 high temperature alarm severity level.
		-----------------------------
		Value:
		critical
		major
		minor
		deferred
		---------------------------"

		::= { ilaEdfaPlusConfigurationEntry 246 }

	ilaEdfaPlusPump1LowTemperatureAlarmSeverity OBJECT-TYPE
		SYNTAX  	DisplayString
		MAX-ACCESS  	read-write
		STATUS  	current

		DESCRIPTION
		 " to set/get ILA EDFA PLUS card pump 1 low temperature alarm severity level.
		-----------------------------
		Value:
		critical
		major
		minor
		deferred
		---------------------------"

		::= { ilaEdfaPlusConfigurationEntry 247 }

	ilaEdfaPlusPump2LowTemperatureAlarmSeverity OBJECT-TYPE
		SYNTAX  	DisplayString
		MAX-ACCESS  	read-write
		STATUS  	current

		DESCRIPTION
		 " to set/get ILA EDFA PLUS card pump 2 low temperature alarm severity level.
		-----------------------------
		Value:
		critical
		major
		minor
		deferred
		---------------------------"

		::= { ilaEdfaPlusConfigurationEntry 248 }

	ilaEdfaPlusPump1HighTemperatureWarningSeverity OBJECT-TYPE
		SYNTAX  	DisplayString
		MAX-ACCESS  	read-write
		STATUS  	current

		DESCRIPTION
		 " to set/get ILA EDFA PLUS card pump 1 high temperature warning severity level.
		-----------------------------
		Value:
		critical
		major
		minor
		deferred
		---------------------------"

		::= { ilaEdfaPlusConfigurationEntry 249 }

	ilaEdfaPlusPump2HighTemperatureWarningSeverity OBJECT-TYPE
		SYNTAX  	DisplayString
		MAX-ACCESS  	read-write
		STATUS  	current

		DESCRIPTION
		 " to set/get ILA EDFA PLUS card pump 2 high temperature warning severity level.
		-----------------------------
		Value:
		critical
		major
		minor
		deferred
		---------------------------"

		::= { ilaEdfaPlusConfigurationEntry 250 }

	ilaEdfaPlusPump1LowTemperatureWarningSeverity OBJECT-TYPE
		SYNTAX  	DisplayString
		MAX-ACCESS  	read-write
		STATUS  	current

		DESCRIPTION
		 " to set/get ILA EDFA PLUS card pump 1 low temperature warning severity level.
		-----------------------------
		Value:
		critical
		major
		minor
		deferred
		---------------------------"

		::= { ilaEdfaPlusConfigurationEntry 251 }

	ilaEdfaPlusPump2LowTemperatureWarningSeverity OBJECT-TYPE
		SYNTAX  	DisplayString
		MAX-ACCESS  	read-write
		STATUS  	current

		DESCRIPTION
		 " to set/get ILA EDFA PLUS card pump 2 low temperature warning severity level.
		-----------------------------
		Value:
		critical
		major
		minor
		deferred
		---------------------------"

		::= { ilaEdfaPlusConfigurationEntry 252 }

	ilaEdfaPlusPump1HighOperatingCurrentAlarmSeverity OBJECT-TYPE
		SYNTAX  	DisplayString
		MAX-ACCESS  	read-write
		STATUS  	current

		DESCRIPTION
		 " to set/get ILA EDFA PLUS card pump 1 high operating current alarm severity level.
		-----------------------------
		Value:
		critical
		major
		minor
		deferred
		---------------------------"

		::= { ilaEdfaPlusConfigurationEntry 253 }

	ilaEdfaPlusPump2HighOperatingCurrentAlarmSeverity OBJECT-TYPE
		SYNTAX  	DisplayString
		MAX-ACCESS  	read-write
		STATUS  	current

		DESCRIPTION
		 " to set/get ILA EDFA PLUS card pump 2 high operating current alarm severity level.
		-----------------------------
		Value:
		critical
		major
		minor
		deferred
		---------------------------"

		::= { ilaEdfaPlusConfigurationEntry 254 }

	ilaEdfaPlusPump1LowOperatingCurrentAlarmSeverity OBJECT-TYPE
		SYNTAX  	DisplayString
		MAX-ACCESS  	read-write
		STATUS  	current

		DESCRIPTION
		 " to set/get ILA EDFA PLUS card pump 1 low operating current alarm severity level.
		-----------------------------
		Value:
		critical
		major
		minor
		deferred
		---------------------------"

		::= { ilaEdfaPlusConfigurationEntry 255 }

	ilaEdfaPlusPump2LowOperatingCurrentAlarmSeverity OBJECT-TYPE
		SYNTAX  	DisplayString
		MAX-ACCESS  	read-write
		STATUS  	current

		DESCRIPTION
		 " to set/get ILA EDFA PLUS card pump 2 low operating current alarm severity level.
		-----------------------------
		Value:
		critical
		major
		minor
		deferred
		---------------------------"

		::= { ilaEdfaPlusConfigurationEntry 256 }

	ilaEdfaPlusPump1HighOperatingCurrentWarningSeverity OBJECT-TYPE
		SYNTAX  	DisplayString
		MAX-ACCESS  	read-write
		STATUS  	current

		DESCRIPTION
		 " to set/get ILA EDFA PLUS card pump 1 high operating current warning severity level.
		-----------------------------
		Value:
		critical
		major
		minor
		deferred
		---------------------------"

		::= { ilaEdfaPlusConfigurationEntry 257 }

	ilaEdfaPlusPump2HighOperatingCurrentWarningSeverity OBJECT-TYPE
		SYNTAX  	DisplayString
		MAX-ACCESS  	read-write
		STATUS  	current

		DESCRIPTION
		 " to set/get ILA EDFA PLUS card pump 2 high operating current warning severity level.
		-----------------------------
		Value:
		critical
		major
		minor
		deferred
		---------------------------"

		::= { ilaEdfaPlusConfigurationEntry 258 }

	ilaEdfaPlusPump1LowOperatingCurrentWarningSeverity OBJECT-TYPE
		SYNTAX  	DisplayString
		MAX-ACCESS  	read-write
		STATUS  	current

		DESCRIPTION
		 " to set/get ILA EDFA PLUS card pump 1 low operating current warning severity level.
		-----------------------------
		Value:
		critical
		major
		minor
		deferred
		---------------------------"

		::= { ilaEdfaPlusConfigurationEntry 259 }

	ilaEdfaPlusPump2LowOperatingCurrentWarningSeverity OBJECT-TYPE
		SYNTAX  	DisplayString
		MAX-ACCESS  	read-write
		STATUS  	current

		DESCRIPTION
		 " to set/get ILA EDFA PLUS card pump 2 low operating current warning severity level.
		-----------------------------
		Value:
		critical
		major
		minor
		deferred
		---------------------------"

		::= { ilaEdfaPlusConfigurationEntry 260 }

	ilaEdfaPlusPump1HighThermoElectricCoolerCurrentAlarmSeverity OBJECT-TYPE
		SYNTAX  	DisplayString
		MAX-ACCESS  	read-write
		STATUS  	current

		DESCRIPTION
		 " to set/get ILA EDFA PLUS card pump 1 high thermo electric cooler current alarm severity level.
		-----------------------------
		Value:
		critical
		major
		minor
		deferred
		---------------------------"

		::= { ilaEdfaPlusConfigurationEntry 261 }

	ilaEdfaPlusPump2HighThermoElectricCoolerCurrentAlarmSeverity OBJECT-TYPE
		SYNTAX  	DisplayString
		MAX-ACCESS  	read-write
		STATUS  	current

		DESCRIPTION
		 " to set/get ILA EDFA PLUS card pump 2 high thermo electric cooler current alarm severity level.
		-----------------------------
		Value:
		critical
		major
		minor
		deferred
		---------------------------"

		::= { ilaEdfaPlusConfigurationEntry 262 }


	ilaEdfaPlusPump1LowThermoElectricCoolerCurrentAlarmSeverity OBJECT-TYPE
		SYNTAX  	DisplayString
		MAX-ACCESS  	read-write
		STATUS  	current

		DESCRIPTION
		 " to set/get ILA EDFA PLUS card pump 1 low thermo electric cooler current alarm severity level.
		-----------------------------
		Value:
		critical
		major
		minor
		deferred
		---------------------------"

		::= { ilaEdfaPlusConfigurationEntry 263 }

	ilaEdfaPlusPump2LowThermoElectricCoolerCurrentAlarmSeverity OBJECT-TYPE
		SYNTAX  	DisplayString
		MAX-ACCESS  	read-write
		STATUS  	current

		DESCRIPTION
		 " to set/get ILA EDFA PLUS card pump 2 low thermo electric cooler current alarm severity level.
		-----------------------------
		Value:
		critical
		major
		minor
		deferred
		---------------------------"

		::= { ilaEdfaPlusConfigurationEntry 264 }

	ilaEdfaPlusPump1HighThermoElectricCoolerCurrentWarningSeverity OBJECT-TYPE
		SYNTAX  	DisplayString
		MAX-ACCESS  	read-write
		STATUS  	current

		DESCRIPTION
		 " to set/get ILA EDFA PLUS card pump 1 high thermo electric cooler current warning severity level.
		-----------------------------
		Value:
		critical
		major
		minor
		deferred
		---------------------------"

		::= { ilaEdfaPlusConfigurationEntry 265 }

	ilaEdfaPlusPump2HighThermoElectricCoolerCurrentWarningSeverity OBJECT-TYPE
		SYNTAX  	DisplayString
		MAX-ACCESS  	read-write
		STATUS  	current

		DESCRIPTION
		 " to set/get ILA EDFA PLUS card pump 2 high thermo electric cooler current warning severity level.
		-----------------------------
		Value:
		critical
		major
		minor
		deferred
		---------------------------"

		::= { ilaEdfaPlusConfigurationEntry 266 }

	ilaEdfaPlusPump1LowThermoElectricCoolerCurrentWarningSeverity OBJECT-TYPE
		SYNTAX  	DisplayString
		MAX-ACCESS  	read-write
		STATUS  	current

		DESCRIPTION
		 " to set/get ILA EDFA PLUS card pump 1 low thermo electric cooler current warning severity level.
		-----------------------------
		Value:
		critical
		major
		minor
		deferred
		---------------------------"

		::= { ilaEdfaPlusConfigurationEntry 267 } 

	ilaEdfaPlusPump2LowThermoElectricCoolerCurrentWarningSeverity OBJECT-TYPE
		SYNTAX  	DisplayString
		MAX-ACCESS  	read-write
		STATUS  	current

		DESCRIPTION
		 " to set/get ILA EDFA PLUS card pump 2 low thermo electric cooler current warning severity level.
		-----------------------------
		Value:
		critical
		major
		minor
		deferred
		---------------------------"

		::= { ilaEdfaPlusConfigurationEntry 268 } 
                               	
	ilaEdfaPlusVariableOpticalAttenuatorHighInputPowerAlarmSeverity OBJECT-TYPE
		SYNTAX  	DisplayString
		MAX-ACCESS  	read-write
		STATUS  	current

		DESCRIPTION
		 " to set/get ILA EDFA PLUS card variable optical attenuator high input power alarm severity level.
		-----------------------------
		Value:
		critical
		major
		minor
		deferred
		---------------------------"

		::= { ilaEdfaPlusConfigurationEntry 269 }

	ilaEdfaPlusVariableOpticalAttenuatorLowInputPowerAlarmSeverity OBJECT-TYPE
		SYNTAX  	DisplayString
		MAX-ACCESS  	read-write
		STATUS  	current

		DESCRIPTION
		 " to set/get ILA EDFA PLUS card variable optical attenuator low input power alarm severity level.
		-----------------------------
		Value:
		critical
		major
		minor
		deferred
		---------------------------"

		::= { ilaEdfaPlusConfigurationEntry 270 }

	ilaEdfaPlusVariableOpticalAttenuatorHighInputPowerWarningSeverity OBJECT-TYPE
		SYNTAX  	DisplayString
		MAX-ACCESS  	read-write
		STATUS  	current

		DESCRIPTION
		 " to set/get ILA EDFA PLUS card variable optical attenuator high input power warning severity level.
		-----------------------------
		Value:
		critical
		major
		minor
		deferred
		---------------------------"

		::= { ilaEdfaPlusConfigurationEntry 271 }

	ilaEdfaPlusVariableOpticalAttenuatorLowInputPowerWarningSeverity OBJECT-TYPE
		SYNTAX  	DisplayString
		MAX-ACCESS  	read-write
		STATUS  	current

		DESCRIPTION
		 " to set/get ILA EDFA PLUS card variable optical attenuator low input power warning severity level.
		-----------------------------
		Value:
		critical
		major
		minor
		deferred
		---------------------------"

		::= { ilaEdfaPlusConfigurationEntry 272 }

	ilaEdfaPlusInputOutOfRangeAlarmSeverity OBJECT-TYPE
		SYNTAX  	DisplayString
		MAX-ACCESS  	read-write
		STATUS  	current

		DESCRIPTION
		 " to set/get ILA EDFA PLUS card Input Out Of Range Alarm severity level.
		-----------------------------
		Value:
		critical
		major
		minor
		deferred
		---------------------------"

		::= { ilaEdfaPlusConfigurationEntry 273 }

	ilaEdfaPlusOutputOutOfRangeAlarmSeverity OBJECT-TYPE
		SYNTAX  	DisplayString
		MAX-ACCESS  	read-write
		STATUS  	current

		DESCRIPTION
		 " to set/get ILA EDFA PLUS card Output Out Of Range Alarm severity level.
		-----------------------------
		Value:
		critical
		major
		minor
		deferred
		---------------------------"

		::= { ilaEdfaPlusConfigurationEntry 274 }

	ilaEdfaPlusPumpBiasCurrentAlarmSeverity OBJECT-TYPE
		SYNTAX  	DisplayString
		MAX-ACCESS  	read-write
		STATUS  	current

		DESCRIPTION
		 " to set/get ILA EDFA PLUS card Pump Bias Current Alarm severity level.
		-----------------------------
		Value:
		critical
		major
		minor
		deferred
		---------------------------"

		::= { ilaEdfaPlusConfigurationEntry 275 }

	ilaEdfaPlusPump1CoolingTemperatureAlarmSeverity OBJECT-TYPE
		SYNTAX  	DisplayString
		MAX-ACCESS  	read-write
		STATUS  	current

		DESCRIPTION
		 " to set/get ILA EDFA PLUS card Pump 1 cooling temperature alarm severity level for stage 1.
		-----------------------------
		Value:
		critical
		major
		minor
		deferred
		---------------------------"

		::= { ilaEdfaPlusConfigurationEntry 276 }

	ilaEdfaPlusPump2CoolingTemperatureAlarmSeverity OBJECT-TYPE
		SYNTAX  	DisplayString
		MAX-ACCESS  	read-write
		STATUS  	current

		DESCRIPTION
		 " to set/get ILA EDFA PLUS card Pump 2 cooling temperature alarm severity level for stage 1.
		-----------------------------
		Value:
		critical
		major
		minor
		deferred
		---------------------------"

		::= { ilaEdfaPlusConfigurationEntry 277 }

	ilaEdfaPlusPump1LaserPowerAlarmSeverity OBJECT-TYPE
		SYNTAX  	DisplayString
		MAX-ACCESS  	read-write
		STATUS  	current

		DESCRIPTION
		 " to set/get ILA EDFA PLUS card Pump 1 laser power alarm severity level for stage 1.
		-----------------------------
		Value:
		critical
		major
		minor
		deferred
		---------------------------"

		::= { ilaEdfaPlusConfigurationEntry 278 }

	ilaEdfaPlusPump2LaserPowerAlarmSeverity OBJECT-TYPE
		SYNTAX  	DisplayString
		MAX-ACCESS  	read-write
		STATUS  	current

		DESCRIPTION
		 " to set/get ILA EDFA PLUS card Pump 2 laser power alarm severity level for stage 1.
		-----------------------------
		Value:
		critical
		major
		minor
		deferred
		---------------------------"

		::= { ilaEdfaPlusConfigurationEntry 279 }

	ilaEdfaPlusCardSoftwareUpgrade OBJECT-TYPE
		SYNTAX 		DisplayString
		MAX-ACCESS 	read-write
		STATUS 		current
		DESCRIPTION
			"Valid only as SET command.
			This property upgrades the software of the ILA-EDFA-PLUS card
			It takes the path of the software release as
			a value,
			ilaEdfaPlusInterface: 0
			Values:
			eg: /home/root/rel-2.0.0.tar.gz
			-----------------------------"

		::= { ilaEdfaPlusConfigurationEntry 280 }

	ilaEdfaPlusMidInOutOfRangeAlarmInhibit OBJECT-TYPE
		SYNTAX  	INTEGER
		MAX-ACCESS  	read-write
		STATUS  	current

		DESCRIPTION
		 " to set/get ILA EDFA PLUS card Mid Input Out Of Range Alarm Inhibit status.
		-----------------------------
		Value:
		1 - Inhibit
		0 - Do Not Inhibit
		-----------------------------"

		::= { ilaEdfaPlusConfigurationEntry 281 }

	ilaEdfaPlusMidOutOutOfRangeAlarmInhibit OBJECT-TYPE
		SYNTAX  	INTEGER
		MAX-ACCESS  	read-write
		STATUS  	current

		DESCRIPTION
		 " to set/get ILA EDFA PLUS card Mid Output Out Of Range Alarm Inhibit status.
		-----------------------------
		Value:
		1 - Inhibit
		0 - Do Not Inhibit
		-----------------------------"

		::= { ilaEdfaPlusConfigurationEntry 282 }

	ilaEdfaPlusMidInOutOfRangeAlarmSeverity OBJECT-TYPE
		SYNTAX  	DisplayString
		MAX-ACCESS  	read-write
		STATUS  	current

		DESCRIPTION
		 " to set/get ILA EDFA PLUS card Mid Input Out Of Range Alarm severity level.
		-----------------------------
		Value:
		critical
		major
		minor
		deferred
		---------------------------"

		::= { ilaEdfaPlusConfigurationEntry 283 }

	ilaEdfaPlusMidOutOutOfRangeAlarmSeverity OBJECT-TYPE
		SYNTAX  	DisplayString
		MAX-ACCESS  	read-write
		STATUS  	current

		DESCRIPTION
		 " to set/get ILA EDFA PLUS card Mid Output Out Of Range Alarm severity level.
		-----------------------------
		Value:
		critical
		major
		minor
		deferred
		---------------------------"

		::= { ilaEdfaPlusConfigurationEntry 284 }

	ilaEdfaPlusConfigurationTableRowStatus OBJECT-TYPE
              SYNTAX      RowStatus
              MAX-ACCESS  read-write
              STATUS      current
              DESCRIPTION
                      "	This is MIB realted property,
			NOT to be considered as a card property"
              ::= { ilaEdfaPlusConfigurationEntry 285 }

--*****************************************************************************
--				ILA EDFA PLUS ALARMS
--*****************************************************************************         
              
	ilaEdfaPlusAlarmQueryTable OBJECT-TYPE
		SYNTAX  	SEQUENCE OF IlaEdfaPlusAlarmQueryEntry
		MAX-ACCESS  	not-accessible
		STATUS  	current

		DESCRIPTION
		 "we can get ILA EDFA PLUS card alarm details"

		::= { ilaEdfaPlusAlarmQuery 1 }
	      
	ilaEdfaPlusAlarmQueryEntry OBJECT-TYPE
		SYNTAX  	IlaEdfaPlusAlarmQueryEntry
		MAX-ACCESS  	not-accessible
		STATUS  	current

		DESCRIPTION 
		 "Enter node rack, subrack, slot and ilaEdfaPlusInterface numbers"

		INDEX   { node, rack, subRack, slot, ilaEdfaPlusInterface }

		::= { ilaEdfaPlusAlarmQueryTable 1 }

	IlaEdfaPlusAlarmQueryEntry ::= 
		SEQUENCE {
				ilaEdfaPlusOpticalInputPowerFailureAlarmForStage1 		DisplayString,
				ilaEdfaPlusOpticalInputPowerFailureAlarmForStage2 		DisplayString,
				ilaEdfaPlusOpticalHighInputPowerAlarmForStage1			DisplayString,
				ilaEdfaPlusOpticalHighInputPowerAlarmForStage2			DisplayString,
				ilaEdfaPlusOpticalLowInputPowerAlarmForStage1	 		DisplayString,
				ilaEdfaPlusOpticalLowInputPowerAlarmForStage2	 		DisplayString,
				ilaEdfaPlusOpticalHighInputPowerWarningForStage1	 	DisplayString,
				ilaEdfaPlusOpticalHighInputPowerWarningForStage2	 	DisplayString,
				ilaEdfaPlusOpticalLowInputPowerWarningForStage1 		DisplayString,
				ilaEdfaPlusOpticalLowInputPowerWarningForStage2 		DisplayString,
				ilaEdfaPlusOpticalOutputPowerFailureAlarmForStage1		DisplayString,
				ilaEdfaPlusOpticalOutputPowerFailureAlarmForStage2		DisplayString,
				ilaEdfaPlusOpticalHighOutputPowerAlarmForStage1			DisplayString,
				ilaEdfaPlusOpticalHighOutputPowerAlarmForStage2			DisplayString,
				ilaEdfaPlusOpticalLowOutputPowerAlarmForStage1			DisplayString,
				ilaEdfaPlusOpticalLowOutputPowerAlarmForStage2			DisplayString,
				ilaEdfaPlusOpticalHighOutputPowerWarningForStage1		DisplayString,
				ilaEdfaPlusOpticalHighOutputPowerWarningForStage2		DisplayString,
				ilaEdfaPlusOpticalLowOutputPowerWarningForStage1		DisplayString,
				ilaEdfaPlusOpticalLowOutputPowerWarningForStage2		DisplayString,
				ilaEdfaPlusModuleHighTemperatureAlarm				DisplayString,
				ilaEdfaPlusModuleLowTemperatureAlarm				DisplayString,
				ilaEdfaPlusModuleHighTemperatureWarning				DisplayString,
				ilaEdfaPlusModuleLowTemperatureWarning				DisplayString,
				ilaEdfaPlusPump1HighTemperatureAlarm				DisplayString,
				ilaEdfaPlusPump2HighTemperatureAlarm				DisplayString,
				ilaEdfaPlusPump1LowTemperatureAlarm				DisplayString,
				ilaEdfaPlusPump2LowTemperatureAlarm				DisplayString,
				ilaEdfaPlusPump1HighTemperatureWarning				DisplayString,
				ilaEdfaPlusPump2HighTemperatureWarning				DisplayString,
				ilaEdfaPlusPump1LowTemperatureWarning				DisplayString,
				ilaEdfaPlusPump2LowTemperatureWarning				DisplayString,
				ilaEdfaPlusPump1HighOperatingCurrentAlarm			DisplayString,
				ilaEdfaPlusPump2HighOperatingCurrentAlarm			DisplayString,
				ilaEdfaPlusPump1LowOperatingCurrentAlarm			DisplayString,
				ilaEdfaPlusPump2LowOperatingCurrentAlarm			DisplayString,
				ilaEdfaPlusPump1HighOperatingCurrentWarning			DisplayString,
				ilaEdfaPlusPump2HighOperatingCurrentWarning			DisplayString,
				ilaEdfaPlusPump1LowOperatingCurrentWarning			DisplayString,
				ilaEdfaPlusPump2LowOperatingCurrentWarning			DisplayString,
				ilaEdfaPlusPump1HighThermoElectricCoolerCurrentAlarm		DisplayString,
				ilaEdfaPlusPump2HighThermoElectricCoolerCurrentAlarm		DisplayString,
				ilaEdfaPlusPump1LowThermoElectricCoolerCurrentAlarm		DisplayString,
				ilaEdfaPlusPump2LowThermoElectricCoolerCurrentAlarm		DisplayString,
				ilaEdfaPlusPump1HighThermoElectricCoolerCurrentWarning		DisplayString,
				ilaEdfaPlusPump2HighThermoElectricCoolerCurrentWarning		DisplayString,
				ilaEdfaPlusPump1LowThermoElectricCoolerCurrentWarning		DisplayString,
				ilaEdfaPlusPump2LowThermoElectricCoolerCurrentWarning		DisplayString,
				ilaEdfaPlusVariableOpticalAttenuatorHighInputPowerAlarm 	DisplayString,
				ilaEdfaPlusVariableOpticalAttenuatorLowInputPowerAlarm 		DisplayString,
				ilaEdfaPlusVariableOpticalAttenuatorHighInputPowerWarning 	DisplayString,
				ilaEdfaPlusVariableOpticalAttenuatorLowInputPowerWarning 	DisplayString,
				ilaEdfaPlusInputOutOfRangeAlarm					DisplayString,
				ilaEdfaPlusOutputOutOfRangeAlarm				DisplayString,
				ilaEdfaPlusMidInOutOfRangeAlarm					DisplayString,
				ilaEdfaPlusMidOutOutOfRangeAlarm				DisplayString,
				ilaEdfaPlusPumpBiasCurrentAlarm					DisplayString,
				ilaEdfaPlusPump1CoolingTemperatureAlarm				DisplayString,
				ilaEdfaPlusPump2CoolingTemperatureAlarm				DisplayString,
				ilaEdfaPlusPump1LaserPowerAlarm					DisplayString,
				ilaEdfaPlusPump2LaserPowerAlarm					DisplayString,
				ilaEdfaPlusAlarmQueryTableRowStatus				RowStatus
			}

	ilaEdfaPlusOpticalInputPowerFailureAlarmForStage1 OBJECT-TYPE
		SYNTAX  	DisplayString
		MAX-ACCESS  	read-only
		STATUS  	current

		DESCRIPTION
		 " to get ILA EDFA PLUS card optical input power failure alarm status for stage 1.
		-----------------------------
		Values :
		If Alarm is Present - Date and Time Stamp
			    eg:2017-5-18,9:47:20.0,+5:30
		If Alarm is Absent  - 0
		-----------------------------"

		::= { ilaEdfaPlusAlarmQueryEntry 1 }	              

	ilaEdfaPlusOpticalInputPowerFailureAlarmForStage2 OBJECT-TYPE
		SYNTAX  	DisplayString
		MAX-ACCESS  	read-only
		STATUS  	current

		DESCRIPTION
		 " to get ILA EDFA PLUS card optical input power failure alarm status for stage 2.
		-----------------------------
		Values :
		If Alarm is Present - Date and Time Stamp
			    eg:2017-5-18,9:47:20.0,+5:30
		If Alarm is Absent  - 0
		-----------------------------"

		::= { ilaEdfaPlusAlarmQueryEntry 2 }
		      
	ilaEdfaPlusOpticalHighInputPowerAlarmForStage1 OBJECT-TYPE
		SYNTAX  	DisplayString
		MAX-ACCESS  	read-only
		STATUS  	current

		DESCRIPTION
		 " to get ILA EDFA PLUS card optical high input power alarm status for stage 1.
		-----------------------------
		Values :
		If Alarm is Present - Date and Time Stamp
			    eg:2017-5-18,9:47:20.0,+5:30
		If Alarm is Absent  - 0
		-----------------------------"

		::= { ilaEdfaPlusAlarmQueryEntry 3 }	              

	ilaEdfaPlusOpticalHighInputPowerAlarmForStage2 OBJECT-TYPE
		SYNTAX  	DisplayString
		MAX-ACCESS  	read-only
		STATUS  	current

		DESCRIPTION
		 " to get ILA EDFA PLUS card optical high input power alarm status for stage 2.
		-----------------------------
		Values :
		If Alarm is Present - Date and Time Stamp
			    eg:2017-5-18,9:47:20.0,+5:30
		If Alarm is Absent  - 0
		-----------------------------"

		::= { ilaEdfaPlusAlarmQueryEntry 4 }
		      
	ilaEdfaPlusOpticalLowInputPowerAlarmForStage1 OBJECT-TYPE
		SYNTAX  	DisplayString
		MAX-ACCESS  	read-only
		STATUS  	current

		DESCRIPTION
		 " to get ILA EDFA PLUS card optical low input power alarm status for stage 1.
		-----------------------------
		Values :
		If Alarm is Present - Date and Time Stamp
			    eg:2017-5-18,9:47:20.0,+5:30
		If Alarm is Absent  - 0
		-----------------------------"

		::= { ilaEdfaPlusAlarmQueryEntry 5 }	              

	ilaEdfaPlusOpticalLowInputPowerAlarmForStage2 OBJECT-TYPE
		SYNTAX  	DisplayString
		MAX-ACCESS  	read-only
		STATUS  	current

		DESCRIPTION
		 " to get ILA EDFA PLUS card optical low input power alarm status for stage 2.
		-----------------------------
		Values :
		If Alarm is Present - Date and Time Stamp
			    eg:2017-5-18,9:47:20.0,+5:30
		If Alarm is Absent  - 0
		-----------------------------"

		::= { ilaEdfaPlusAlarmQueryEntry 6 }
		      
	ilaEdfaPlusOpticalHighInputPowerWarningForStage1 OBJECT-TYPE
		SYNTAX  	DisplayString
		MAX-ACCESS  	read-only
		STATUS  	current

		DESCRIPTION
		 " to get ILA EDFA PLUS card optical high input power warning status for stage 1.
		-----------------------------
		Values :
		If Alarm is Present - Date and Time Stamp
			    eg:2017-5-18,9:47:20.0,+5:30
		If Alarm is Absent  - 0
		-----------------------------"

		::= { ilaEdfaPlusAlarmQueryEntry 7 }	              

	ilaEdfaPlusOpticalHighInputPowerWarningForStage2 OBJECT-TYPE
		SYNTAX  	DisplayString
		MAX-ACCESS  	read-only
		STATUS  	current

		DESCRIPTION
		 " to get ILA EDFA PLUS card optical high input power warning status for stage 2.
		-----------------------------
		Values :
		If Alarm is Present - Date and Time Stamp
			    eg:2017-5-18,9:47:20.0,+5:30
		If Alarm is Absent  - 0
		-----------------------------"

		::= { ilaEdfaPlusAlarmQueryEntry 8 }
		      
	ilaEdfaPlusOpticalLowInputPowerWarningForStage1 OBJECT-TYPE
		SYNTAX  	DisplayString
		MAX-ACCESS  	read-only
		STATUS  	current

		DESCRIPTION
		 " to get ILA EDFA PLUS card optical low input power warning status for stage 1.
		-----------------------------
		Values :
		If Alarm is Present - Date and Time Stamp
			    eg:2017-5-18,9:47:20.0,+5:30
		If Alarm is Absent  - 0
		-----------------------------"
	
	      ::= { ilaEdfaPlusAlarmQueryEntry 9 }	              

	ilaEdfaPlusOpticalLowInputPowerWarningForStage2 OBJECT-TYPE
		SYNTAX  	DisplayString
		MAX-ACCESS  	read-only
		STATUS  	current

		DESCRIPTION
		 " to get ILA EDFA PLUS card optical low input power warning status for stage 2.
		-----------------------------
		Values :
		If Alarm is Present - Date and Time Stamp
			    eg:2017-5-18,9:47:20.0,+5:30
		If Alarm is Absent  - 0
		-----------------------------"
	
	      ::= { ilaEdfaPlusAlarmQueryEntry 10 }
		      
	ilaEdfaPlusOpticalOutputPowerFailureAlarmForStage1 OBJECT-TYPE
		SYNTAX  	DisplayString
		MAX-ACCESS  	read-only
		STATUS  	current

		DESCRIPTION
		 " to get ILA EDFA PLUS card optical high output power failure alarm status for stage 1.
		-----------------------------
		Values :
		If Alarm is Present - Date and Time Stamp
			    eg:2017-5-18,9:47:20.0,+5:30
		If Alarm is Absent  - 0
		-----------------------------"

		::= { ilaEdfaPlusAlarmQueryEntry 11 }	              

	ilaEdfaPlusOpticalOutputPowerFailureAlarmForStage2 OBJECT-TYPE
		SYNTAX  	DisplayString
		MAX-ACCESS  	read-only
		STATUS  	current

		DESCRIPTION
		 " to get ILA EDFA PLUS card optical high output power failure alarm status for stage 2.
		-----------------------------
		Values :
		If Alarm is Present - Date and Time Stamp
			    eg:2017-5-18,9:47:20.0,+5:30
		If Alarm is Absent  - 0
		-----------------------------"

		::= { ilaEdfaPlusAlarmQueryEntry 12 }
		      
	ilaEdfaPlusOpticalHighOutputPowerAlarmForStage1 OBJECT-TYPE
		SYNTAX  	DisplayString
		MAX-ACCESS  	read-only
		STATUS  	current

		DESCRIPTION
		 " to get ILA EDFA PLUS card optical high output power alarm status for stage 1.
		-----------------------------
		Values :
		If Alarm is Present - Date and Time Stamp
			    eg:2017-5-18,9:47:20.0,+5:30
		If Alarm is Absent  - 0
		-----------------------------"

		::= { ilaEdfaPlusAlarmQueryEntry 13 }

	ilaEdfaPlusOpticalHighOutputPowerAlarmForStage2 OBJECT-TYPE
		SYNTAX  	DisplayString
		MAX-ACCESS  	read-only
		STATUS  	current

		DESCRIPTION
		 " to get ILA EDFA PLUS card optical high output power alarm status for stage 2.
		-----------------------------
		Values :
		If Alarm is Present - Date and Time Stamp
			    eg:2017-5-18,9:47:20.0,+5:30
		If Alarm is Absent  - 0
		-----------------------------"

		::= { ilaEdfaPlusAlarmQueryEntry 14 }

	ilaEdfaPlusOpticalLowOutputPowerAlarmForStage1 OBJECT-TYPE
		SYNTAX  	DisplayString
		MAX-ACCESS  	read-only
		STATUS  	current

		DESCRIPTION
		 " to get ILA EDFA PLUS card optical low output power alarm status for stage 1.
		-----------------------------
		Values :
		If Alarm is Present - Date and Time Stamp
			    eg:2017-5-18,9:47:20.0,+5:30
		If Alarm is Absent  - 0
		-----------------------------"

		::= { ilaEdfaPlusAlarmQueryEntry 15 }	              

	ilaEdfaPlusOpticalLowOutputPowerAlarmForStage2 OBJECT-TYPE
		SYNTAX  	DisplayString
		MAX-ACCESS  	read-only
		STATUS  	current

		DESCRIPTION
		 " to get ILA EDFA PLUS card optical low output power alarm status for stage 2.
		-----------------------------
		Values :
		If Alarm is Present - Date and Time Stamp
			    eg:2017-5-18,9:47:20.0,+5:30
		If Alarm is Absent  - 0
		-----------------------------"

		::= { ilaEdfaPlusAlarmQueryEntry 16 }
		      
	ilaEdfaPlusOpticalHighOutputPowerWarningForStage1 OBJECT-TYPE
		SYNTAX  	DisplayString
		MAX-ACCESS  	read-only
		STATUS  	current

		DESCRIPTION
		 " to get ILA EDFA PLUS card optical high output power warning status for stage 1.
		-----------------------------
		Values :
		If Alarm is Present - Date and Time Stamp
			    eg:2017-5-18,9:47:20.0,+5:30
		If Alarm is Absent  - 0
		-----------------------------"

		::= { ilaEdfaPlusAlarmQueryEntry 17 }	              

	ilaEdfaPlusOpticalHighOutputPowerWarningForStage2 OBJECT-TYPE
		SYNTAX  	DisplayString
		MAX-ACCESS  	read-only
		STATUS  	current

		DESCRIPTION
		 " to get ILA EDFA PLUS card optical high output power warning status for stage 2.
		-----------------------------
		Values :
		If Alarm is Present - Date and Time Stamp
			    eg:2017-5-18,9:47:20.0,+5:30
		If Alarm is Absent  - 0
		-----------------------------"

		::= { ilaEdfaPlusAlarmQueryEntry 18 }
		      
	ilaEdfaPlusOpticalLowOutputPowerWarningForStage1 OBJECT-TYPE
		SYNTAX  	DisplayString
		MAX-ACCESS  	read-only
		STATUS  	current

		DESCRIPTION
		 " to get ILA EDFA PLUS card optical low output power warning status for stage 1.
		-----------------------------
		Values :
		If Alarm is Present - Date and Time Stamp
			    eg:2017-5-18,9:47:20.0,+5:30
		If Alarm is Absent  - 0
		-----------------------------"

		::= { ilaEdfaPlusAlarmQueryEntry 19 }	              

	ilaEdfaPlusOpticalLowOutputPowerWarningForStage2 OBJECT-TYPE
		SYNTAX  	DisplayString
		MAX-ACCESS  	read-only
		STATUS  	current

		DESCRIPTION
		 " to get ILA EDFA PLUS card optical low output power warning status for stage 2.
		-----------------------------
		Values :
		If Alarm is Present - Date and Time Stamp
			    eg:2017-5-18,9:47:20.0,+5:30
		If Alarm is Absent  - 0
		-----------------------------"

		::= { ilaEdfaPlusAlarmQueryEntry 20 }
		      
	ilaEdfaPlusModuleHighTemperatureAlarm OBJECT-TYPE
		SYNTAX  	DisplayString
		MAX-ACCESS  	read-only
		STATUS  	current

		DESCRIPTION
		 " to get ILA EDFA PLUS card module high temperature alarm status.
		-----------------------------
		Values :
		If Alarm is Present - Date and Time Stamp
			    eg:2017-5-18,9:47:20.0,+5:30
		If Alarm is Absent  - 0
		-----------------------------"

		::= { ilaEdfaPlusAlarmQueryEntry 21 }	              
		      
	ilaEdfaPlusModuleLowTemperatureAlarm OBJECT-TYPE
		SYNTAX  	DisplayString
		MAX-ACCESS  	read-only
		STATUS  	current

		DESCRIPTION
		 " to get ILA EDFA PLUS card module low temperature alarm status.
		-----------------------------
		Values :
		If Alarm is Present - Date and Time Stamp
			    eg:2017-5-18,9:47:20.0,+5:30
		If Alarm is Absent  - 0
		-----------------------------"
	
	      ::= { ilaEdfaPlusAlarmQueryEntry 22 }	              
		      
	ilaEdfaPlusModuleHighTemperatureWarning OBJECT-TYPE
		SYNTAX  	DisplayString
		MAX-ACCESS  	read-only
		STATUS  	current

		DESCRIPTION
		 " to get ILA EDFA PLUS card module high temperature warning status.
		-----------------------------
		Values :
		If Alarm is Present - Date and Time Stamp
			    eg:2017-5-18,9:47:20.0,+5:30
		If Alarm is Absent  - 0
		-----------------------------"

		::= { ilaEdfaPlusAlarmQueryEntry 23 }	              
		      
	ilaEdfaPlusModuleLowTemperatureWarning OBJECT-TYPE
		SYNTAX  	DisplayString
		MAX-ACCESS  	read-only
		STATUS  	current

		DESCRIPTION
		 " to get ILA EDFA PLUS card module low temperature warning status.
		-----------------------------
		Values :
		If Alarm is Present - Date and Time Stamp
			    eg:2017-5-18,9:47:20.0,+5:30
		If Alarm is Absent  - 0
		-----------------------------"

		::= { ilaEdfaPlusAlarmQueryEntry 24 }

	ilaEdfaPlusPump1HighTemperatureAlarm OBJECT-TYPE
		SYNTAX  	DisplayString
		MAX-ACCESS  	read-only
		STATUS  	current

		DESCRIPTION
		 " to get ILA EDFA PLUS card pump 1 high temperature alarm status.
		-----------------------------
		Values :
		If Alarm is Present - Date and Time Stamp
			    eg:2017-5-18,9:47:20.0,+5:30
		If Alarm is Absent  - 0
		-----------------------------"

		::= { ilaEdfaPlusAlarmQueryEntry 25 }	              

	ilaEdfaPlusPump2HighTemperatureAlarm OBJECT-TYPE
		SYNTAX  	DisplayString
		MAX-ACCESS  	read-only
		STATUS  	current

		DESCRIPTION
		 " to get ILA EDFA PLUS card pump 2 high temperature alarm status.
		-----------------------------
		Values :
		If Alarm is Present - Date and Time Stamp
			    eg:2017-5-18,9:47:20.0,+5:30
		If Alarm is Absent  - 0
		-----------------------------"

		::= { ilaEdfaPlusAlarmQueryEntry 26 }
		      
	ilaEdfaPlusPump1LowTemperatureAlarm OBJECT-TYPE
		SYNTAX  	DisplayString
		MAX-ACCESS  	read-only
		STATUS  	current

		DESCRIPTION
		 " to get ILA EDFA PLUS card pump 1 low temperature alarm status.
		-----------------------------
		Values :
		If Alarm is Present - Date and Time Stamp
			    eg:2017-5-18,9:47:20.0,+5:30
		If Alarm is Absent  - 0
		-----------------------------"

		::= { ilaEdfaPlusAlarmQueryEntry 27 }	              

	ilaEdfaPlusPump2LowTemperatureAlarm OBJECT-TYPE
		SYNTAX  	DisplayString
		MAX-ACCESS  	read-only
		STATUS  	current

		DESCRIPTION
		 " to get ILA EDFA PLUS card pump 2 low temperature alarm status.
		-----------------------------
		Values :
		If Alarm is Present - Date and Time Stamp
			    eg:2017-5-18,9:47:20.0,+5:30
		If Alarm is Absent  - 0
		-----------------------------"

		::= { ilaEdfaPlusAlarmQueryEntry 28 }
	      
	ilaEdfaPlusPump1HighTemperatureWarning OBJECT-TYPE
		SYNTAX  	DisplayString
		MAX-ACCESS  	read-only
		STATUS  	current

		DESCRIPTION
		 " to get ILA EDFA PLUS card pump 1 high temperature warning status.
		-----------------------------
		Values :
		If Alarm is Present - Date and Time Stamp
			    eg:2017-5-18,9:47:20.0,+5:30
		If Alarm is Absent  - 0
		-----------------------------"

		::= { ilaEdfaPlusAlarmQueryEntry 29 }	              

	ilaEdfaPlusPump2HighTemperatureWarning OBJECT-TYPE
		SYNTAX  	DisplayString
		MAX-ACCESS  	read-only
		STATUS  	current

		DESCRIPTION
		 " to get ILA EDFA PLUS card pump 2 high temperature warning status.
		-----------------------------
		Values :
		If Alarm is Present - Date and Time Stamp
			    eg:2017-5-18,9:47:20.0,+5:30
		If Alarm is Absent  - 0
		-----------------------------"

		::= { ilaEdfaPlusAlarmQueryEntry 30 }
		      
	ilaEdfaPlusPump1LowTemperatureWarning OBJECT-TYPE
		SYNTAX  	DisplayString
		MAX-ACCESS  	read-only
		STATUS  	current

		DESCRIPTION
		 " to get ILA EDFA PLUS card pump 1 low temperature warning status.
		-----------------------------
		Values :
		If Alarm is Present - Date and Time Stamp
			    eg:2017-5-18,9:47:20.0,+5:30
		If Alarm is Absent  - 0
		-----------------------------"

		::= { ilaEdfaPlusAlarmQueryEntry 31 }	              

	ilaEdfaPlusPump2LowTemperatureWarning OBJECT-TYPE
		SYNTAX  	DisplayString
		MAX-ACCESS  	read-only
		STATUS  	current

		DESCRIPTION
		 " to get ILA EDFA PLUS card pump 2 low temperature warning status.
		-----------------------------
		Values :
		If Alarm is Present - Date and Time Stamp
			    eg:2017-5-18,9:47:20.0,+5:30
		If Alarm is Absent  - 0
		-----------------------------"

		::= { ilaEdfaPlusAlarmQueryEntry 32 }
		      
	ilaEdfaPlusPump1HighOperatingCurrentAlarm OBJECT-TYPE
		SYNTAX  	DisplayString
		MAX-ACCESS  	read-only
		STATUS  	current

		DESCRIPTION
		 " to get ILA EDFA PLUS card pump 1 high operating current alarm status.
		-----------------------------
		Values :
		If Alarm is Present - Date and Time Stamp
			    eg:2017-5-18,9:47:20.0,+5:30
		If Alarm is Absent  - 0
		-----------------------------"
	
	      ::= { ilaEdfaPlusAlarmQueryEntry 33 }	              

	ilaEdfaPlusPump2HighOperatingCurrentAlarm OBJECT-TYPE
		SYNTAX  	DisplayString
		MAX-ACCESS  	read-only
		STATUS  	current

		DESCRIPTION
		 " to get ILA EDFA PLUS card pump 2 high operating current alarm status.
		-----------------------------
		Values :
		If Alarm is Present - Date and Time Stamp
			    eg:2017-5-18,9:47:20.0,+5:30
		If Alarm is Absent  - 0
		-----------------------------"
	
	      ::= { ilaEdfaPlusAlarmQueryEntry 34 }
		      
	ilaEdfaPlusPump1LowOperatingCurrentAlarm OBJECT-TYPE
		SYNTAX  	DisplayString
		MAX-ACCESS  	read-only
		STATUS  	current

		DESCRIPTION
		 " to get ILA EDFA PLUS card pump 1 low operating current alarm status.
		-----------------------------
		Values :
		If Alarm is Present - Date and Time Stamp
			    eg:2017-5-18,9:47:20.0,+5:30
		If Alarm is Absent  - 0
		-----------------------------"

		::= { ilaEdfaPlusAlarmQueryEntry 35 }	              

	ilaEdfaPlusPump2LowOperatingCurrentAlarm OBJECT-TYPE
		SYNTAX  	DisplayString
		MAX-ACCESS  	read-only
		STATUS  	current

		DESCRIPTION
		 " to get ILA EDFA PLUS card pump 2 low operating current alarm status.
		-----------------------------
		Values :
		If Alarm is Present - Date and Time Stamp
			    eg:2017-5-18,9:47:20.0,+5:30
		If Alarm is Absent  - 0
		-----------------------------"

		::= { ilaEdfaPlusAlarmQueryEntry 36 }
		      
	ilaEdfaPlusPump1HighOperatingCurrentWarning OBJECT-TYPE
		SYNTAX  	DisplayString
		MAX-ACCESS  	read-only
		STATUS  	current

		DESCRIPTION
		 " to get ILA EDFA PLUS card pump 1 high operating current warning status.
		-----------------------------
		Values :
		If Alarm is Present - Date and Time Stamp
			    eg:2017-5-18,9:47:20.0,+5:30
		If Alarm is Absent  - 0
		-----------------------------"

		::= { ilaEdfaPlusAlarmQueryEntry 37 }

	ilaEdfaPlusPump2HighOperatingCurrentWarning OBJECT-TYPE
		SYNTAX  	DisplayString
		MAX-ACCESS  	read-only
		STATUS  	current

		DESCRIPTION
		 " to get ILA EDFA PLUS card pump 2 high operating current warning status.
		-----------------------------
		Values :
		If Alarm is Present - Date and Time Stamp
			    eg:2017-5-18,9:47:20.0,+5:30
		If Alarm is Absent  - 0
		-----------------------------"

		::= { ilaEdfaPlusAlarmQueryEntry 38 }

	ilaEdfaPlusPump1LowOperatingCurrentWarning OBJECT-TYPE
		SYNTAX  	DisplayString
		MAX-ACCESS  	read-only
		STATUS  	current

		DESCRIPTION
		 " to get ILA EDFA PLUS card pump 1 low operating current warning status.
		-----------------------------
		Values :
		If Alarm is Present - Date and Time Stamp
			    eg:2017-5-18,9:47:20.0,+5:30
		If Alarm is Absent  - 0
		-----------------------------"

		::= { ilaEdfaPlusAlarmQueryEntry 39 }

	ilaEdfaPlusPump2LowOperatingCurrentWarning OBJECT-TYPE
		SYNTAX  	DisplayString
		MAX-ACCESS  	read-only
		STATUS  	current

		DESCRIPTION
		 " to get ILA EDFA PLUS card pump 2 low operating current warning status.
		-----------------------------
		Values :
		If Alarm is Present - Date and Time Stamp
			    eg:2017-5-18,9:47:20.0,+5:30
		If Alarm is Absent  - 0
		-----------------------------"

		::= { ilaEdfaPlusAlarmQueryEntry 40 }

	ilaEdfaPlusPump1HighThermoElectricCoolerCurrentAlarm OBJECT-TYPE
		SYNTAX  	DisplayString
		MAX-ACCESS  	read-only
		STATUS  	current

		DESCRIPTION
		 " to get ILA EDFA PLUS card pump 1 high thermo electric cooler current alarm status.
		-----------------------------
		Values :
		If Alarm is Present - Date and Time Stamp
			    eg:2017-5-18,9:47:20.0,+5:30
		If Alarm is Absent  - 0
		-----------------------------"

		::= { ilaEdfaPlusAlarmQueryEntry 41 }

	ilaEdfaPlusPump2HighThermoElectricCoolerCurrentAlarm OBJECT-TYPE
		SYNTAX  	DisplayString
		MAX-ACCESS  	read-only
		STATUS  	current

		DESCRIPTION
		 " to get ILA EDFA PLUS card pump 2 high thermo electric cooler current alarm status.
		-----------------------------
		Values :
		If Alarm is Present - Date and Time Stamp
			    eg:2017-5-18,9:47:20.0,+5:30
		If Alarm is Absent  - 0
		-----------------------------"

		::= { ilaEdfaPlusAlarmQueryEntry 42 }

	ilaEdfaPlusPump1LowThermoElectricCoolerCurrentAlarm OBJECT-TYPE
		SYNTAX  	DisplayString
		MAX-ACCESS  	read-only
		STATUS  	current

		DESCRIPTION
		 " to get ILA EDFA PLUS card pump 1 low thermo electric cooler current alarm status.
		-----------------------------
		Values :
		If Alarm is Present - Date and Time Stamp
			    eg:2017-5-18,9:47:20.0,+5:30
		If Alarm is Absent  - 0
		-----------------------------"

		::= { ilaEdfaPlusAlarmQueryEntry 43 }

	ilaEdfaPlusPump2LowThermoElectricCoolerCurrentAlarm OBJECT-TYPE
		SYNTAX  	DisplayString
		MAX-ACCESS  	read-only
		STATUS  	current

		DESCRIPTION
		 " to get ILA EDFA PLUS card pump 2 low thermo electric cooler current alarm status.
		-----------------------------
		Values :
		If Alarm is Present - Date and Time Stamp
			    eg:2017-5-18,9:47:20.0,+5:30
		If Alarm is Absent  - 0
		-----------------------------"

		::= { ilaEdfaPlusAlarmQueryEntry 44 }

	ilaEdfaPlusPump1HighThermoElectricCoolerCurrentWarning OBJECT-TYPE
		SYNTAX  	DisplayString
		MAX-ACCESS  	read-only
		STATUS  	current

		DESCRIPTION
		 " to get ILA EDFA PLUS card pump 1 high thermo electric cooler current warning status.
		-----------------------------
		Values :
		If Alarm is Present - Date and Time Stamp
			    eg:2017-5-18,9:47:20.0,+5:30
		If Alarm is Absent  - 0
		-----------------------------"

		::= { ilaEdfaPlusAlarmQueryEntry 45 }

	ilaEdfaPlusPump2HighThermoElectricCoolerCurrentWarning OBJECT-TYPE
		SYNTAX  	DisplayString
		MAX-ACCESS  	read-only
		STATUS  	current

		DESCRIPTION
		 " to get ILA EDFA PLUS card pump 2 high thermo electric cooler current warning status.
		-----------------------------
		Values :
		If Alarm is Present - Date and Time Stamp
			    eg:2017-5-18,9:47:20.0,+5:30
		If Alarm is Absent  - 0
		-----------------------------"

		::= { ilaEdfaPlusAlarmQueryEntry 46 }

	ilaEdfaPlusPump1LowThermoElectricCoolerCurrentWarning OBJECT-TYPE
		SYNTAX  	DisplayString
		MAX-ACCESS  	read-only
		STATUS  	current

		DESCRIPTION
		 " to get ILA EDFA PLUS card pump 1 low thermo electric cooler current warning status.
		-----------------------------
		Values :
		If Alarm is Present - Date and Time Stamp
			    eg:2017-5-18,9:47:20.0,+5:30
		If Alarm is Absent  - 0
		-----------------------------"

		::= { ilaEdfaPlusAlarmQueryEntry 47 }

	ilaEdfaPlusPump2LowThermoElectricCoolerCurrentWarning OBJECT-TYPE
		SYNTAX  	DisplayString
		MAX-ACCESS  	read-only
		STATUS  	current

		DESCRIPTION
		 " to get ILA EDFA PLUS card pump 2 low thermo electric cooler current warning status.
		-----------------------------
		Values :
		If Alarm is Present - Date and Time Stamp
			    eg:2017-5-18,9:47:20.0,+5:30
		If Alarm is Absent  - 0
		-----------------------------"

		::= { ilaEdfaPlusAlarmQueryEntry 48 }

	ilaEdfaPlusVariableOpticalAttenuatorHighInputPowerAlarm OBJECT-TYPE
		SYNTAX  	DisplayString
		MAX-ACCESS  	read-only
		STATUS  	current

		DESCRIPTION
		 " to get ILA EDFA PLUS card variable optical attenuator high input power alarm status.
		-----------------------------
		Values :
		If Alarm is Present - Date and Time Stamp
			    eg:2017-5-18,9:47:20.0,+5:30
		If Alarm is Absent  - 0
		-----------------------------"

		::= { ilaEdfaPlusAlarmQueryEntry 49 }

	ilaEdfaPlusVariableOpticalAttenuatorLowInputPowerAlarm OBJECT-TYPE
		SYNTAX  	DisplayString
		MAX-ACCESS  	read-only
		STATUS  	current

		DESCRIPTION
		 " to get ILA EDFA PLUS card variable optical attenuator low input power alarm status.
		-----------------------------
		Values :
		If Alarm is Present - Date and Time Stamp
			    eg:2017-5-18,9:47:20.0,+5:30
		If Alarm is Absent  - 0
		-----------------------------"

		::= { ilaEdfaPlusAlarmQueryEntry 50 }

	ilaEdfaPlusVariableOpticalAttenuatorHighInputPowerWarning OBJECT-TYPE
		SYNTAX  	DisplayString
		MAX-ACCESS  	read-only
		STATUS  	current

		DESCRIPTION
		 " to get ILA EDFA PLUS card variable optical attenuator high input power warning status.
		-----------------------------
		Values :
		If Alarm is Present - Date and Time Stamp
			    eg:2017-5-18,9:47:20.0,+5:30
		If Alarm is Absent  - 0
		-----------------------------"

		::= { ilaEdfaPlusAlarmQueryEntry 51 }

	ilaEdfaPlusVariableOpticalAttenuatorLowInputPowerWarning OBJECT-TYPE
		SYNTAX  	DisplayString
		MAX-ACCESS  	read-only
		STATUS  	current

		DESCRIPTION
		 " to get ILA EDFA PLUS card variable optical attenuator low input power warning status.
		-----------------------------
		Values :
		If Alarm is Present - Date and Time Stamp
			    eg:2017-5-18,9:47:20.0,+5:30
		If Alarm is Absent  - 0
		-----------------------------"

		::= { ilaEdfaPlusAlarmQueryEntry 52 }	              

	ilaEdfaPlusInputOutOfRangeAlarm OBJECT-TYPE
		SYNTAX  	DisplayString
		MAX-ACCESS  	read-only
		STATUS  	current

		DESCRIPTION
		 " to get ILA EDFA PLUS card input out of range alarm status.
		-----------------------------
		Values :
		If Alarm is Present - Date and Time Stamp
			    eg:2017-5-18,9:47:20.0,+5:30
		If Alarm is Absent  - 0
		-----------------------------"

		::= { ilaEdfaPlusAlarmQueryEntry 53 }

	ilaEdfaPlusOutputOutOfRangeAlarm OBJECT-TYPE
		SYNTAX  	DisplayString
		MAX-ACCESS  	read-only
		STATUS  	current

		DESCRIPTION
		 " to get ILA EDFA PLUS card output out of range alarm status.
		-----------------------------
		Values :
		If Alarm is Present - Date and Time Stamp
			    eg:2017-5-18,9:47:20.0,+5:30
		If Alarm is Absent  - 0
		-----------------------------"

		::= { ilaEdfaPlusAlarmQueryEntry 54 }

	ilaEdfaPlusMidInOutOfRangeAlarm OBJECT-TYPE
		SYNTAX  	DisplayString
		MAX-ACCESS  	read-only
		STATUS  	current

		DESCRIPTION
		 " to get ILA EDFA PLUS card stage 2 input out of range alarm status.
		-----------------------------
		Values :
		If Alarm is Present - Date and Time Stamp
			    eg:2017-5-18,9:47:20.0,+5:30
		If Alarm is Absent  - 0
		-----------------------------"

		::= { ilaEdfaPlusAlarmQueryEntry 55 }

	ilaEdfaPlusMidOutOutOfRangeAlarm OBJECT-TYPE
		SYNTAX  	DisplayString
		MAX-ACCESS  	read-only
		STATUS  	current

		DESCRIPTION
		 " to get ILA EDFA PLUS card stage 1 output out of range alarm status.
		-----------------------------
		Values :
		If Alarm is Present - Date and Time Stamp
			    eg:2017-5-18,9:47:20.0,+5:30
		If Alarm is Absent  - 0
		-----------------------------"

		::= { ilaEdfaPlusAlarmQueryEntry 56 }

	ilaEdfaPlusPumpBiasCurrentAlarm OBJECT-TYPE
		SYNTAX  	DisplayString
		MAX-ACCESS  	read-only
		STATUS  	current

		DESCRIPTION
		 " to get ILA EDFA PLUS card pump bias current alarm status.
		-----------------------------
		Values :
		If Alarm is Present - Date and Time Stamp
			    eg:2017-5-18,9:47:20.0,+5:30
		If Alarm is Absent  - 0
		-----------------------------"

		::= { ilaEdfaPlusAlarmQueryEntry 57 }

	ilaEdfaPlusPump1CoolingTemperatureAlarm OBJECT-TYPE
		SYNTAX  	DisplayString
		MAX-ACCESS  	read-only
		STATUS  	current

		DESCRIPTION
		 " to get ILA EDFA PLUS card pump 1 cooling temperature alarm status for stage 1.
		-----------------------------
		Values :
		If Alarm is Present - Date and Time Stamp
			    eg:2017-5-18,9:47:20.0,+5:30
		If Alarm is Absent  - 0
		-----------------------------"

		::= { ilaEdfaPlusAlarmQueryEntry 58 }

	ilaEdfaPlusPump2CoolingTemperatureAlarm OBJECT-TYPE
		SYNTAX  	DisplayString
		MAX-ACCESS  	read-only
		STATUS  	current

		DESCRIPTION
		 " to get ILA EDFA PLUS card pump 2 cooling temperature alarm status for stage 1.
		-----------------------------
		Values :
		If Alarm is Present - Date and Time Stamp
			    eg:2017-5-18,9:47:20.0,+5:30
		If Alarm is Absent  - 0
		-----------------------------"

		::= { ilaEdfaPlusAlarmQueryEntry 59 }

	ilaEdfaPlusPump1LaserPowerAlarm OBJECT-TYPE
		SYNTAX  	DisplayString
		MAX-ACCESS  	read-only
		STATUS  	current

		DESCRIPTION
		 " to get ILA EDFA PLUS card pump 1 laser power alarm status for stage 1.
		-----------------------------
		Values :
		If Alarm is Present - Date and Time Stamp
			    eg:2017-5-18,9:47:20.0,+5:30
		If Alarm is Absent  - 0
		-----------------------------"

		::= { ilaEdfaPlusAlarmQueryEntry 60 }

	ilaEdfaPlusPump2LaserPowerAlarm OBJECT-TYPE
		SYNTAX  	DisplayString
		MAX-ACCESS  	read-only
		STATUS  	current

		DESCRIPTION
		 " to get ILA EDFA PLUS card pump 2 laser power alarm status for stage 1.
		-----------------------------
		Values :
		If Alarm is Present - Date and Time Stamp
			    eg:2017-5-18,9:47:20.0,+5:30
		If Alarm is Absent  - 0
		-----------------------------"

		::= { ilaEdfaPlusAlarmQueryEntry 61 }

	ilaEdfaPlusAlarmQueryTableRowStatus OBJECT-TYPE
              SYNTAX      RowStatus
              MAX-ACCESS  read-write
              STATUS      current
              DESCRIPTION
                      "	This is MIB realted property,
			NOT to be considered as a card property"
              ::= { ilaEdfaPlusAlarmQueryEntry 62 }

--*****************************************************************************
--				ILA EDFA PLUS PERFORMANCE
--***************************************************************************** 

	ilaEdfaPlusPerformanceTable OBJECT-TYPE
		SYNTAX  	SEQUENCE OF IlaEdfaPlusPerformanceEntry
		MAX-ACCESS  	not-accessible
		STATUS  	current

		DESCRIPTION
		 "we can get ILA EDFA PLUS card performance details "

		::= { ilaEdfaPlusPerformance 1 }
	      
	ilaEdfaPlusPerformanceEntry OBJECT-TYPE
		SYNTAX  	IlaEdfaPlusPerformanceEntry
		MAX-ACCESS  	not-accessible
		STATUS  	current

		DESCRIPTION 
		 "Enter node rack, subrack, slot and ilaEdfaPlusInterface numbers"

		INDEX   { node, rack, subRack, slot, ilaEdfaPlusInterface }

		::= { ilaEdfaPlusPerformanceTable 1 }
	
	IlaEdfaPlusPerformanceEntry ::= 
		SEQUENCE {
				ilaEdfaPlusModuleTemperature					DisplayString,
				ilaEdfaPlusInputPowerForStage1					DisplayString,
				ilaEdfaPlusInputPowerForStage2					DisplayString,
				ilaEdfaPlusOutputPowerForStage1					DisplayString,
				ilaEdfaPlusOutputPowerForStage2					DisplayString,
				ilaEdfaPlusAmplifiedSpontaneousEmmissionPowerForStage1		DisplayString,
				ilaEdfaPlusAmplifiedSpontaneousEmmissionPowerForStage2		DisplayString,
				ilaEdfaPlusSignalGainForStage1					DisplayString,
				ilaEdfaPlusSignalGainForStage2					DisplayString,
				ilaEdfaPlusSignalOutputPowerForStage1				DisplayString,
				ilaEdfaPlusSignalOutputPowerForStage2				DisplayString,
				ilaEdfaPlusPump1LaserPower					DisplayString,
				ilaEdfaPlusPump2LaserPower					DisplayString,
				ilaEdfaPlusPump1Temperature					DisplayString,
				ilaEdfaPlusPump2Temperature					DisplayString,
				ilaEdfaPlusPump1OperatingCurrent				DisplayString,
				ilaEdfaPlusPump2OperatingCurrent				DisplayString,
				ilaEdfaPlusPump1ThermoElectricCoolerCurrent			DisplayString,
				ilaEdfaPlusPump2ThermoElectricCoolerCurrent			DisplayString,
				ilaEdfaPlusPump1CoolingTemperature				DisplayString,
				ilaEdfaPlusPump2CoolingTemperature				DisplayString,
				ilaEdfaPlusVariableOpticalAttenuatorInputPower			DisplayString,
				ilaEdfaPlusVariableOpticalAttenuatorOutputPower			DisplayString,
				ilaEdfaPlusVariableOpticalAttenuatorActualAttenuation		DisplayString,
				ilaEdfaPlusPerformanceTableRowStatus				RowStatus
			}
	
	ilaEdfaPlusModuleTemperature OBJECT-TYPE
		SYNTAX  	DisplayString
		MAX-ACCESS  	read-only
		STATUS  	current

		DESCRIPTION
		 " to get ILA EDFA PLUS card module temperature.
		-----------------------------
		Values:
		eg: 18.5
		-----------------------------"

		::= { ilaEdfaPlusPerformanceEntry 1 }

	ilaEdfaPlusInputPowerForStage1 OBJECT-TYPE
		SYNTAX  	DisplayString
		MAX-ACCESS  	read-only
		STATUS  	current

		DESCRIPTION
		 " to get ILA EDFA PLUS card input power for stage 1.
		-----------------------------
		Values:
		eg: 1.5
		-----------------------------"

		::= { ilaEdfaPlusPerformanceEntry 2 }	 

	ilaEdfaPlusInputPowerForStage2 OBJECT-TYPE
		SYNTAX  	DisplayString
		MAX-ACCESS  	read-only
		STATUS  	current

		DESCRIPTION
		 " to get ILA EDFA PLUS card input power for stage 2.
		-----------------------------
		Values:
		eg: 1.5
		-----------------------------"

		::= { ilaEdfaPlusPerformanceEntry 3 }
	      
	ilaEdfaPlusOutputPowerForStage1 OBJECT-TYPE
		SYNTAX  	DisplayString
		MAX-ACCESS  	read-only
		STATUS  	current

		DESCRIPTION
		 " to get ILA EDFA PLUS card output power for stage 1.
		-----------------------------
		Values:
		eg: 18.5
		-----------------------------"
	
	      ::= { ilaEdfaPlusPerformanceEntry 4 }	 

	ilaEdfaPlusOutputPowerForStage2 OBJECT-TYPE
		SYNTAX  	DisplayString
		MAX-ACCESS  	read-only
		STATUS  	current

		DESCRIPTION
		 " to get ILA EDFA PLUS card output power for stage 2.
		-----------------------------
		Values:
		eg: 2.5
		-----------------------------"
	
	      ::= { ilaEdfaPlusPerformanceEntry 5 }	 

	ilaEdfaPlusAmplifiedSpontaneousEmmissionPowerForStage1 OBJECT-TYPE
		SYNTAX  	DisplayString
		MAX-ACCESS  	read-only
		STATUS  	current

		DESCRIPTION
		 " to get ILA EDFA PLUS card Amplified Spontaneous Emmission power for stage 1.
		-----------------------------
		Values:
		eg: 2.5
		-----------------------------"

		::= { ilaEdfaPlusPerformanceEntry 6 }

	ilaEdfaPlusAmplifiedSpontaneousEmmissionPowerForStage2 OBJECT-TYPE
		SYNTAX  	DisplayString
		MAX-ACCESS  	read-only
		STATUS  	current

		DESCRIPTION
		 " to get ILA EDFA PLUS card Amplified Spontaneous Emmission power for stage 2.
		-----------------------------
		Values:
		eg: 18.5
		-----------------------------"

		::= { ilaEdfaPlusPerformanceEntry 7 }

	ilaEdfaPlusSignalGainForStage1 OBJECT-TYPE
		SYNTAX  	DisplayString
		MAX-ACCESS  	read-only
		STATUS  	current

		DESCRIPTION
		 " to get ILA EDFA PLUS signal gain for stage 1.
		-----------------------------
		Values:
		eg: 18.5
		-----------------------------"

		::= { ilaEdfaPlusPerformanceEntry 8 }

	ilaEdfaPlusSignalGainForStage2 OBJECT-TYPE
		SYNTAX  	DisplayString
		MAX-ACCESS  	read-only
		STATUS  	current

		DESCRIPTION
		 " to get ILA EDFA PLUS signal gain for stage 2.
		-----------------------------
		Values:
		eg: 18.5
		-----------------------------"

		::= { ilaEdfaPlusPerformanceEntry 9 }

	ilaEdfaPlusSignalOutputPowerForStage1 OBJECT-TYPE
		SYNTAX  	DisplayString
		MAX-ACCESS  	read-only
		STATUS  	current

		DESCRIPTION
		 " to get ILA EDFA PLUS card signal output power for stage 1.
		-----------------------------
		Values:
		eg: 18.5
		-----------------------------"

		::= { ilaEdfaPlusPerformanceEntry 10 }

	ilaEdfaPlusSignalOutputPowerForStage2 OBJECT-TYPE
		SYNTAX  	DisplayString
		MAX-ACCESS  	read-only
		STATUS  	current

		DESCRIPTION
		 " to get ILA EDFA PLUS card signal output power for stage 2.
		-----------------------------
		Values:
		eg: 18.5
		-----------------------------"

		::= { ilaEdfaPlusPerformanceEntry 11 }
	      	
	ilaEdfaPlusPump1LaserPower OBJECT-TYPE
		SYNTAX  	DisplayString
		MAX-ACCESS  	read-only
		STATUS  	current

		DESCRIPTION
		 " to get ILA EDFA PLUS card pump 1 laser power.
		-----------------------------
		Values:
		eg: 18.5
		-----------------------------"

		::= { ilaEdfaPlusPerformanceEntry 21 }	 

	ilaEdfaPlusPump2LaserPower OBJECT-TYPE
		SYNTAX  	DisplayString
		MAX-ACCESS  	read-only
		STATUS  	current

		DESCRIPTION
		 " to get ILA EDFA PLUS card pump 2 laser power.
		-----------------------------
		Values:
		eg: 18.5
		-----------------------------"

		::= { ilaEdfaPlusPerformanceEntry 22 }
	      
	ilaEdfaPlusPump1Temperature OBJECT-TYPE
		SYNTAX  	DisplayString
		MAX-ACCESS  	read-only
		STATUS  	current

		DESCRIPTION
		 " to get ILA EDFA PLUS card pump 1 temperature.
		-----------------------------
		Values:
		eg: 18.5
		-----------------------------"

		::= { ilaEdfaPlusPerformanceEntry 23 }	 

	ilaEdfaPlusPump2Temperature OBJECT-TYPE
		SYNTAX  	DisplayString
		MAX-ACCESS  	read-only
		STATUS  	current

		DESCRIPTION
		 " to get ILA EDFA PLUS card pump 2 temperature.
		-----------------------------
		Values:
		eg: 18.5
		-----------------------------"

		::= { ilaEdfaPlusPerformanceEntry 24 }

	ilaEdfaPlusPump1OperatingCurrent OBJECT-TYPE
		SYNTAX  	DisplayString
		MAX-ACCESS  	read-only
		STATUS  	current

		DESCRIPTION
		 " to get ILA EDFA PLUS card pump 1 operating current.
		-----------------------------
		Values:
		eg: 18.5
		-----------------------------"

		::= { ilaEdfaPlusPerformanceEntry 25 }	 

	ilaEdfaPlusPump2OperatingCurrent OBJECT-TYPE
		SYNTAX  	DisplayString
		MAX-ACCESS  	read-only
		STATUS  	current

		DESCRIPTION
		 " to get ILA EDFA PLUS card pump 2 operating current.
		-----------------------------
		Values:
		eg: 18.5
		-----------------------------"

		::= { ilaEdfaPlusPerformanceEntry 26 }
	      
	ilaEdfaPlusPump1ThermoElectricCoolerCurrent OBJECT-TYPE
		SYNTAX  	DisplayString
		MAX-ACCESS  	read-only
		STATUS  	current

		DESCRIPTION
		 " to get ILA EDFA PLUS card pump 1 thermo electric cooler current.
		-----------------------------
		Values:
		eg: 18.5
		-----------------------------"
	
	      ::= { ilaEdfaPlusPerformanceEntry 27 }

	ilaEdfaPlusPump2ThermoElectricCoolerCurrent OBJECT-TYPE
		SYNTAX  	DisplayString
		MAX-ACCESS  	read-only
		STATUS  	current

		DESCRIPTION
		 " to get ILA EDFA PLUS card pump 2 thermo electric cooler current.
		-----------------------------
		Values:
		eg: 18.5
		-----------------------------"
	
	      ::= { ilaEdfaPlusPerformanceEntry 28 }	

	ilaEdfaPlusPump1CoolingTemperature OBJECT-TYPE
		SYNTAX  	DisplayString
		MAX-ACCESS  	read-only
		STATUS  	current

		DESCRIPTION
		 " to get ILA EDFA PLUS card pump 1 cooling temperature.
		-----------------------------
		Values:
		eg: 18.5
		-----------------------------"

		::= { ilaEdfaPlusPerformanceEntry 29 }

	ilaEdfaPlusPump2CoolingTemperature OBJECT-TYPE
		SYNTAX  	DisplayString
		MAX-ACCESS  	read-only
		STATUS  	current

		DESCRIPTION
		 " to get ILA EDFA PLUS card pump 2 cooling temperature.
		-----------------------------
		Values:
		eg: 18.5
		-----------------------------"

		::= { ilaEdfaPlusPerformanceEntry 30 } 
	      
	ilaEdfaPlusVariableOpticalAttenuatorInputPower OBJECT-TYPE
		SYNTAX  	DisplayString
		MAX-ACCESS  	read-only
		STATUS  	current

		DESCRIPTION
		 " to get ILA EDFA PLUS card variable optical attenuator input power.
		-----------------------------
		Values:
		eg: 18.5
		-----------------------------"

		::= { ilaEdfaPlusPerformanceEntry 41 }	 
	      		
	ilaEdfaPlusVariableOpticalAttenuatorOutputPower OBJECT-TYPE
		SYNTAX  	DisplayString
		MAX-ACCESS  	read-only
		STATUS  	current

		DESCRIPTION
		 " to get ILA EDFA PLUS card output power.
		-----------------------------
		Values:
		eg: 18.5
		-----------------------------"

		::= { ilaEdfaPlusPerformanceEntry 42 }	 

	ilaEdfaPlusVariableOpticalAttenuatorActualAttenuation OBJECT-TYPE
		SYNTAX  	DisplayString
		MAX-ACCESS  	read-only
		STATUS  	current

		DESCRIPTION
		 " to get ILA EDFA PLUS card variable optical attenuator actual attenuation.
		-----------------------------
		Values:
		eg: 18.5
		-----------------------------"

		::= { ilaEdfaPlusPerformanceEntry 43 }

	ilaEdfaPlusPerformanceTableRowStatus OBJECT-TYPE
              SYNTAX      RowStatus
              MAX-ACCESS  read-write
              STATUS      current
              DESCRIPTION
                      "	This is MIB realted property,
			NOT to be considered as a card property"
              ::= { ilaEdfaPlusPerformanceEntry 44 }

--*****************************************************************************
--		 	 ILA EDFA PLUS Alarm Notification Table
--***************************************************************************** 

	ilaEdfaPlusOpticalInputPowerFailureAlarmForStage1Trap NOTIFICATION-TYPE
		OBJECTS  { ilaEdfaPlusOpticalInputPowerFailureAlarmForStage1
			}
		STATUS  current

		DESCRIPTION
		 " This trap is sent when ilaEdfaPlus optical input power failure alarm for stage 1 state changes "

		::= { ilaEdfaPlusAlarmNotification 1 }

	ilaEdfaPlusOpticalInputPowerFailureAlarmForStage2Trap NOTIFICATION-TYPE
		OBJECTS  { ilaEdfaPlusOpticalInputPowerFailureAlarmForStage2
			}
		STATUS  current

		DESCRIPTION
		 " This trap is sent when ilaEdfaPlus optical input power failure alarm for stage 2 state changes "

		::= { ilaEdfaPlusAlarmNotification 2 }
	      
	ilaEdfaPlusOpticalHighInputPowerAlarmForStage1Trap NOTIFICATION-TYPE
		OBJECTS  { ilaEdfaPlusOpticalHighInputPowerAlarmForStage1
			}
		STATUS  current

		DESCRIPTION
		 " This trap is sent when ilaEdfaPlus optical high input power alarm for stage 1 state changes "

		::= { ilaEdfaPlusAlarmNotification 3 }              

	ilaEdfaPlusOpticalHighInputPowerAlarmForStage2Trap NOTIFICATION-TYPE
		OBJECTS  { ilaEdfaPlusOpticalHighInputPowerAlarmForStage2
			}
		STATUS  current

		DESCRIPTION
		 " This trap is sent when ilaEdfaPlus optical high input power alarm for stage 2 state changes "

		::= { ilaEdfaPlusAlarmNotification 4 } 
	      
	ilaEdfaPlusOpticalLowInputPowerAlarmForStage1Trap NOTIFICATION-TYPE
		OBJECTS  { ilaEdfaPlusOpticalLowInputPowerAlarmForStage1
			}
		STATUS  current

		DESCRIPTION
		 " This trap is sent when ilaEdfaPlus optical low input power alarm for stage 1 state changes "

		::= { ilaEdfaPlusAlarmNotification 5 } 
	      
	ilaEdfaPlusOpticalLowInputPowerAlarmForStage2Trap NOTIFICATION-TYPE
		OBJECTS  { ilaEdfaPlusOpticalLowInputPowerAlarmForStage2
			}
		STATUS  current

		DESCRIPTION
		 " This trap is sent when ilaEdfaPlus optical low input power alarm for stage 2 state changes "

		::= { ilaEdfaPlusAlarmNotification 6 }
	      
	ilaEdfaPlusOpticalHighInputPowerWarningForStage1Trap NOTIFICATION-TYPE
		OBJECTS  { ilaEdfaPlusOpticalHighInputPowerWarningForStage1
			}
		STATUS  current

		DESCRIPTION
		 " This trap is sent when ilaEdfaPlus optical high input power warning for stage 1 state changes "

		::= { ilaEdfaPlusAlarmNotification 7 } 
	      
	ilaEdfaPlusOpticalHighInputPowerWarningForStage2Trap NOTIFICATION-TYPE
		OBJECTS  { ilaEdfaPlusOpticalHighInputPowerWarningForStage2
			}
		STATUS  current

		DESCRIPTION
		 " This trap is sent when ilaEdfaPlus optical high input power warning for stage 2 state changes "

		::= { ilaEdfaPlusAlarmNotification 8 } 
	      
	ilaEdfaPlusOpticalLowInputPowerWarningForStage1Trap NOTIFICATION-TYPE
		OBJECTS  { ilaEdfaPlusOpticalLowInputPowerWarningForStage1
			}
		STATUS  current

		DESCRIPTION
		 " This trap is sent when ilaEdfaPlus optical low input power warning for stage 1 state changes "

		::= { ilaEdfaPlusAlarmNotification 9 }      

	ilaEdfaPlusOpticalLowInputPowerWarningForStage2Trap NOTIFICATION-TYPE
		OBJECTS  { ilaEdfaPlusOpticalLowInputPowerWarningForStage2
			}
		STATUS  current

		DESCRIPTION
		 " This trap is sent when ilaEdfaPlus optical low input power warning for stage 2 state changes "

		::= { ilaEdfaPlusAlarmNotification 10 } 
	      
	ilaEdfaPlusOpticalOutputPowerFailureAlarmForStage1Trap NOTIFICATION-TYPE
		OBJECTS  { ilaEdfaPlusOpticalOutputPowerFailureAlarmForStage1
			}
		STATUS  current

		DESCRIPTION
		 " This trap is sent when ilaEdfaPlus optical output power failure alarm for stage 1 state changes "

		::= { ilaEdfaPlusAlarmNotification 11 } 
 
	ilaEdfaPlusOpticalOutputPowerFailureAlarmForStage2Trap NOTIFICATION-TYPE
		OBJECTS  { ilaEdfaPlusOpticalOutputPowerFailureAlarmForStage2
			}
		STATUS  current

		DESCRIPTION
		 " This trap is sent when ilaEdfaPlus optical output power failure alarm for stage 2 state changes "

		::= { ilaEdfaPlusAlarmNotification 12 } 	
     
	ilaEdfaPlusOpticalHighOutputPowerAlarmForStage1Trap NOTIFICATION-TYPE
		OBJECTS  { ilaEdfaPlusOpticalHighOutputPowerAlarmForStage1
			}
		STATUS  current

		DESCRIPTION
		 " This trap is sent when ilaEdfaPlus optical high output power alarm for stage 1 state changes "

		::= { ilaEdfaPlusAlarmNotification 13 }  

	ilaEdfaPlusOpticalHighOutputPowerAlarmForStage2Trap NOTIFICATION-TYPE
		OBJECTS  { ilaEdfaPlusOpticalHighOutputPowerAlarmForStage2
			}
		STATUS  current

		DESCRIPTION
		 " This trap is sent when ilaEdfaPlus optical high output power alarm for stage 2 state changes "

		::= { ilaEdfaPlusAlarmNotification 14 } 

	ilaEdfaPlusOpticalLowOutputPowerAlarmForStage1Trap NOTIFICATION-TYPE
		OBJECTS  { ilaEdfaPlusOpticalLowOutputPowerAlarmForStage1
			}
		STATUS  current

		DESCRIPTION
		 " This trap is sent when ilaEdfaPlus optical low output power alarm for stage 1 state changes "

		::= { ilaEdfaPlusAlarmNotification 15 }

	ilaEdfaPlusOpticalLowOutputPowerAlarmForStage2Trap NOTIFICATION-TYPE
		OBJECTS  { ilaEdfaPlusOpticalLowOutputPowerAlarmForStage2
			}
		STATUS  current

		DESCRIPTION
		 " This trap is sent when ilaEdfaPlus optical low output power alarm for stage 2 state changes "

		::= { ilaEdfaPlusAlarmNotification 16 }
	      
	ilaEdfaPlusOpticalHighOutputPowerWarningForStage1Trap NOTIFICATION-TYPE
		OBJECTS  { ilaEdfaPlusOpticalHighOutputPowerWarningForStage1
			}
		STATUS  current

		DESCRIPTION
		 " This trap is sent when ilaEdfaPlus optical high output power warning for stage 1 state changes "

		::= { ilaEdfaPlusAlarmNotification 17 }              

	ilaEdfaPlusOpticalHighOutputPowerWarningForStage2Trap NOTIFICATION-TYPE
		OBJECTS  { ilaEdfaPlusOpticalHighOutputPowerWarningForStage2
			}
		STATUS  current

		DESCRIPTION
		 " This trap is sent when ilaEdfaPlus optical high output power warning for stage 2 state changes "

		::= { ilaEdfaPlusAlarmNotification 18 } 
	      
	ilaEdfaPlusOpticalLowOutputPowerWarningForStage1Trap NOTIFICATION-TYPE
		OBJECTS  { ilaEdfaPlusOpticalLowOutputPowerWarningForStage1
			}
		STATUS  current

		DESCRIPTION
		 " This trap is sent when ilaEdfaPlus optical low output power warning for stage 1 state changes "

		::= { ilaEdfaPlusAlarmNotification 19 } 

	ilaEdfaPlusOpticalLowOutputPowerWarningForStage2Trap NOTIFICATION-TYPE
		OBJECTS  { ilaEdfaPlusOpticalLowOutputPowerWarningForStage2
			}
		STATUS  current

		DESCRIPTION
		 " This trap is sent when ilaEdfaPlus optical low output power warning for stage 2 state changes "

		::= { ilaEdfaPlusAlarmNotification 20 } 	      
	      
	ilaEdfaPlusModuleHighTemperatureAlarmTrap NOTIFICATION-TYPE
		OBJECTS  { ilaEdfaPlusModuleHighTemperatureAlarm
			}
		STATUS  current

		DESCRIPTION
		 " This trap is sent when ilaEdfaPlus module high temperature alarm state changes "

		::= { ilaEdfaPlusAlarmNotification 21 } 
	      	      
	ilaEdfaPlusModuleLowTemperatureAlarmTrap NOTIFICATION-TYPE
		OBJECTS  { ilaEdfaPlusModuleLowTemperatureAlarm
			}
		STATUS  current

		DESCRIPTION
		 " This trap is sent when ilaEdfaPlus module low temperature alarm state changes "

		::= { ilaEdfaPlusAlarmNotification 22 }      
	      
	ilaEdfaPlusModuleHighTemperatureWarningTrap NOTIFICATION-TYPE
		OBJECTS  { ilaEdfaPlusModuleHighTemperatureWarning
			}
		STATUS  current

		DESCRIPTION
		 " This trap is sent when ilaEdfaPlus module high temperature warning state changes "

		::= { ilaEdfaPlusAlarmNotification 23 }  
	     
	ilaEdfaPlusModuleLowTemperatureWarningTrap NOTIFICATION-TYPE
		OBJECTS  { ilaEdfaPlusModuleLowTemperatureWarning
			}
		STATUS  current

		DESCRIPTION
		 " This trap is sent when ilaEdfaPlus module low temperature warning state changes "

		::= { ilaEdfaPlusAlarmNotification 24 } 

	ilaEdfaPlusPump1HighTemperatureAlarmTrap NOTIFICATION-TYPE
		OBJECTS  { ilaEdfaPlusPump1HighTemperatureAlarm
			}
		STATUS  current

		DESCRIPTION
		 " This trap is sent when ilaEdfaPlus pump 1 high temperature alarm state changes "

		::= { ilaEdfaPlusAlarmNotification 25 }

	ilaEdfaPlusPump2HighTemperatureAlarmTrap NOTIFICATION-TYPE
		OBJECTS  { ilaEdfaPlusPump2HighTemperatureAlarm
			}
		STATUS  current

		DESCRIPTION
		 " This trap is sent when ilaEdfaPlus pump 2 high temperature alarm state changes "

		::= { ilaEdfaPlusAlarmNotification 26 }
	      
	ilaEdfaPlusPump1LowTemperatureAlarmTrap NOTIFICATION-TYPE
		OBJECTS  { ilaEdfaPlusPump1LowTemperatureAlarm
			}
		STATUS  current

		DESCRIPTION
		 " This trap is sent when ilaEdfaPlus pump 1 low temperature alarm state changes "

		::= { ilaEdfaPlusAlarmNotification 27 }              

	ilaEdfaPlusPump2LowTemperatureAlarmTrap NOTIFICATION-TYPE
		OBJECTS  { ilaEdfaPlusPump2LowTemperatureAlarm
			}
		STATUS  current

		DESCRIPTION
		 " This trap is sent when ilaEdfaPlus pump 2 low temperature alarm state changes "

		::= { ilaEdfaPlusAlarmNotification 28 }
	      
	ilaEdfaPlusPump1HighTemperatureWarningTrap NOTIFICATION-TYPE
		OBJECTS  { ilaEdfaPlusPump1HighTemperatureWarning
			}
		STATUS  current

		DESCRIPTION
		 " This trap is sent when ilaEdfaPlus pump 1 high temperature warning state changes "

		::= { ilaEdfaPlusAlarmNotification 29 } 
	      
	ilaEdfaPlusPump2HighTemperatureWarningTrap NOTIFICATION-TYPE
		OBJECTS  { ilaEdfaPlusPump2HighTemperatureWarning
			}
		STATUS  current

		DESCRIPTION
		 " This trap is sent when ilaEdfaPlus pump 2 high temperature warning state changes "

		::= { ilaEdfaPlusAlarmNotification 30 } 
	      
	ilaEdfaPlusPump1LowTemperatureWarningTrap NOTIFICATION-TYPE
		OBJECTS  { ilaEdfaPlusPump1LowTemperatureWarning
			}
		STATUS  current

		DESCRIPTION
		 " This trap is sent when ilaEdfaPlus pump 1 low temperature warning state changes "

		::= { ilaEdfaPlusAlarmNotification 31 } 
	      
	ilaEdfaPlusPump2LowTemperatureWarningTrap NOTIFICATION-TYPE
		OBJECTS  { ilaEdfaPlusPump2LowTemperatureWarning
			}
		STATUS  current

		DESCRIPTION
		 " This trap is sent when ilaEdfaPlus pump 2 low temperature warning state changes "

		::= { ilaEdfaPlusAlarmNotification 32 } 
	      
	ilaEdfaPlusPump1HighOperatingCurrentAlarmTrap NOTIFICATION-TYPE
		OBJECTS  { ilaEdfaPlusPump1HighOperatingCurrentAlarm
			}
		STATUS  current

		DESCRIPTION
		 " This trap is sent when ilaEdfaPlus pump 1 high operating current alarm state changes "

		::= { ilaEdfaPlusAlarmNotification 33 }      

	ilaEdfaPlusPump2HighOperatingCurrentAlarmTrap NOTIFICATION-TYPE
		OBJECTS  { ilaEdfaPlusPump2HighOperatingCurrentAlarm
			}
		STATUS  current

		DESCRIPTION
		 " This trap is sent when ilaEdfaPlus pump 2 high operating current alarm state changes "

		::= { ilaEdfaPlusAlarmNotification 34 }
	      
	ilaEdfaPlusPump1LowOperatingCurrentAlarmTrap NOTIFICATION-TYPE
		OBJECTS  { ilaEdfaPlusPump1LowOperatingCurrentAlarm
			}
		STATUS  current

		DESCRIPTION
		 " This trap is sent when ilaEdfaPlus pump 1 low operating current alarm state changes "

		::= { ilaEdfaPlusAlarmNotification 35 }  
	      
	ilaEdfaPlusPump2LowOperatingCurrentAlarmTrap NOTIFICATION-TYPE
		OBJECTS  { ilaEdfaPlusPump2LowOperatingCurrentAlarm
			}
		STATUS  current

		DESCRIPTION
		 " This trap is sent when ilaEdfaPlus pump 2 low operating current alarm state changes "

		::= { ilaEdfaPlusAlarmNotification 36 }  
	     
	ilaEdfaPlusPump1HighOperatingCurrentWarningTrap NOTIFICATION-TYPE
		OBJECTS  { ilaEdfaPlusPump1HighOperatingCurrentWarning
			}
		STATUS  current

		DESCRIPTION
		 " This trap is sent when ilaEdfaPlus pump 1 high operating current warning state changes "

		::= { ilaEdfaPlusAlarmNotification 37 } 
	     
	ilaEdfaPlusPump2HighOperatingCurrentWarningTrap NOTIFICATION-TYPE
		OBJECTS  { ilaEdfaPlusPump2HighOperatingCurrentWarning
			}
		STATUS  current

		DESCRIPTION
		 " This trap is sent when ilaEdfaPlus pump 2 high operating current warning state changes "

		::= { ilaEdfaPlusAlarmNotification 38 } 

	ilaEdfaPlusPump1LowOperatingCurrentWarningTrap NOTIFICATION-TYPE
		OBJECTS  { ilaEdfaPlusPump1LowOperatingCurrentWarning
			}
		STATUS  current

		DESCRIPTION
		 " This trap is sent when ilaEdfaPlus pump 1 low operating current warning state changes "

		::= { ilaEdfaPlusAlarmNotification 39 }

	ilaEdfaPlusPump2LowOperatingCurrentWarningTrap NOTIFICATION-TYPE
		OBJECTS  { ilaEdfaPlusPump2LowOperatingCurrentWarning
			}
		STATUS  current

		DESCRIPTION
		 " This trap is sent when ilaEdfaPlus pump 2 low operating current warning state changes "

		::= { ilaEdfaPlusAlarmNotification 40 }
	      
	ilaEdfaPlusPump1HighThermoElectricCoolerCurrentAlarmTrap NOTIFICATION-TYPE
		OBJECTS  { ilaEdfaPlusPump1HighThermoElectricCoolerCurrentAlarm
			}
		STATUS  current

		DESCRIPTION
		 " This trap is sent when ilaEdfaPlus pump 1 high thermo electric cooler current alarm state changes "

		::= { ilaEdfaPlusAlarmNotification 41 }              
	      
	ilaEdfaPlusPump2HighThermoElectricCoolerCurrentAlarmTrap NOTIFICATION-TYPE
		OBJECTS  { ilaEdfaPlusPump2HighThermoElectricCoolerCurrentAlarm
			}
		STATUS  current

		DESCRIPTION
		 " This trap is sent when ilaEdfaPlus pump 2 high thermo electric cooler current alarm state changes "

		::= { ilaEdfaPlusAlarmNotification 42 }
	      
	ilaEdfaPlusPump1LowThermoElectricCoolerCurrentAlarmTrap NOTIFICATION-TYPE
		OBJECTS  { ilaEdfaPlusPump1LowThermoElectricCoolerCurrentAlarm
			}
		STATUS  current

		DESCRIPTION
		 " This trap is sent when ilaEdfaPlus pump 1 low thermo electric cooler current alarm state changes "

		::= { ilaEdfaPlusAlarmNotification 43 } 
	      
	ilaEdfaPlusPump2LowThermoElectricCoolerCurrentAlarmTrap NOTIFICATION-TYPE
		OBJECTS  { ilaEdfaPlusPump2LowThermoElectricCoolerCurrentAlarm
			}
		STATUS  current

		DESCRIPTION
		 " This trap is sent when ilaEdfaPlus pump 2 low thermo electric cooler current alarm state changes "

		::= { ilaEdfaPlusAlarmNotification 44 } 	      
	      
	ilaEdfaPlusPump1HighThermoElectricCoolerCurrentWarningTrap NOTIFICATION-TYPE
		OBJECTS  { ilaEdfaPlusPump1HighThermoElectricCoolerCurrentWarning
			}
		STATUS  current

		DESCRIPTION
		 " This trap is sent when ilaEdfaPlus pump 1 high thermo electric cooler current warning state changes "

		::= { ilaEdfaPlusAlarmNotification 45 } 
	      
	ilaEdfaPlusPump2HighThermoElectricCoolerCurrentWarningTrap NOTIFICATION-TYPE
		OBJECTS  { ilaEdfaPlusPump2HighThermoElectricCoolerCurrentWarning
			}
		STATUS  current

		DESCRIPTION
		 " This trap is sent when ilaEdfaPlus pump 2 high thermo electric cooler current warning state changes "

		::= { ilaEdfaPlusAlarmNotification 46 } 
	      
	ilaEdfaPlusPump1LowThermoElectricCoolerCurrentWarningTrap NOTIFICATION-TYPE
		OBJECTS  { ilaEdfaPlusPump1LowThermoElectricCoolerCurrentWarning
			}
		STATUS  current

		DESCRIPTION
		 " This trap is sent when ilaEdfaPlus pump 1 low thermo electric cooler current warning state changes "

		::= { ilaEdfaPlusAlarmNotification 47 }            

	ilaEdfaPlusPump2LowThermoElectricCoolerCurrentWarningTrap NOTIFICATION-TYPE
		OBJECTS  { ilaEdfaPlusPump2LowThermoElectricCoolerCurrentWarning
			}
		STATUS  current

		DESCRIPTION
		 " This trap is sent when ilaEdfaPlus pump 2 low thermo electric cooler current warning state changes "

		::= { ilaEdfaPlusAlarmNotification 48 }  
	      
	ilaEdfaPlusVariableOpticalAttenuatorHighInputPowerAlarmTrap NOTIFICATION-TYPE
		OBJECTS  { ilaEdfaPlusVariableOpticalAttenuatorHighInputPowerAlarm
			}
		STATUS  current

		DESCRIPTION
		 " This trap is sent when ilaEdfaPlus variable optical attenuator high input power alarm state changes "

		::= { ilaEdfaPlusAlarmNotification 49 }              
	      
	ilaEdfaPlusVariableOpticalAttenuatorLowInputPowerAlarmTrap NOTIFICATION-TYPE
		OBJECTS  { ilaEdfaPlusVariableOpticalAttenuatorLowInputPowerAlarm
			}
		STATUS  current

		DESCRIPTION
		 " This trap is sent when ilaEdfaPlus variable optical attenuator low input power alarm state changes "

		::= { ilaEdfaPlusAlarmNotification 50 } 
	      	      
	ilaEdfaPlusVariableOpticalAttenuatorHighInputPowerWarningTrap NOTIFICATION-TYPE
		OBJECTS  { ilaEdfaPlusVariableOpticalAttenuatorHighInputPowerWarning
			}
		STATUS  current

		DESCRIPTION
		 " This trap is sent when ilaEdfaPlus variable optical attenuator high input power warning state changes "

		::= { ilaEdfaPlusAlarmNotification 51 } 
	            
	ilaEdfaPlusVariableOpticalAttenuatorLowInputPowerWarningTrap NOTIFICATION-TYPE
		OBJECTS  { ilaEdfaPlusVariableOpticalAttenuatorLowInputPowerWarning
			}
		STATUS  current

		DESCRIPTION
		 " This trap is sent when ilaEdfaPlus variable optical attenuator low input power warning state changes "

		::= { ilaEdfaPlusAlarmNotification 52 } 

	ilaEdfaPlusInputOutOfRangeAlarmTrap NOTIFICATION-TYPE
		OBJECTS  { ilaEdfaPlusInputOutOfRangeAlarm
			}
		STATUS  current

		DESCRIPTION
		 " This trap is sent when ilaEdfaPlus input out of range alarm state changes "

		::= { ilaEdfaPlusAlarmNotification 53 }

	ilaEdfaPlusOutputOutOfRangeAlarmTrap NOTIFICATION-TYPE
		OBJECTS  { ilaEdfaPlusOutputOutOfRangeAlarm
			}
		STATUS  current

		DESCRIPTION
		 " This trap is sent when ilaEdfaPlus output out of range alarm state changes "

		::= { ilaEdfaPlusAlarmNotification 54 }

	ilaEdfaPlusMidInOutOfRangeAlarmTrap NOTIFICATION-TYPE
		OBJECTS  { ilaEdfaPlusMidInOutOfRangeAlarm
			}
		STATUS  current

		DESCRIPTION
		 " This trap is sent when ilaEdfaPlus Mid input out of range alarm state changes "

		::= { ilaEdfaPlusAlarmNotification 55 }

	ilaEdfaPlusMidOutOutOfRangeAlarmTrap NOTIFICATION-TYPE
		OBJECTS  { ilaEdfaPlusMidOutOutOfRangeAlarm
			}
		STATUS  current

		DESCRIPTION
		 " This trap is sent when ilaEdfaPlus Mid output out of range alarm state changes "

		::= { ilaEdfaPlusAlarmNotification 56 }
	      
	ilaEdfaPlusPumpBiasCurrentAlarmTrap NOTIFICATION-TYPE
		OBJECTS  { ilaEdfaPlusPumpBiasCurrentAlarm
			}
		STATUS  current

		DESCRIPTION
		 " This trap is sent when ilaEdfaPlus pump bias current alarm state changes "

		::= { ilaEdfaPlusAlarmNotification 57 } 
	
	ilaEdfaPlusPump1CoolingTemperatureAlarmTrap NOTIFICATION-TYPE
		OBJECTS  { ilaEdfaPlusPump1CoolingTemperatureAlarm
			}
		STATUS  current

		DESCRIPTION
		 " This trap is sent when ilaEdfaPlus pump 1 cooling temperature alarm state changes "

		::= { ilaEdfaPlusAlarmNotification 58 } 

	ilaEdfaPlusPump2CoolingTemperatureAlarmTrap NOTIFICATION-TYPE
		OBJECTS  { ilaEdfaPlusPump2CoolingTemperatureAlarm
			}
		STATUS  current

		DESCRIPTION
		 " This trap is sent when ilaEdfaPlus pump 2 cooling temperature alarm state changes "

		::= { ilaEdfaPlusAlarmNotification 59 } 

	ilaEdfaPlusPump1LaserPowerAlarmTrap NOTIFICATION-TYPE
		OBJECTS  { ilaEdfaPlusPump1LaserPowerAlarm
			}
		STATUS  current

		DESCRIPTION
		 " This trap is sent when ilaEdfaPlus pump 1 laser power alarm state changes "

		::= { ilaEdfaPlusAlarmNotification 60 } 

	ilaEdfaPlusPump2LaserPowerAlarmTrap NOTIFICATION-TYPE
		OBJECTS  { ilaEdfaPlusPump2LaserPowerAlarm
			}
		STATUS  current

		DESCRIPTION
		 " This trap is sent when ilaEdfaPlus pump 2 laser power alarm state changes "

		::= { ilaEdfaPlusAlarmNotification 61 } 
	      
--*****************************************************************************
             
	snmpCurrentNotificationsGroup NOTIFICATION-GROUP
		NOTIFICATIONS 	{ 
					ilaEdfaPlusOpticalInputPowerFailureAlarmForStage1Trap,
					ilaEdfaPlusOpticalInputPowerFailureAlarmForStage2Trap,
					ilaEdfaPlusOpticalHighInputPowerAlarmForStage1Trap,
					ilaEdfaPlusOpticalHighInputPowerAlarmForStage2Trap,
					ilaEdfaPlusOpticalLowInputPowerAlarmForStage1Trap,
					ilaEdfaPlusOpticalLowInputPowerAlarmForStage2Trap,
					ilaEdfaPlusOpticalHighInputPowerWarningForStage1Trap,
					ilaEdfaPlusOpticalHighInputPowerWarningForStage2Trap,
					ilaEdfaPlusOpticalLowInputPowerWarningForStage1Trap,
					ilaEdfaPlusOpticalLowInputPowerWarningForStage2Trap,
					ilaEdfaPlusOpticalOutputPowerFailureAlarmForStage1Trap,
					ilaEdfaPlusOpticalOutputPowerFailureAlarmForStage2Trap,
					ilaEdfaPlusOpticalHighOutputPowerAlarmForStage1Trap,
					ilaEdfaPlusOpticalHighOutputPowerAlarmForStage2Trap,
					ilaEdfaPlusOpticalLowOutputPowerAlarmForStage1Trap,
					ilaEdfaPlusOpticalLowOutputPowerAlarmForStage2Trap,
					ilaEdfaPlusOpticalHighOutputPowerWarningForStage1Trap,
					ilaEdfaPlusOpticalHighOutputPowerWarningForStage2Trap,
					ilaEdfaPlusOpticalLowOutputPowerWarningForStage1Trap,
					ilaEdfaPlusOpticalLowOutputPowerWarningForStage2Trap,
					ilaEdfaPlusModuleHighTemperatureAlarmTrap,
					ilaEdfaPlusModuleLowTemperatureAlarmTrap,
					ilaEdfaPlusModuleHighTemperatureWarningTrap,
					ilaEdfaPlusModuleLowTemperatureWarningTrap,
					ilaEdfaPlusPump1HighTemperatureAlarmTrap,
					ilaEdfaPlusPump2HighTemperatureAlarmTrap,
					ilaEdfaPlusPump1LowTemperatureAlarmTrap,
					ilaEdfaPlusPump2LowTemperatureAlarmTrap,
					ilaEdfaPlusPump1HighTemperatureWarningTrap,
					ilaEdfaPlusPump2HighTemperatureWarningTrap,
					ilaEdfaPlusPump1LowTemperatureWarningTrap,
					ilaEdfaPlusPump2LowTemperatureWarningTrap,
					ilaEdfaPlusPump1HighOperatingCurrentAlarmTrap,
					ilaEdfaPlusPump2HighOperatingCurrentAlarmTrap,
					ilaEdfaPlusPump1LowOperatingCurrentAlarmTrap,
					ilaEdfaPlusPump2LowOperatingCurrentAlarmTrap,
					ilaEdfaPlusPump1HighOperatingCurrentWarningTrap,
					ilaEdfaPlusPump2HighOperatingCurrentWarningTrap,
					ilaEdfaPlusPump1LowOperatingCurrentWarningTrap,
					ilaEdfaPlusPump2LowOperatingCurrentWarningTrap,
					ilaEdfaPlusPump1HighThermoElectricCoolerCurrentAlarmTrap,
					ilaEdfaPlusPump2HighThermoElectricCoolerCurrentAlarmTrap,
					ilaEdfaPlusPump1LowThermoElectricCoolerCurrentAlarmTrap,
					ilaEdfaPlusPump2LowThermoElectricCoolerCurrentAlarmTrap,
					ilaEdfaPlusPump1HighThermoElectricCoolerCurrentWarningTrap,
					ilaEdfaPlusPump2HighThermoElectricCoolerCurrentWarningTrap,
					ilaEdfaPlusPump1LowThermoElectricCoolerCurrentWarningTrap,
					ilaEdfaPlusPump2LowThermoElectricCoolerCurrentWarningTrap,
					ilaEdfaPlusVariableOpticalAttenuatorHighInputPowerAlarmTrap,
					ilaEdfaPlusVariableOpticalAttenuatorLowInputPowerAlarmTrap,
					ilaEdfaPlusVariableOpticalAttenuatorHighInputPowerWarningTrap,
					ilaEdfaPlusVariableOpticalAttenuatorLowInputPowerWarningTrap,
					ilaEdfaPlusInputOutOfRangeAlarmTrap,
					ilaEdfaPlusOutputOutOfRangeAlarmTrap,
					ilaEdfaPlusMidInOutOfRangeAlarmTrap,
					ilaEdfaPlusMidOutOutOfRangeAlarmTrap,
					ilaEdfaPlusPumpBiasCurrentAlarmTrap,
					ilaEdfaPlusPump1CoolingTemperatureAlarmTrap,
					ilaEdfaPlusPump2CoolingTemperatureAlarmTrap,
					ilaEdfaPlusPump1LaserPowerAlarmTrap,
					ilaEdfaPlusPump2LaserPowerAlarmTrap
				}
		STATUS current

		DESCRIPTION
		"The UTL DWDM current notifications group"

		::= { ilaEdfaPlus 5 }                           

--***************************************************************************** 

	snmpcurrentGroup OBJECT-GROUP
		OBJECTS {
				ilaEdfaPlusInterface,
				ilaEdfaPlusEepromCardId,
				ilaEdfaPlusEepromCardName,
				ilaEdfaPlusEepromPartCode,
				ilaEdfaPlusEepromCardSerialNumber,
				ilaEdfaPlusEepromHardwareExternalReleaseVersion,
				ilaEdfaPlusSoftwareExternalReleaseVersion,
				ilaEdfaPlusEepromHardwareInternalReleaseVersion,
				ilaEdfaPlusSoftwareInternalReleaseVersion,
				ilaEdfaPlusEepromCardUidNumber,
				ilaEdfaPlusEepromCardEUI48Number,
				ilaEdfaPlusEepromCardEUI64Number,
				ilaEdfaPlusCardRootFileSystemVersion,
				ilaEdfaPlusInstallationDate,
				ilaEdfaPlusCommissionDate,
				ilaEdfaPlusCardRunningTime,
				ilaEdfaPlusCardRestartCount,
				ilaEdfaPlusModuleVendorName,
				ilaEdfaPlusModuleSerialNumber,
				ilaEdfaPlusNumberOfChannelsSupported,
				ilaEdfaPlusNumberOfPumpSupported,
				ilaEdfaPlusMaxGainSupported,
				ilaEdfaPlusSaturationOutputPowerSupported,
				ilaEdfaPlusMidStageAccessSupport,
				ilaEdfaPlusDirection,
				ilaEdfaPlusStage2VoaPresenceStatus,
				ilaEdfaPlusModuleType,
				ilaEdfaPlusCardGeneralDetailsTableRowStatus,
				ilaEdfaPlusCardSoftReset,
				ilaEdfaPlusCardDefaultFactoryReset,
				ilaEdfaPlusAlarmMonitoringStatus,
				ilaEdfaPlusManageUnmanageStatus,
				ilaEdfaPlusSyncSystemTimeWithNtpServer,
				ilaEdfaPlusSyncRtcWithNtpServer,
				ilaEdfaPlusSyncRtcWithSystemTime,
				ilaEdfaPlusUpdateGivenTimeIntoSystem,
				ilaEdfaPlusUpdateGivenTimeIntoRtc,
				ilaEdfaPlusSystemTimeAndRtcTime,
				ilaEdfaPlusVariableOpticalAttenuatorReset,
				ilaEdfaPlusPump1LaserStatus,
				ilaEdfaPlusPump2LaserStatus,
				ilaEdfaPlusAutomaticPowerReductionStatusForStage1,
				ilaEdfaPlusAutomaticPowerReductionStatusForStage2,
				ilaEdfaPlusAutomaticLaserShutdownStatusForStage1,
				ilaEdfaPlusAutomaticLaserShutdownStatusForStage2,
				ilaEdfaPlusModuleOperatingModeForStage1,
				ilaEdfaPlusModuleOperatingModeForStage2,
				ilaEdfaPlusModuleGainInAutomaticGainControlModeForStage2,
				ilaEdfaPlusModuleGainInAutomaticGainControlModeForStage1,
				ilaEdfaPlusModuleOutputPowerInAutomaticPowerControlMode,
				ilaEdfaPlusPump1OperatingCurrentInAutomaticCurrentControlMode,
				ilaEdfaPlusPump2OperatingCurrentInAutomaticCurrentControlMode,
				ilaEdfaPlusGainTilt,
				ilaEdfaPlusVariableOpticalAttenuatorAttenuationForStage2,
				ilaEdfaPlusOutputPowerLimitFunctionStatusInAutomaticGainControlModeForStage1,
				ilaEdfaPlusOutputPowerLimitFunctionStatusInAutomaticGainControlModeForStage2,
				ilaEdfaPlusOutputPowerLimitInAutomaticGainControlModeForStage1,
				ilaEdfaPlusOutputPowerLimitInAutomaticGainControlModeForStage2,
				ilaEdfaPlusAutomaticPowerReductionForStage1Threshold,
				ilaEdfaPlusAutomaticPowerReductionForStage2Threshold,
				ilaEdfaPlusOpticalInputPowerFailureAlarmForStage1Threshold,
				ilaEdfaPlusOpticalInputPowerFailureAlarmForStage2Threshold,
				ilaEdfaPlusOpticalHighInputPowerAlarmForStage1Threshold,
				ilaEdfaPlusOpticalHighInputPowerAlarmForStage2Threshold,
				ilaEdfaPlusOpticalLowInputPowerAlarmForStage1Threshold,
				ilaEdfaPlusOpticalLowInputPowerAlarmForStage2Threshold,
				ilaEdfaPlusOpticalHighInputPowerWarningForStage1Threshold,
				ilaEdfaPlusOpticalHighInputPowerWarningForStage2Threshold,
				ilaEdfaPlusOpticalLowInputPowerWarningForStage1Threshold,
				ilaEdfaPlusOpticalLowInputPowerWarningForStage2Threshold,
				ilaEdfaPlusOpticalOutputPowerFailureAlarmForStage1Threshold,
				ilaEdfaPlusOpticalOutputPowerFailureAlarmForStage2Threshold,
				ilaEdfaPlusOpticalHighOutputPowerAlarmForStage1Threshold,
				ilaEdfaPlusOpticalHighOutputPowerAlarmForStage2Threshold,
				ilaEdfaPlusOpticalLowOutputPowerAlarmForStage1Threshold,
				ilaEdfaPlusOpticalLowOutputPowerAlarmForStage2Threshold,
				ilaEdfaPlusOpticalHighOutputPowerWarningForStage1Threshold,
				ilaEdfaPlusOpticalHighOutputPowerWarningForStage2Threshold,
				ilaEdfaPlusOpticalLowOutputPowerWarningForStage1Threshold,
				ilaEdfaPlusOpticalLowOutputPowerWarningForStage2Threshold,
				ilaEdfaPlusModuleHighTemperatureAlarmThreshold,
				ilaEdfaPlusModuleLowTemperatureAlarmThreshold,
				ilaEdfaPlusModuleHighTemperatureWarningThreshold,
				ilaEdfaPlusModuleLowTemperatureWarningThreshold,
				ilaEdfaPlusPump1HighTemperatureAlarmThreshold,
				ilaEdfaPlusPump2HighTemperatureAlarmThreshold,
				ilaEdfaPlusPump1LowTemperatureAlarmThreshold,
				ilaEdfaPlusPump2LowTemperatureAlarmThreshold,
				ilaEdfaPlusPump1HighTemperatureWarningThreshold,
				ilaEdfaPlusPump2HighTemperatureWarningThreshold,
				ilaEdfaPlusPump1LowTemperatureWarningThreshold,
				ilaEdfaPlusPump2LowTemperatureWarningThreshold,
				ilaEdfaPlusPump1HighOperatingCurrentAlarmThreshold,
				ilaEdfaPlusPump2HighOperatingCurrentAlarmThreshold,
				ilaEdfaPlusPump1LowOperatingCurrentAlarmThreshold,
				ilaEdfaPlusPump2LowOperatingCurrentAlarmThreshold,
				ilaEdfaPlusPump1HighOperatingCurrentWarningThreshold,
				ilaEdfaPlusPump2HighOperatingCurrentWarningThreshold,
				ilaEdfaPlusPump1LowOperatingCurrentWarningThreshold,
				ilaEdfaPlusPump2LowOperatingCurrentWarningThreshold,
				ilaEdfaPlusPump1HighThermoElectricCoolerCurrentAlarmThreshold,
				ilaEdfaPlusPump2HighThermoElectricCoolerCurrentAlarmThreshold,
				ilaEdfaPlusPump1LowThermoElectricCoolerCurrentAlarmThreshold,
				ilaEdfaPlusPump2LowThermoElectricCoolerCurrentAlarmThreshold,
				ilaEdfaPlusPump1HighThermoElectricCoolerCurrentWarningThreshold,
				ilaEdfaPlusPump2HighThermoElectricCoolerCurrentWarningThreshold,
				ilaEdfaPlusPump1LowThermoElectricCoolerCurrentWarningThreshold,
				ilaEdfaPlusPump2LowThermoElectricCoolerCurrentWarningThreshold,
				ilaEdfaPlusVariableOpticalAttenuatorHighInputPowerAlarmThreshold,
				ilaEdfaPlusVariableOpticalAttenuatorLowInputPowerAlarmThreshold,
				ilaEdfaPlusVariableOpticalAttenuatorHighInputPowerWarningThreshold,
				ilaEdfaPlusVariableOpticalAttenuatorLowInputPowerWarningThreshold,
				ilaEdfaPlusOpticalInputPowerFailureAlarmForStage1Inhibit,
				ilaEdfaPlusOpticalInputPowerFailureAlarmForStage2Inhibit,
				ilaEdfaPlusOpticalHighInputPowerAlarmForStage1Inhibit,
				ilaEdfaPlusOpticalHighInputPowerAlarmForStage2Inhibit,
				ilaEdfaPlusOpticalLowInputPowerAlarmForStage1Inhibit,
				ilaEdfaPlusOpticalLowInputPowerAlarmForStage2Inhibit,
				ilaEdfaPlusOpticalHighInputPowerWarningForStage1Inhibit,
				ilaEdfaPlusOpticalHighInputPowerWarningForStage2Inhibit,
				ilaEdfaPlusOpticalLowInputPowerWarningForStage1Inhibit,
				ilaEdfaPlusOpticalLowInputPowerWarningForStage2Inhibit,
				ilaEdfaPlusOpticalOutputPowerFailureAlarmForStage1Inhibit,
				ilaEdfaPlusOpticalOutputPowerFailureAlarmForStage2Inhibit,
				ilaEdfaPlusOpticalHighOutputPowerAlarmForStage1Inhibit,
				ilaEdfaPlusOpticalHighOutputPowerAlarmForStage2Inhibit,
				ilaEdfaPlusOpticalLowOutputPowerAlarmForStage1Inhibit,
				ilaEdfaPlusOpticalLowOutputPowerAlarmForStage2Inhibit,
				ilaEdfaPlusOpticalHighOutputPowerWarningForStage1Inhibit,
				ilaEdfaPlusOpticalHighOutputPowerWarningForStage2Inhibit,
				ilaEdfaPlusOpticalLowOutputPowerWarningForStage1Inhibit,
				ilaEdfaPlusOpticalLowOutputPowerWarningForStage2Inhibit,
				ilaEdfaPlusModuleHighTemperatureAlarmInhibit,
				ilaEdfaPlusModuleLowTemperatureAlarmInhibit,
				ilaEdfaPlusModuleHighTemperatureWarningInhibit,
				ilaEdfaPlusModuleLowTemperatureWarningInhibit,
				ilaEdfaPlusPump1HighTemperatureAlarmInhibit,
				ilaEdfaPlusPump2HighTemperatureAlarmInhibit,
				ilaEdfaPlusPump1LowTemperatureAlarmInhibit,
				ilaEdfaPlusPump2LowTemperatureAlarmInhibit,
				ilaEdfaPlusPump1HighTemperatureWarningInhibit,
				ilaEdfaPlusPump2HighTemperatureWarningInhibit,
				ilaEdfaPlusPump1LowTemperatureWarningInhibit,
				ilaEdfaPlusPump2LowTemperatureWarningInhibit,
				ilaEdfaPlusPump1HighOperatingCurrentAlarmInhibit,
				ilaEdfaPlusPump2HighOperatingCurrentAlarmInhibit,
				ilaEdfaPlusPump1LowOperatingCurrentAlarmInhibit,
				ilaEdfaPlusPump2LowOperatingCurrentAlarmInhibit,
				ilaEdfaPlusPump1HighOperatingCurrentWarningInhibit,
				ilaEdfaPlusPump2HighOperatingCurrentWarningInhibit,
				ilaEdfaPlusPump1LowOperatingCurrentWarningInhibit,
				ilaEdfaPlusPump2LowOperatingCurrentWarningInhibit,
				ilaEdfaPlusPump1HighThermoElectricCoolerCurrentAlarmInhibit,
				ilaEdfaPlusPump2HighThermoElectricCoolerCurrentAlarmInhibit,
				ilaEdfaPlusPump1LowThermoElectricCoolerCurrentAlarmInhibit,
				ilaEdfaPlusPump2LowThermoElectricCoolerCurrentAlarmInhibit,
				ilaEdfaPlusPump1HighThermoElectricCoolerCurrentWarningInhibit,
				ilaEdfaPlusPump2HighThermoElectricCoolerCurrentWarningInhibit,
				ilaEdfaPlusPump1LowThermoElectricCoolerCurrentWarningInhibit,
				ilaEdfaPlusPump2LowThermoElectricCoolerCurrentWarningInhibit,
				ilaEdfaPlusVariableOpticalAttenuatorHighInputPowerAlarmInhibit,
				ilaEdfaPlusVariableOpticalAttenuatorLowInputPowerAlarmInhibit,
				ilaEdfaPlusVariableOpticalAttenuatorHighInputPowerWarningInhibit,
				ilaEdfaPlusVariableOpticalAttenuatorLowInputPowerWarningInhibit,
				ilaEdfaPlusInputOutOfRangeAlarmInhibit,
				ilaEdfaPlusOutputOutOfRangeAlarmInhibit,
				ilaEdfaPlusPumpBiasCurrentAlarmInhibit,
				ilaEdfaPlusPump1CoolingTemperatureAlarmInhibit,
				ilaEdfaPlusPump2CoolingTemperatureAlarmInhibit,
				ilaEdfaPlusPump1LaserPowerAlarmInhibit,
				ilaEdfaPlusPump2LaserPowerAlarmInhibit,
				ilaEdfaPlusOpticalInputPowerFailureAlarmForStage1Severity,
				ilaEdfaPlusOpticalInputPowerFailureAlarmForStage2Severity,
				ilaEdfaPlusOpticalHighInputPowerAlarmForStage1Severity,
				ilaEdfaPlusOpticalHighInputPowerAlarmForStage2Severity,
				ilaEdfaPlusOpticalLowInputPowerAlarmForStage1Severity,
				ilaEdfaPlusOpticalLowInputPowerAlarmForStage2Severity,
				ilaEdfaPlusOpticalHighInputPowerWarningForStage1Severity,
				ilaEdfaPlusOpticalHighInputPowerWarningForStage2Severity,
				ilaEdfaPlusOpticalLowInputPowerWarningForStage1Severity,
				ilaEdfaPlusOpticalLowInputPowerWarningForStage2Severity,
				ilaEdfaPlusOpticalOutputPowerFailureAlarmForStage1Severity,
				ilaEdfaPlusOpticalOutputPowerFailureAlarmForStage2Severity,
				ilaEdfaPlusOpticalHighOutputPowerAlarmForStage1Severity,
				ilaEdfaPlusOpticalHighOutputPowerAlarmForStage2Severity,
				ilaEdfaPlusOpticalLowOutputPowerAlarmForStage1Severity,
				ilaEdfaPlusOpticalLowOutputPowerAlarmForStage2Severity,
				ilaEdfaPlusOpticalHighOutputPowerWarningForStage1Severity,
				ilaEdfaPlusOpticalHighOutputPowerWarningForStage2Severity,
				ilaEdfaPlusOpticalLowOutputPowerWarningForStage1Severity,
				ilaEdfaPlusOpticalLowOutputPowerWarningForStage2Severity,
				ilaEdfaPlusModuleHighTemperatureAlarmSeverity,
				ilaEdfaPlusModuleLowTemperatureAlarmSeverity,
				ilaEdfaPlusModuleHighTemperatureWarningSeverity,
				ilaEdfaPlusModuleLowTemperatureWarningSeverity,
				ilaEdfaPlusPump1HighTemperatureAlarmSeverity,
				ilaEdfaPlusPump2HighTemperatureAlarmSeverity,
				ilaEdfaPlusPump1LowTemperatureAlarmSeverity,
				ilaEdfaPlusPump2LowTemperatureAlarmSeverity,
				ilaEdfaPlusPump1HighTemperatureWarningSeverity,
				ilaEdfaPlusPump2HighTemperatureWarningSeverity,
				ilaEdfaPlusPump1LowTemperatureWarningSeverity,
				ilaEdfaPlusPump2LowTemperatureWarningSeverity,
				ilaEdfaPlusPump1HighOperatingCurrentAlarmSeverity,
				ilaEdfaPlusPump2HighOperatingCurrentAlarmSeverity,
				ilaEdfaPlusPump1LowOperatingCurrentAlarmSeverity,
				ilaEdfaPlusPump2LowOperatingCurrentAlarmSeverity,
				ilaEdfaPlusPump1HighOperatingCurrentWarningSeverity,
				ilaEdfaPlusPump2HighOperatingCurrentWarningSeverity,
				ilaEdfaPlusPump1LowOperatingCurrentWarningSeverity,
				ilaEdfaPlusPump2LowOperatingCurrentWarningSeverity,
				ilaEdfaPlusPump1HighThermoElectricCoolerCurrentAlarmSeverity,
				ilaEdfaPlusPump2HighThermoElectricCoolerCurrentAlarmSeverity,
				ilaEdfaPlusPump1LowThermoElectricCoolerCurrentAlarmSeverity,
				ilaEdfaPlusPump2LowThermoElectricCoolerCurrentAlarmSeverity,
				ilaEdfaPlusPump1HighThermoElectricCoolerCurrentWarningSeverity,
				ilaEdfaPlusPump2HighThermoElectricCoolerCurrentWarningSeverity,
				ilaEdfaPlusPump1LowThermoElectricCoolerCurrentWarningSeverity,
				ilaEdfaPlusPump2LowThermoElectricCoolerCurrentWarningSeverity,
				ilaEdfaPlusVariableOpticalAttenuatorHighInputPowerAlarmSeverity,
				ilaEdfaPlusVariableOpticalAttenuatorLowInputPowerAlarmSeverity,
				ilaEdfaPlusVariableOpticalAttenuatorHighInputPowerWarningSeverity,
				ilaEdfaPlusVariableOpticalAttenuatorLowInputPowerWarningSeverity,
				ilaEdfaPlusInputOutOfRangeAlarmSeverity,
				ilaEdfaPlusOutputOutOfRangeAlarmSeverity,
				ilaEdfaPlusPumpBiasCurrentAlarmSeverity,
				ilaEdfaPlusPump1CoolingTemperatureAlarmSeverity,
				ilaEdfaPlusPump2CoolingTemperatureAlarmSeverity,
				ilaEdfaPlusPump1LaserPowerAlarmSeverity,
				ilaEdfaPlusPump2LaserPowerAlarmSeverity,
				ilaEdfaPlusCardSoftwareUpgrade,
				ilaEdfaPlusMidInOutOfRangeAlarmInhibit,
				ilaEdfaPlusMidOutOutOfRangeAlarmInhibit,
				ilaEdfaPlusMidInOutOfRangeAlarmSeverity,
				ilaEdfaPlusMidOutOutOfRangeAlarmSeverity,
				ilaEdfaPlusConfigurationTableRowStatus,
				ilaEdfaPlusOpticalInputPowerFailureAlarmForStage1,
				ilaEdfaPlusOpticalInputPowerFailureAlarmForStage2,
				ilaEdfaPlusOpticalHighInputPowerAlarmForStage1,
				ilaEdfaPlusOpticalHighInputPowerAlarmForStage2,
				ilaEdfaPlusOpticalLowInputPowerAlarmForStage1,
				ilaEdfaPlusOpticalLowInputPowerAlarmForStage2,
				ilaEdfaPlusOpticalHighInputPowerWarningForStage1,
				ilaEdfaPlusOpticalHighInputPowerWarningForStage2,
				ilaEdfaPlusOpticalLowInputPowerWarningForStage1,
				ilaEdfaPlusOpticalLowInputPowerWarningForStage2,
				ilaEdfaPlusOpticalOutputPowerFailureAlarmForStage1,
				ilaEdfaPlusOpticalOutputPowerFailureAlarmForStage2,
				ilaEdfaPlusOpticalHighOutputPowerAlarmForStage1,
				ilaEdfaPlusOpticalHighOutputPowerAlarmForStage2,
				ilaEdfaPlusOpticalLowOutputPowerAlarmForStage1,
				ilaEdfaPlusOpticalLowOutputPowerAlarmForStage2,
				ilaEdfaPlusOpticalHighOutputPowerWarningForStage1,
				ilaEdfaPlusOpticalHighOutputPowerWarningForStage2,
				ilaEdfaPlusOpticalLowOutputPowerWarningForStage1,
				ilaEdfaPlusOpticalLowOutputPowerWarningForStage2,
				ilaEdfaPlusModuleHighTemperatureAlarm,
				ilaEdfaPlusModuleLowTemperatureAlarm,
				ilaEdfaPlusModuleHighTemperatureWarning,
				ilaEdfaPlusModuleLowTemperatureWarning,
				ilaEdfaPlusPump1HighTemperatureAlarm,
				ilaEdfaPlusPump2HighTemperatureAlarm,
				ilaEdfaPlusPump1LowTemperatureAlarm	,
				ilaEdfaPlusPump2LowTemperatureAlarm	,
				ilaEdfaPlusPump1HighTemperatureWarning,
				ilaEdfaPlusPump2HighTemperatureWarning,
				ilaEdfaPlusPump1LowTemperatureWarning,
				ilaEdfaPlusPump2LowTemperatureWarning,
				ilaEdfaPlusPump1HighOperatingCurrentAlarm,
				ilaEdfaPlusPump2HighOperatingCurrentAlarm,
				ilaEdfaPlusPump1LowOperatingCurrentAlarm,
				ilaEdfaPlusPump2LowOperatingCurrentAlarm,
				ilaEdfaPlusPump1HighOperatingCurrentWarning,
				ilaEdfaPlusPump2HighOperatingCurrentWarning,
				ilaEdfaPlusPump1LowOperatingCurrentWarning,
				ilaEdfaPlusPump2LowOperatingCurrentWarning,
				ilaEdfaPlusPump1HighThermoElectricCoolerCurrentAlarm,
				ilaEdfaPlusPump2HighThermoElectricCoolerCurrentAlarm,
				ilaEdfaPlusPump1LowThermoElectricCoolerCurrentAlarm,
				ilaEdfaPlusPump2LowThermoElectricCoolerCurrentAlarm,
				ilaEdfaPlusPump1HighThermoElectricCoolerCurrentWarning,
				ilaEdfaPlusPump2HighThermoElectricCoolerCurrentWarning,
				ilaEdfaPlusPump1LowThermoElectricCoolerCurrentWarning,
				ilaEdfaPlusPump2LowThermoElectricCoolerCurrentWarning,
				ilaEdfaPlusVariableOpticalAttenuatorHighInputPowerAlarm,
				ilaEdfaPlusVariableOpticalAttenuatorLowInputPowerAlarm,
				ilaEdfaPlusVariableOpticalAttenuatorHighInputPowerWarning,
				ilaEdfaPlusVariableOpticalAttenuatorLowInputPowerWarning,
				ilaEdfaPlusInputOutOfRangeAlarm,
				ilaEdfaPlusOutputOutOfRangeAlarm,
				ilaEdfaPlusMidInOutOfRangeAlarm,
				ilaEdfaPlusMidOutOutOfRangeAlarm,
				ilaEdfaPlusPumpBiasCurrentAlarm,
				ilaEdfaPlusPump1CoolingTemperatureAlarm,
				ilaEdfaPlusPump2CoolingTemperatureAlarm,
				ilaEdfaPlusPump1LaserPowerAlarm,
				ilaEdfaPlusPump2LaserPowerAlarm,
				ilaEdfaPlusAlarmQueryTableRowStatus,
				ilaEdfaPlusModuleTemperature,
				ilaEdfaPlusInputPowerForStage1,
				ilaEdfaPlusInputPowerForStage2,
				ilaEdfaPlusOutputPowerForStage1,
				ilaEdfaPlusOutputPowerForStage2,
				ilaEdfaPlusAmplifiedSpontaneousEmmissionPowerForStage1,
				ilaEdfaPlusAmplifiedSpontaneousEmmissionPowerForStage2,
				ilaEdfaPlusSignalGainForStage1,
				ilaEdfaPlusSignalGainForStage2,
				ilaEdfaPlusSignalOutputPowerForStage1,
				ilaEdfaPlusSignalOutputPowerForStage2,
				ilaEdfaPlusPump1LaserPower,
				ilaEdfaPlusPump2LaserPower,
				ilaEdfaPlusPump1Temperature,
				ilaEdfaPlusPump2Temperature,
				ilaEdfaPlusPump1OperatingCurrent,
				ilaEdfaPlusPump2OperatingCurrent,
				ilaEdfaPlusPump1ThermoElectricCoolerCurrent,
				ilaEdfaPlusPump2ThermoElectricCoolerCurrent,
				ilaEdfaPlusPump1CoolingTemperature,
				ilaEdfaPlusPump2CoolingTemperature,
				ilaEdfaPlusVariableOpticalAttenuatorInputPower,
				ilaEdfaPlusVariableOpticalAttenuatorOutputPower,
				ilaEdfaPlusVariableOpticalAttenuatorActualAttenuation,
				ilaEdfaPlusPerformanceTableRowStatus
			}
		STATUS	current

		DESCRIPTION
		"A collection of objects from RFC 1213 made current by this MIB module."

		::= { utlrnd 2 }
	
END
